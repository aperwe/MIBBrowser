---------------------------------------------------------
-- SAGEM-DR.mib
-- MIB generated by MG-SOFT Visual MIB Builder Version 1.5 Build 103
-- Thursday, August 24, 2000 at 17:11:34
---------------------------------------------------------

	SAGEM-DR-MIB DEFINITIONS ::= BEGIN

		IMPORTS 
			enterprises			
				FROM RFC1155-SMI			
			MODULE-IDENTITY			
				FROM SNMPv2-SMI;
	
	
		sagem-dr MODULE-IDENTITY
			LAST-UPDATED "199912230000Z"
			ORGANIZATION
				"SAGEM-Tolbiac"
			CONTACT-INFO
				"    "
			DESCRIPTION
				"The MIB module defines enterprises/sagem-dr entry"
			::= { enterprises 1038 }

	
--
-- Type definitions
--
	
		IntDateTime ::= INTEGER (1..2147483647)
		
		Severity ::= INTEGER
			{
			non-alarmed(1),
			minor(2),
			major(3),
			critical(4),
			warning(5),
			inv-non-alarmed(6),
			inv-minor(7),
			inv-major(8),
			inv-critical(9),
			inv-warning(10)
			}
		
		CommunityAccessList ::= INTEGER
			{
			iONOSANMobserver(1),
			iONOSANMoperator(2),
			iONOSANMsupervisor(3),
			dIRECTACCESSobserver(4),
			dIRECTACCESSoperator(5),
			dIRECTACCESSsupervisor(6),
			iONOSANMclientobserver(7),
			iONOSANMclientoperator(8),
			dIRECTACCESSclientobserver(9),
			dIRECTACCESSclientoperator(10)
			}
		
	
--
-- Node definitions
--
	
	
	END

-----------------------------------------------
-- SAGEM-DR.mib
-----------------------------------------------
