--
-- MSAP-MIB.my
-- MIB generated by MG-SOFT Visual MIB Builder Version 2.5 Build 225
-- Monday, October 08, 2001 at 13:19:43
--

-- ***************************************************************************
-- 
-- MM   MM  SSSS    A    PPPP         MM   MM  III  BBBB
-- M M M M S       A A   P   P        M M M M   I   B   B
-- M  M  M S      A   A  P   P        M  M  M   I   B   B
-- M     M  SSS   AAAAA  PPPP  =====  M     M   I   BBBB
-- M     M     S  A   A  P            M     M   I   B   B
-- M     M     S  A   A  P            M     M   I   B   B
-- M     M SSSS   A   A  P            M     M  III  BBBB
-- 
-- ***************************************************************************
-- LAST-UPDATED       "24.07.2001"
-- ORGANIZATION       "Siemens AG, ICN AS AN"
-- CONTACT-INFO       "Gerald Schreiber
--                     Siemens PSE D 
--                     phone:  +49 (0)40 7678 1234
--                     e-mail: Gerald.Schreiber@bbcom-hh.de"
-- 
-- DESCRIPTION
--    "This module defines the management information base (MIB) for managing
--     features introduced with MSAP.
--     It is meant to be used in connection with the XLD-MIB. 
--     The MSAP-MIB consists of five parts:
--       - AAL1 objects
--       - Line Test Management (LTM) Group
--       - User Port (US) Group
--       - version control group
--       - Trunk Line Maintenance (TLM) group
--     All attributes of the MIB are read only. Only the attributes of the
--     control groups can be written. Thus, the creation and the change of
--     items is only possible by means of the use of the control group. The
--     management system has to write the data which belong to an command
--     which should be execute. Then the command can be written. The result of
--     the command is reported in an attribute or by means of a trap. Created
--     and changed table items are reported by means of traps.
--     The notification about alarms is not part of this MIB. Alarms are
--     reported in the way it is defined by the XLD-MIB."
-- 
-- ***************************************************************************
-- Date        Change                                               Author
-- ***************************************************************************
-- 31.05.2001  AFI Version                                          GSc
-- 
-- 20.06.2001  AFI1 Version
--             Include new MIB-objects for the SW module TLM.       KPK
--             These TLM-MIB-objects are for the SU_POTS32/
--             SU_IVD_POTS16 a POTS PPTP (msapPotsPptpTable and
--             msapPotsPptpControlGroup) and for the SU_ISDN24
--             a ISDN PPTP (msapIsdnPptpTable and
--             msapIsdnPptpControlGroup). 
--             The modules are located in the msap tree. 
--             Therefore the prefix of these modules is msap.
-- 
-- 24.07.2001  PreAFI2 Version                                      HAN
--             Update after external review of AFI and AFI1 
--             version.
--             New specification of US (Aal1/2 support pots/isdn).
-- 
-- 04.09.2001  IUS Version                                      HAN
--             Update after external review of AFI2 
--             version.
-- 
-- 08.10.2001  IUS2 Version                                     HAN
--             Update after external review of IUS 
--             version.
-- 
-- ***************************************************************************
-- 

	MSAP-MIB DEFINITIONS ::= BEGIN

		IMPORTS 
			onu			
				FROM AN-MIB			
			OBJECT-TYPE			
				FROM RFC-1212			
			TRAP-TYPE			
				FROM RFC-1215			
			TimeTicks, Counter, Gauge			
				FROM RFC1155-SMI			
			xldv20IfIndex, xldv20Traps, Unsigned16, Xldv20OperState, Xldv20AdminState, 
			Xldv20ControlStatus, DisplayString			
				FROM XLDV20-MIB;
	
	
--
-- Type definitions
--
	
		MsapAal1IndexType ::= INTEGER (1..3072)
		
		MsapVccIndexType ::= INTEGER
		
		MsapAal1HwUnitIndexType ::= Unsigned16
		
		MsapAal1AlarmStateType ::= INTEGER
		
		MsapAal1CbrClockModeType ::= INTEGER
			{
			synchronous(1),
			srts(2)
			}
		
-- MsapAal1CasType:
-- - SU_CES supports just basic mode at the moment
		MsapAal1CasType ::= INTEGER
			{
			basic(1),
			e1Cas(2)
			}
		
		MsapAal1PartialFillType ::= INTEGER (0..47)
		
-- MsapAal1ConnTypeType:
-- - Only pvc ist supported at the moment
		MsapAal1ConnTypeType ::= INTEGER
			{
			pvc(1),
			activeSvc(2),
			passiveSvc(3),
			other(4)
			}
		
		MsapAal1DbCesType ::= INTEGER
			{
			on(1),
			off(2)
			}
		
		MsapAal1SignalingModeType ::= INTEGER
			{
			nosignaling(1),
			elcpsignaling(2)
			}
		
		MsapAal1CgControlReqType ::= INTEGER
			{
			noRequest(1),
			commExecStarted(5),
			paramFaulty(11),
			requestBusy(12),
			setDataFailed(13),
			aswTimeout(14),
			commandFailed(15),
			commandSucceeded(16),
			lackOfResources(17),
			wrongVccIndex(18),
			wrongHwUnitIndex(19),
			wrongHwUnitType(20),
			indexInUse(21),
			wrongAal1IfIndex(22),
			ifInUse(23),
			wrongAal1IfState(24),
			ifAlreadyLocked(25),
			ifAlreadyUnlocked(26),
			msapCreateAal1Interface(100),
			msapDeleteAal1Interface(101),
			msapModifyAal1Interface(102),
			msapLockAal1Interface(103),
			msapUnlockAal1Interface(104)
			}
		
		MsapAal1CgControlTimerType ::= INTEGER
		
		MsapUsAalxIfIndexType ::= INTEGER
		
		MsapUsAalTypeType ::= INTEGER
			{
			aal1(1),
			aal2(2)
			}
		
		MsapUsPortNumberType ::= INTEGER (1..223)
		
		MsapUsOperStateCauseType ::= OCTET STRING (SIZE (85))
		
		MsapUsIndexType ::= INTEGER (1..14336)
		
		MsapUsAdminStateType ::= INTEGER
			{
			unlocked(1),
			locked(2),
			lockRequest(3)
			}
		
		MsapUsTypeType ::= INTEGER
			{
			ces(1),
			pstn(2),
			isdn-ba(3),
			isdn-ll(4)
			}
		
		MsapUsPptpIfIndexType ::= INTEGER
		
		MsapUsCesServiceType ::= INTEGER
			{
			framed(1),
			unframed(2)
			}
		
		MsapUsTimeSlotMapType ::= INTEGER
		
		MsapUsIsdnLlDChannelMode ::= INTEGER
			{
			multiplexed(1),
			nonMultiplexed(2)
			}
		
		MsapUsCtrlControlReqType ::= INTEGER
			{
			noRequest(1),
			commExecStarted(5),
			paramFaulty(11),
			requestBusy(12),
			setDataFailed(13),
			aswTimeout(14),
			commandFailed(15),
			commandSucceeded(16),
			lackOfResources(17),
			wrongAalxIndex(18),
			wrongPptpIfIndex(19),
			typeNotMatchPptpIfIndex(20),
			indexInUse(21),
			timeSlotInUse(22),
			wrongUsIndex(23),
			wrongUsState(24),
			wrongReferencedType(25),
			typeNotMatchAalxIfIndex(26),
			typeWrongUsType(27),
			typeWrongUsControlReq(28),
			msapCreateUs(100),
			msapDeleteUs(101),
			msapModifyUs(102),
			msapChangeAdminStateUs(103)
			}
		
		MsapUsCtrlControlTimerType ::= INTEGER
		
		MsapLtmGlobalThresholdType ::= INTEGER (0..448)
		
		MsapLtmGlobalTimerType ::= INTEGER
		
		MsapLtmControlRequestType ::= INTEGER
			{
			noRequest(1),
			commExecStarted(5),
			paramFaulty(11),
			requestBusy(12),
			setDataFailed(13),
			aswTimeout(14),
			commandFailed(15),
			commandSucceeded(16),
			lackOfResources(17),
			msapLtmErrWrongIfIndex(20),
			msapLtmErrWrongMeasState(21),
			msapLtmErrWrongInterfaceType(22),
			msapLtmErrWrongResIndex(23),
			msapLtmErrWrongThresIndex(24),
			createAutoMeas(100),
			deleteAutoMeas(101),
			loadDefaultThres(102),
			enablePat(103),
			disablePat(104),
			startMeas(105),
			modifyThres(106),
			enableAccess(107),
			disableAccess(108),
			startSendMeteringImpulses(109),
			stopSendMeteringImpulses(110),
			startSendRingingImpulses(111),
			stopSendRingingImpulses(112),
			startFeedNormal(113),
			stopFeedNormal(114),
			startFeedReversed(115),
			stopFeedReversed(116),
			startTerminalTest(117),
			stopTerminalTest(118),
			startSendTestTone(119),
			stopSendTestTone(120),
			resetPort(121),
			startInterfaceTestSignal(122),
			stopInterfaceTestSignal(123),
			startLoopInterface(124),
			stopLoopInterface(125),
			startLoopNt(126),
			stopLoopNt(127),
			startForcedActivation(128),
			stopForcedActivation(129),
			startBerTest(130),
			stopBerTest(131),
			getLineState(132),
			getMeasResult(133),
			getBerResult(134),
			getAlarmRecord(135),
			loadDefaultGlobals(136)
			}
		
		MsapLtmSltLineAccessType ::= INTEGER
			{
			release(1),
			bridgedConnection(2),
			outwardConnection(3),
			inwardConncetion(4),
			forcedOutwardConnection(5),
			forcedInwardConncetion(6)
			}
		
		MsapLtmSltMeasRequestType ::= INTEGER
			{
			release(1),
			outward(3),
			inward(4),
			forcedOutward(5),
			forcedInward(6),
			testTone(7),
			getDefaultThresholds(8)
			}
		
		MsapLtmSltLineTypeType ::= INTEGER
			{
			pots(1),
			isdn(2)
			}
		
		MsapLtmSltLineStateType ::= INTEGER
			{
			blocked(1),
			idle(2),
			busy(3)
			}
		
		MsapLtmSltViaSplitterType ::= INTEGER
			{
			yes(1),
			no(2)
			}
		
		MsapLtmSltResultStatusType ::= INTEGER
			{
			noData(0),
			measOk(1),
			measPartSucc(2),
			measAbort(3)
			}
		
		MsapLtmMaintCpePotsKindType ::= INTEGER
			{
			off(0),
			testTone(1),
			normalPolarity(2),
			reversedPolarity(3),
			sendMeteringImpulses(4),
			sendRingingImpulses(5),
			terminalTest(6)
			}
		
		MsapLtmMaintCpePotsNumberType ::= Gauge (1..255)
		
		MsapLtmMaintCpePotsRingingTypeType ::= Gauge (0..127)
		
		MsapLtmMaintCpeIsdnKindType ::= INTEGER
			{
			off(0),
			testTone(1)
			}
		
		MsapLtmMaintCpeIsdnLineAccessType ::= INTEGER
			{
			off(0),
			outward(1),
			forcedOutward(2)
			}
		
		MsapLtmSltCheckType ::= INTEGER
			{
			yes(1),
			no(2)
			}
		
		MsapLtmSltAutoAlarmType ::= INTEGER
			{
			on(1),
			off(2)
			}
		
		MsapLtmSltMeasNoFeasReasonType ::= INTEGER
			{
			busy(1),
			timeout(2),
			incomingSeizure(3)
			}
		
		MsapLtmSltPoutForeignVoltageFrequencyAeType ::= Counter
		
		MsapLtmSltPoutForeignVoltageFrequencyAbType ::= Counter
		
		MsapLtmSltPoutForeignVoltageFrequencyBeType ::= Counter
		
		MsapLtmSltPoutForeignVoltageDcAeType ::= Counter
		
		MsapLtmSltPoutForeignVoltageDcAbType ::= Counter
		
		MsapLtmSltPoutForeignVoltageDcBeType ::= Counter
		
		MsapLtmSltPoutForeignVoltageAcAeType ::= Counter
		
		MsapLtmSltPoutForeignVoltageAcAbType ::= Counter
		
		MsapLtmSltPoutForeignVoltageAcBeType ::= Counter
		
		MsapLtmSltPoutResistanceAeType ::= Counter
		
		MsapLtmSltPoutResistanceAbType ::= Counter
		
		MsapLtmSltPoutResistanceBaType ::= Counter
		
		MsapLtmSltPoutResistanceBeType ::= Counter
		
		MsapLtmSltPoutCapacityAeType ::= Counter
		
		MsapLtmSltPoutCapacityAbType ::= Counter
		
		MsapLtmSltPoutCapacityBeType ::= Counter
		
		MsapLtmSltPoutCheckPpaType ::= INTEGER
			{
			ok(13),
			notOk(223)
			}
		
		MsapLtmSltPoutCheckRingerLoadType ::= INTEGER
			{
			ok(13),
			notOk(223)
			}
		
		MsapLtmSltPinOpenCircuitVoltageType ::= Counter
		
		MsapLtmSltPinFeedingCurrentType ::= Counter
		
		MsapLtmSltPinRingingVoltageType ::= Counter
		
		MsapLtmSltPinMeteringVoltageType ::= Counter
		
		MsapLtmSltPinIdleChannelNoiseType ::= Counter
		
		MsapLtmSltPinCheckTestToneType ::= INTEGER
			{
			ok(13),
			notOk(223)
			}
		
		MsapLtmSltPinCheckOffHookDetectionType ::= INTEGER
			{
			ok(13),
			notOk(223)
			}
		
		MsapLtmSltPinCheckCodecType ::= INTEGER
			{
			ok(13),
			notOk(223)
			}
		
		MsapLtmSltPinCheckOverVoltageProtectionType ::= INTEGER
			{
			ok(13),
			notOk(223)
			}
		
		MsapLtmMaintIsdnSwitchType ::= INTEGER
			{
			off(0),
			on(1)
			}
		
		MsapLtmMaintIsdnLoopNtModeType ::= INTEGER
			{
			complete(1),
			b1(2),
			b2(3)
			}
		
		MsapLtmMaintIsdnBerStartType ::= INTEGER
			{
			off(1),
			b1(2),
			b2(3)
			}
		
		MsapPptpPortDataType ::= OCTET STRING (SIZE (0..40))
		
		MsapNbOperStateType ::= INTEGER
			{
			nbBlocked(1),
			nbIdle(2),
			nbBusy(3),
			nbNotAvailable(4)
			}
		
		MsapPptpConnectionType ::= INTEGER
			{
			pptpNo(1),
			pptpToWire(2)
			}
		
		MsapPotsKindOfPortType ::= INTEGER
			{
			potsInterface(1),
			emergencyEquipmentPort(2),
			testProbePort(4)
			}
		
		MsapPotsInputLevelF2Type ::= INTEGER (0..60)
		
		MsapPotsOutputLevelF2Type ::= INTEGER (0..60)
		
		MsapPotsImpedanceType ::= INTEGER
			{
			imp600Ohm(1),
			imp900Ohm(2),
			impComplex(4)
			}
		
		MsapPotsMeteringSignalTypeType ::= INTEGER
			{
			no(1),
			dependingOnMessage(2),
			silentReversalOnly(4),
			frequencyOnly(8)
			}
		
		MsapPotsFeedingType ::= INTEGER
			{
			ordinaryPhone(1),
			payPhone(2)
			}
		
		MsapPotsGroundKeyType ::= INTEGER
			{
			disable(1),
			enable(2)
			}
		
		MsapPotsMeteringVoltageType ::= INTEGER
			{
			meteringVoltagePrjSpecific(1),
			meteringVoltage2Vrms(2)
			}
		
		MsapPotsMeteringFrequencyType ::= INTEGER
			{
			meteringFrq12kHz(1),
			meteringFrq16kHz(2)
			}
		
		MsapPotsRingingFrequencyType ::= INTEGER
			{
			ringingFrqPrjSpecific(1),
			ringingFrq25Hz(2),
			ringingFrq50Hz(3)
			}
		
		MsapPotsAdditionalStateInformationType ::= OCTET STRING (SIZE (82))
		
		MsapPotsCtrlControlReqType ::= INTEGER
			{
			noRequest(1),
			commExecStarted(5),
			paramFaulty(11),
			requestBusy(12),
			setDataFailed(13),
			aswTimeout(14),
			commandFailed(15),
			commandSucceeded(16),
			wrongHwUnitIndex(17),
			wrongHwUnitType(18),
			wrongState(19),
			msapPotsPptpChangeData(100)
			}
		
		MsapPotsCtrlControlTimerType ::= INTEGER
		
		MsapIsdnOnOffType ::= INTEGER
			{
			isdnOn(1),
			isdnOff(2)
			}
		
		MsapIsdnB1ServiceType ::= INTEGER
			{
			isdnNotConfigured(1),
			isdnBra(2),
			isdnLl(4),
			isdnPlc(8)
			}
		
		MsapIsdnLoopType ::= INTEGER
			{
			isdnOffLoop(1),
			isdnAccessLoop(2)
			}
		
		MsapIsdnB2ServiceType ::= INTEGER
			{
			isdnNotConfigured(1),
			isdnBra(2),
			isdnLl(4)
			}
		
		MsapIsdnDServiceType ::= INTEGER
			{
			isdnNotConfigured(1),
			isdnTransparent(2)
			}
		
		MsapIsdnYesNoType ::= INTEGER
			{
			isdnYes(1),
			isdnNo(2)
			}
		
		MsapIsdnEocSendType ::= OCTET STRING (SIZE (2))
		
		MsapIsdnAdditionalStateInformationType ::= OCTET STRING (SIZE (93))
		
		MsapIsdnCtrlControlReqType ::= INTEGER
			{
			noRequest(1),
			commExecStarted(5),
			paramFaulty(11),
			requestBusy(12),
			setDataFailed(13),
			aswTimeout(14),
			commandFailed(15),
			commandSucceeded(16),
			wrongHwUnitIndex(17),
			wrongHwUnitType(18),
			wrongState(19),
			inUse(20),
			msapIsdnPptpChangeData(100),
			msapIsdnPptpEocSend(101),
			msapIsdnPptpEocReset(102)
			}
		
		MsapIsdnCtrlControlTimerType ::= INTEGER
		
	
--
-- Node definitions
--
	
		msap OBJECT IDENTIFIER ::= { onu 6 }
		
-- *************************************************************************
-- *************************************************************************
-- *************************************************************************
-- *************************************************************************
-- MSAP MIB VERSION CONTROL
-- *************************************************************************
-- *************************************************************************
-- *************************************************************************
-- *************************************************************************
-- 
		msapMibVersionControl OBJECT IDENTIFIER ::= { msap 1 }
		
		msapMibVersion OBJECT-TYPE
			SYNTAX INTEGER
				{
				version1(1),
				preAfi2(2)
				}
			ACCESS read-only
			STATUS mandatory
			DESCRIPTION
				"The version of the MSAP-MIB
				1: first version with AAL1, LTM, US and TLM
				2: preAFI2 after external review AFI/AFI1
				3: IUS after external review AFI2
				4: IUS2 after external review IUS"
			DEFVAL { preAfi2 }
			::= { msapMibVersionControl 1 }
		
-- *************************************************************************
-- *************************************************************************
-- *************************************************************************
-- *************************************************************************
-- MSAP AAL1 Group
-- *************************************************************************
-- *************************************************************************
-- *************************************************************************
-- *************************************************************************
-- 
		msapAal1Objects OBJECT IDENTIFIER ::= { msap 2 }
		
-- *************************************************************************
-- *************************************************************************
-- MSAP AAL1 Interfacetable
-- *************************************************************************
-- *************************************************************************
-- 
		msapAal1IfTable OBJECT-TYPE
			SYNTAX SEQUENCE OF MsapAal1IfEntry
			ACCESS not-accessible
			STATUS mandatory
			DESCRIPTION
				"The CES configuration table used to manage interworking
				between CBR interfaces or channels and ATM Virtual Channel
				Connections (VCCs).  The reverse mapping is shown in the
				msapCESMappingTable."
--DEFAULT next-function-async     fsnAal1IfEntryNext
--DEFAULT get-function-async      fsnAal1IfEntryGet
			::= { msapAal1Objects 1 }
		
		msapAal1IfEntry OBJECT-TYPE
			SYNTAX MsapAal1IfEntry
			ACCESS not-accessible
			STATUS mandatory
			DESCRIPTION
				"An entry in the CES configuration table.  There is one
				entry in the table per CES entity, mapping one CBR
				interface, channel, or bundle to an ATM VCL.
				
				Creation of a row in this table with a non-zero
				msapCESAtmIndex causes a corresponding entry in the
				atmVclTable of the ATM-MIB (RFC1695) to be created."
			INDEX { msapAal1IfIndex }
			::= { msapAal1IfTable 1 }
		
		MsapAal1IfEntry ::=
			SEQUENCE { 
				msapAal1IfIndex
					MsapAal1IndexType,
				msapAal1VccIndex
					MsapVccIndexType,
				msapAal1OperState
					Xldv20OperState,
				msapAal1AdminState
					Xldv20AdminState,
				msapAal1HwUnitIndex
					MsapAal1HwUnitIndexType,
				msapAal1AlarmState
					MsapAal1AlarmStateType,
				msapAal1CbrClockMode
					MsapAal1CbrClockModeType,
				msapAal1Cas
					MsapAal1CasType,
				msapAal1PartialFill
					MsapAal1PartialFillType,
				msapAal1BufMaxSize
					INTEGER,
				msapAal1CdvRxT
					INTEGER,
				msapAal1CellLossIntegrationPeriod
					INTEGER,
				msapAal1ConnType
					MsapAal1ConnTypeType,
				msapAal1DbCes
					MsapAal1DbCesType,
				msapAal1DbCesIdlePattern
					INTEGER,
				msapAal1SignalingMode
					MsapAal1SignalingModeType
			 }

		msapAal1IfIndex OBJECT-TYPE
			SYNTAX MsapAal1IndexType
			ACCESS read-only
			STATUS mandatory
			DESCRIPTION
				"A unique value to identify an entry in the msapAal1IfTable."
			::= { msapAal1IfEntry 1 }
		
		msapAal1VccIndex OBJECT-TYPE
			SYNTAX MsapVccIndexType
			ACCESS read-only
			STATUS mandatory
			DESCRIPTION
				"A unique value to identify an entry in the VCC TP table, which determines the VCC used for AAL1 connection."
			::= { msapAal1IfEntry 2 }
		
		msapAal1OperState OBJECT-TYPE
			SYNTAX Xldv20OperState
			ACCESS read-only
			STATUS mandatory
			DESCRIPTION
				"Identifies whether or not an AAL1 interface is capable of performing its normal function."
			::= { msapAal1IfEntry 3 }
		
		msapAal1AdminState OBJECT-TYPE
			SYNTAX Xldv20AdminState
			ACCESS read-only
			STATUS mandatory
			DESCRIPTION
				"This attribute reports whether the AAL1 interface is activated (unlocked) or deactivated (locked)."
			::= { msapAal1IfEntry 4 }
		
		msapAal1HwUnitIndex OBJECT-TYPE
			SYNTAX MsapAal1HwUnitIndexType
			ACCESS read-only
			STATUS mandatory
			DESCRIPTION
				"A unique value to identify a hardware unit (SU_CES, SU_ISDN,SU_POTS, SU_IVD_POTS) on which the AAL1 interface is located (xldv20HwUnitTable)."
			::= { msapAal1IfEntry 5 }
		
		msapAal1AlarmState OBJECT-TYPE
			SYNTAX MsapAal1AlarmStateType
			ACCESS read-only
			STATUS mandatory
			DESCRIPTION
				"The current alarm state of the AAL1 interface."
			::= { msapAal1IfEntry 6 }
		
		msapAal1CbrClockMode OBJECT-TYPE
			SYNTAX MsapAal1CbrClockModeType
			ACCESS read-only
			STATUS mandatory
			DESCRIPTION
				"Define E1 service clocking mode. This maps into transmit clock source of CBR interface. 	
				For structured modes this value must be set to synchronous(1). For unstructured mode only srts(2) is supported at this time.
				"
			::= { msapAal1IfEntry 7 }
		
		msapAal1Cas OBJECT-TYPE
			SYNTAX MsapAal1CasType
			ACCESS read-only
			STATUS mandatory
			DESCRIPTION
				"This parameter selects which AAL1 Format should be used: Basic(1) does not carry CAS bits, and uses a single 125 usec frame. e1Cas(2) carries CAS bits in a multiframe structure for E1. This applies to structured interfaces only. Default is basic (1). For unstructured interfaces this value must be set to the default of basic (1). Only basic (1) is supported by the SU_CES, SU_ISDN,SU_POTS and SU_IVD_POTS."
			::= { msapAal1IfEntry 8 }
		
		msapAal1PartialFill OBJECT-TYPE
			SYNTAX MsapAal1PartialFillType
			ACCESS read-only
			STATUS mandatory
			DESCRIPTION
				"If partial cell fill is used, the number of user octets per cell must be set with this parameter.  Setting this parameter to zero disables partial cell fill, and causes all cells to be completely filled before they are sent."
			::= { msapAal1IfEntry 9 }
		
		msapAal1BufMaxSize OBJECT-TYPE
			SYNTAX INTEGER (1..65536)
			ACCESS read-only
			STATUS mandatory
			DESCRIPTION
				"Define maximum size in 10 microsecond increments of the reassembly buffer. Some implementations may want allow the maximum buffer size to be programmed to a size less than the physical limit to reduce the maximum delay through a circuit. Because of hardware-restrictions on the SU_CES this values is only adjustable on E1-frame-base -> 125us increments. BufMaxSize has to be a multiple of 125us."
			::= { msapAal1IfEntry 10 }
		
		msapAal1CdvRxT OBJECT-TYPE
			SYNTAX INTEGER (1..65535)
			ACCESS read-only
			STATUS mandatory
			DESCRIPTION
				"The maximum cell arrival jitter in 10 usec increments that the reassembly process will tolerate in the cell stream without producing errors on the CBR service interface. Because of hardware-restrictions on the SU_CES this values is only adjustable on E1-frame-base -> 125us increments. BufMaxSize has to be a multiple of 125us."
			::= { msapAal1IfEntry 11 }
		
		msapAal1CellLossIntegrationPeriod OBJECT-TYPE
			SYNTAX INTEGER (1000..65535)
			ACCESS read-only
			STATUS mandatory
			DESCRIPTION
				"The time in milliseconds for the cell loss integration period. If cells are continuously lost for this period of time, msapCESCellLossStatus is set to loss (2). The default definition is 2500."
			DEFVAL { 2500 }
			::= { msapAal1IfEntry 12 }
		
		msapAal1ConnType OBJECT-TYPE
			SYNTAX MsapAal1ConnTypeType
			ACCESS read-only
			STATUS mandatory
			DESCRIPTION
				"The type of ATM connectivity between associated CES IWF's.
				Valid values are:
				   other      	- none of the types specified below
				   pvc        	- supporting connectivity is a permanent
				                 	  virtual connection
				   activeSvc  	- attempt calls whenever none established
				   passiveSvc 	- accept calls
				
				"
			::= { msapAal1IfEntry 13 }
		
		msapAal1DbCes OBJECT-TYPE
			SYNTAX MsapAal1DbCesType
			ACCESS read-only
			STATUS mandatory
			DESCRIPTION
				"This value enables the elimination / generation of an idle bitpattern (defined by msapAal1DbCesIdlePattern)."
			::= { msapAal1IfEntry 14 }
		
		msapAal1DbCesIdlePattern OBJECT-TYPE
			SYNTAX INTEGER (0..255)
			ACCESS read-only
			STATUS mandatory
			DESCRIPTION
				"Defines the idle bitpattern which is to eliminate / generate. The pattern is only valid while msapAal1DbCes = on."
			::= { msapAal1IfEntry 15 }
		
		msapAal1SignalingMode OBJECT-TYPE
			SYNTAX MsapAal1SignalingModeType
			ACCESS read-only
			STATUS mandatory
			DESCRIPTION
				"Defines the signaling mode of the Aal1 interface. Possible values are: nosignaling, elcpsignaling"
			::= { msapAal1IfEntry 16 }
		
-- *************************************************************************
-- *************************************************************************
-- MSAP AAL1 Controlgroup
-- *************************************************************************
-- *************************************************************************
-- 
		msapAal1ControlGroup OBJECT IDENTIFIER ::= { msapAal1Objects 2 }
		
-- 
		msapAal1CgControlReq OBJECT-TYPE
			SYNTAX MsapAal1CgControlReqType
			ACCESS read-write
			STATUS mandatory
			DESCRIPTION
				" To activate a configured set of data (command: activateData).  "
--DEFAULT test-function-async     fsnAal1CgTest
--DEFAULT next-function-async     fsnAal1CgNext
--DEFAULT set-function-async      fsnAal1CgSet
--DEFAULT get-function-async      fsnAal1CgGet
			::= { msapAal1ControlGroup 1 }
		
		msapAal1CgControlStatus OBJECT-TYPE
			SYNTAX Xldv20ControlStatus
			ACCESS read-only
			STATUS mandatory
			DESCRIPTION
				" Indicates the status of a control request. "
--DEFAULT next-function-async     fsnAal1CgNext
--DEFAULT get-function-async      fsnAal1CgGet
			::= { msapAal1ControlGroup 2 }
		
		msapAal1CgControlReqResult OBJECT-TYPE
			SYNTAX MsapAal1CgControlReqType
			ACCESS read-only
			STATUS mandatory
			DESCRIPTION
				" The result of the last user command. "
--DEFAULT next-function-async     fsnAal1CgNext
--DEFAULT get-function-async      fsnAal1CgGet
			::= { msapAal1ControlGroup 3 }
		
		msapAal1CgControlTimer OBJECT-TYPE
			SYNTAX MsapAal1CgControlTimerType
			ACCESS read-only
			STATUS mandatory
			DESCRIPTION
				" The time stamp of the last command (end of command). "
--DEFAULT next-function-async     fsnAal1CgNext
--DEFAULT get-function-async      fsnAal1CgGet
			::= { msapAal1ControlGroup 4 }
		
		msapAal1CgIfIndex OBJECT-TYPE
			SYNTAX MsapAal1IndexType
			ACCESS read-write
			STATUS mandatory
			DESCRIPTION
				"A unique value to identify an entry in the msapAal1IfTable."
--DEFAULT test-function-async     fsnAal1CgTest
--DEFAULT next-function-async     fsnAal1CgNext
--DEFAULT set-function-async      fsnAal1CgSet
--DEFAULT get-function-async      fsnAal1CgGet
			::= { msapAal1ControlGroup 5 }
		
		msapAal1CgVccIndex OBJECT-TYPE
			SYNTAX MsapVccIndexType
			ACCESS read-write
			STATUS mandatory
			DESCRIPTION
				"A unique value to identify an entry in the VCC TP table, which determines the VCC used for AAL1 connection."
--DEFAULT test-function-async     fsnAal1CgTest
--DEFAULT next-function-async     fsnAal1CgNext
--DEFAULT set-function-async      fsnAal1CgSet
--DEFAULT get-function-async      fsnAal1CgGet
			::= { msapAal1ControlGroup 6 }
		
		msapAal1CgHwUnitIndex OBJECT-TYPE
			SYNTAX MsapAal1HwUnitIndexType
			ACCESS read-write
			STATUS mandatory
			DESCRIPTION
				"A unique value to identify a hardware unit (SU_CES, SU_ISDN,SU_POTS, SU_IVD_POTS) on which the AAL1 interface is located (xldv20HwUnitTable)."
--DEFAULT test-function-async     fsnAal1CgTest
--DEFAULT next-function-async     fsnAal1CgNext
--DEFAULT set-function-async      fsnAal1CgSet
--DEFAULT get-function-async      fsnAal1CgGet
			::= { msapAal1ControlGroup 7 }
		
		msapAal1CgCbrClockMode OBJECT-TYPE
			SYNTAX MsapAal1CbrClockModeType
			ACCESS read-write
			STATUS mandatory
			DESCRIPTION
				"Define E1 service clocking mode. This maps into transmit clock source of CBR interface. 	
				For structured modes this value must be set to synchronous(1). For unstructured mode only srts(2) is supported at this time.
				"
--DEFAULT test-function-async     fsnAal1CgTest
--DEFAULT next-function-async     fsnAal1CgNext
--DEFAULT set-function-async      fsnAal1CgSet
--DEFAULT get-function-async      fsnAal1CgGet
			::= { msapAal1ControlGroup 8 }
		
		msapAal1CgCas OBJECT-TYPE
			SYNTAX MsapAal1CasType
			ACCESS read-write
			STATUS mandatory
			DESCRIPTION
				"This parameter selects which AAL1 Format should be used: Basic(1) does not carry CAS bits, and uses a single 125 usec frame. e1Cas(2) carries CAS bits in a multiframe structure for E1. This applies to structured interfaces only. Default is basic (1). For unstructured interfaces this value must be set to the default of basic (1). Only basic (1) is supported by the SU_CES, SU_ISDN,SU_POTS and SU_IVD_POTS."
--DEFAULT test-function-async     fsnAal1CgTest
--DEFAULT next-function-async     fsnAal1CgNext
--DEFAULT set-function-async      fsnAal1CgSet
--DEFAULT get-function-async      fsnAal1CgGet
			::= { msapAal1ControlGroup 9 }
		
		msapAal1CgPartialFill OBJECT-TYPE
			SYNTAX MsapAal1PartialFillType
			ACCESS read-write
			STATUS mandatory
			DESCRIPTION
				"If partial cell fill is used, the number of user octets per cell must be set with this parameter.  Setting this parameter to zero disables partial cell fill, and causes all cells to be completely filled before they are sent."
--DEFAULT test-function-async     fsnAal1CgTest
--DEFAULT next-function-async     fsnAal1CgNext
--DEFAULT set-function-async      fsnAal1CgSet
--DEFAULT get-function-async      fsnAal1CgGet
			::= { msapAal1ControlGroup 10 }
		
		msapAal1CgBufMaxSize OBJECT-TYPE
			SYNTAX INTEGER (1..65536)
			ACCESS read-write
			STATUS mandatory
			DESCRIPTION
				"Define maximum size in 10 microsecond increments of the reassembly buffer. Some implementations may want allow the maximum buffer size to be programmed to a size less than the physical limit to reduce the maximum delay through a circuit. Because of hardware-restrictions on the SU_CES this values is only adjustable on E1-frame-base -> 125us increments. BufMaxSize has to be a multiple of 125us."
--DEFAULT test-function-async     fsnAal1CgTest
--DEFAULT next-function-async     fsnAal1CgNext
--DEFAULT set-function-async      fsnAal1CgSet
--DEFAULT get-function-async      fsnAal1CgGet
			::= { msapAal1ControlGroup 11 }
		
		msapAal1CgCdvRxT OBJECT-TYPE
			SYNTAX INTEGER (1..65535)
			ACCESS read-write
			STATUS mandatory
			DESCRIPTION
				"The maximum cell arrival jitter in 10 usec increments that the reassembly process will tolerate in the cell stream without producing errors on the CBR service interface. Because of hardware-restrictions on the SU_CES this values is only adjustable on E1-frame-base -> 125us increments. BufMaxSize has to be a multiple of 125us."
--DEFAULT test-function-async     fsnAal1CgTest
--DEFAULT next-function-async     fsnAal1CgNext
--DEFAULT set-function-async      fsnAal1CgSet
--DEFAULT get-function-async      fsnAal1CgGet
			::= { msapAal1ControlGroup 12 }
		
		msapAal1CgCellLossIntegrationPeriod OBJECT-TYPE
			SYNTAX INTEGER (1000..65535)
			ACCESS read-write
			STATUS mandatory
			DESCRIPTION
				"The time in milliseconds for the cell loss integration period. If cells are continuously lost for this period of time, msapCESCellLossStatus is set to loss (2). The default definition is 2500."
			DEFVAL { 2500 }
--DEFAULT test-function-async     fsnAal1CgTest
--DEFAULT next-function-async     fsnAal1CgNext
--DEFAULT set-function-async      fsnAal1CgSet
--DEFAULT get-function-async      fsnAal1CgGet
			::= { msapAal1ControlGroup 13 }
		
		msapAal1CgConnType OBJECT-TYPE
			SYNTAX MsapAal1ConnTypeType
			ACCESS read-write
			STATUS mandatory
			DESCRIPTION
				"The type of ATM connectivity between associated CES IWF's.
				Valid values are:
				   other      	- none of the types specified below
				   pvc        	- supporting connectivity is a permanent
				                 	  virtual connection
				   activeSvc  	- attempt calls whenever none established
				   passiveSvc 	- accept calls
				
				"
--DEFAULT test-function-async     fsnAal1CgTest
--DEFAULT next-function-async     fsnAal1CgNext
--DEFAULT set-function-async      fsnAal1CgSet
--DEFAULT get-function-async      fsnAal1CgGet
			::= { msapAal1ControlGroup 14 }
		
		msapAal1CgDbCes OBJECT-TYPE
			SYNTAX MsapAal1DbCesType
			ACCESS read-write
			STATUS mandatory
			DESCRIPTION
				"This value enables the elimination / generation of an idle bitpattern (defined by msapAal1DbCesIdlePattern)."
--DEFAULT test-function-async     fsnAal1CgTest
--DEFAULT next-function-async     fsnAal1CgNext
--DEFAULT set-function-async      fsnAal1CgSet
--DEFAULT get-function-async      fsnAal1CgGet
			::= { msapAal1ControlGroup 15 }
		
		msapAal1CgDbCesIdlePattern OBJECT-TYPE
			SYNTAX INTEGER
			ACCESS read-write
			STATUS mandatory
			DESCRIPTION
				"Defines the idle bitpattern which is to eliminate / generate. The pattern is only valid while msapAal1DbCes = on."
--DEFAULT test-function-async     fsnAal1CgTest
--DEFAULT next-function-async     fsnAal1CgNext
--DEFAULT set-function-async      fsnAal1CgSet
--DEFAULT get-function-async      fsnAal1CgGet
			::= { msapAal1ControlGroup 16 }
		
		msapAal1CgSignalingMode OBJECT-TYPE
			SYNTAX MsapAal1SignalingModeType
			ACCESS read-write
			STATUS mandatory
			DESCRIPTION
				"Defines the signaling mode of the Aal1 interface. Possible values are: nosignaling, elcpsignaling"
--DEFAULT test-function-async     fsnAal1CgTest
--DEFAULT next-function-async     fsnAal1CgNext
--DEFAULT set-function-async      fsnAal1CgSet
--DEFAULT get-function-async      fsnAal1CgGet
			::= { msapAal1ControlGroup 17 }
		
-- *************************************************************************
-- *************************************************************************
-- MSAP AAL1 Traps
-- *************************************************************************
-- *************************************************************************
-- 
		msapAal1Traps OBJECT IDENTIFIER ::= { msapAal1Objects 3 }
		
		msapAal1TrapVars OBJECT IDENTIFIER ::= { msapAal1Traps 1 }
		
		msapAal1TvTimeAndDate OBJECT-TYPE
			SYNTAX INTEGER
			ACCESS not-accessible
			STATUS mandatory
			DESCRIPTION
				"The time when a traps is sent. It is a parameter of all traps."
			::= { msapAal1TrapVars 1 }
		
		msapAal1TvIfIndex OBJECT-TYPE
			SYNTAX MsapAal1IndexType
			ACCESS not-accessible
			STATUS mandatory
			DESCRIPTION
				"A unique value to identify an entry in the msapAal1IfTable."
			::= { msapAal1TrapVars 2 }
		
		msapAal1TvVccIndex OBJECT-TYPE
			SYNTAX MsapVccIndexType
			ACCESS not-accessible
			STATUS mandatory
			DESCRIPTION
				"A unique value to identify an entry in the VCC TP table, which determines the VCC used for AAL1 connection."
			::= { msapAal1TrapVars 3 }
		
		msapAal1TvOperState OBJECT-TYPE
			SYNTAX Xldv20OperState
			ACCESS not-accessible
			STATUS mandatory
			DESCRIPTION
				"Parameter for the msapTrAal1InterfaceCreated and 
				msapTrAal1InterfaceOperStateChanged Trap. The attribute 
				in the msapAal1IfTable."
			::= { msapAal1TrapVars 4 }
		
		msapAal1TvAdminState OBJECT-TYPE
			SYNTAX Xldv20AdminState
			ACCESS not-accessible
			STATUS mandatory
			DESCRIPTION
				"Parameter for the msapTrAal1InterfaceCreated and the 
				msapTrAal1InterfaceAdminStateChanged Trap. The attribute 
				in the msapAal1IfTable."
			::= { msapAal1TrapVars 5 }
		
		msapAal1TvHwUnitIndex OBJECT-TYPE
			SYNTAX MsapAal1HwUnitIndexType
			ACCESS not-accessible
			STATUS mandatory
			DESCRIPTION
				"A unique value to identify a hardware unit (SU_CES, SU_ISDN,SU_POTS, SU_IVD_POTS) on which the AAL1 interface is located (xldv20HwUnitTable)."
			::= { msapAal1TrapVars 6 }
		
		msapAal1TvAlarmState OBJECT-TYPE
			SYNTAX MsapAal1AlarmStateType
			ACCESS not-accessible
			STATUS mandatory
			DESCRIPTION
				"Parameter for the msapTrAal1InterfaceCreated Trap. The attribute 
				in the msapAal1IfTable."
			::= { msapAal1TrapVars 7 }
		
		msapAal1TvCbrClockMode OBJECT-TYPE
			SYNTAX MsapAal1CbrClockModeType
			ACCESS not-accessible
			STATUS mandatory
			DESCRIPTION
				"Define E1 service clocking mode. This maps into transmit clock source of CBR interface. 	
				For structured modes this value must be set to synchronous(1). For unstructured mode only srts(2) is supported at this time.
				"
			::= { msapAal1TrapVars 8 }
		
		msapAal1TvCas OBJECT-TYPE
			SYNTAX MsapAal1CasType
			ACCESS not-accessible
			STATUS mandatory
			DESCRIPTION
				"This parameter selects which AAL1 Format should be used: Basic(1) does not carry CAS bits, and uses a single 125 usec frame. e1Cas(2) carries CAS bits in a multiframe structure for E1. This applies to structured interfaces only. Default is basic (1). For unstructured interfaces this value must be set to the default of basic (1). Only basic (1) is supported by the SU_CES, SU_ISDN,SU_POTS and SU_IVD_POTS."
			::= { msapAal1TrapVars 9 }
		
		msapAal1TvPartialFill OBJECT-TYPE
			SYNTAX MsapAal1PartialFillType
			ACCESS not-accessible
			STATUS mandatory
			DESCRIPTION
				"If partial cell fill is used, the number of user octets per cell must be set with this parameter.  Setting this parameter to zero disables partial cell fill, and causes all cells to be completely filled before they are sent."
			::= { msapAal1TrapVars 10 }
		
		msapAal1TvBufMaxSize OBJECT-TYPE
			SYNTAX INTEGER (1..65536)
			ACCESS not-accessible
			STATUS mandatory
			DESCRIPTION
				"Define maximum size in 10 microsecond increments of the reassembly buffer. Some implementations may want allow the maximum buffer size to be programmed to a size less than the physical limit to reduce the maximum delay through a circuit. Because of hardware-restrictions on the SU_CES this values is only adjustable on E1-frame-base -> 125us increments. BufMaxSize has to be a multiple of 125us."
			::= { msapAal1TrapVars 11 }
		
		msapAal1TvCdvRxT OBJECT-TYPE
			SYNTAX INTEGER (1..65535)
			ACCESS not-accessible
			STATUS mandatory
			DESCRIPTION
				"The maximum cell arrival jitter in 10 usec increments that the reassembly process will tolerate in the cell stream without producing errors on the CBR service interface. Because of hardware-restrictions on the SU_CES this values is only adjustable on E1-frame-base -> 125us increments. BufMaxSize has to be a multiple of 125us."
			::= { msapAal1TrapVars 12 }
		
		msapAal1TvCellLossIntegrationPeriod OBJECT-TYPE
			SYNTAX INTEGER (1000..65535)
			ACCESS not-accessible
			STATUS mandatory
			DESCRIPTION
				"The time in milliseconds for the cell loss integration period. If cells are continuously lost for this period of time, msapCESCellLossStatus is set to loss (2). The default definition is 2500."
			::= { msapAal1TrapVars 13 }
		
		msapAal1TvConnType OBJECT-TYPE
			SYNTAX MsapAal1ConnTypeType
			ACCESS not-accessible
			STATUS mandatory
			DESCRIPTION
				"The type of ATM connectivity between associated CES IWF's.
				Valid values are:
				   other      	- none of the types specified below
				   pvc        	- supporting connectivity is a permanent
				                 	  virtual connection
				   activeSvc  	- attempt calls whenever none established
				   passiveSvc 	- accept calls
				
				"
			::= { msapAal1TrapVars 14 }
		
		msapAal1TvDbCes OBJECT-TYPE
			SYNTAX MsapAal1DbCesType
			ACCESS not-accessible
			STATUS mandatory
			DESCRIPTION
				"This value enables the elimination / generation of an idle bitpattern (defined by msapAal1DbCesIdlePattern)."
			::= { msapAal1TrapVars 15 }
		
		msapAal1TvDbCesIdlePattern OBJECT-TYPE
			SYNTAX INTEGER
			ACCESS not-accessible
			STATUS mandatory
			DESCRIPTION
				"Defines the idle bitpattern which is to eliminate / generate. The pattern is only valid while msapAal1DbCes = on."
			::= { msapAal1TrapVars 16 }
		
		msapAal1TvSignalingMode OBJECT-TYPE
			SYNTAX MsapAal1SignalingModeType
			ACCESS not-accessible
			STATUS mandatory
			DESCRIPTION
				"Defines the signaling mode of the Aal1 interface. Possible values are: nosignaling, elcpsignaling"
			::= { msapAal1TrapVars 17 }
		
-- *************************************************************************
-- *************************************************************************
-- *************************************************************************
-- *************************************************************************
-- MSAP USERPORT (US) Group
-- *************************************************************************
-- *************************************************************************
-- *************************************************************************
-- *************************************************************************
-- 
		msapUserPortObjects OBJECT IDENTIFIER ::= { msap 3 }
		
-- *************************************************************************
-- *************************************************************************
-- MSAP US Table
-- *************************************************************************
-- *************************************************************************
-- 
		msapUsTable OBJECT-TYPE
			SYNTAX SEQUENCE OF MsapUsEntry
			ACCESS not-accessible
			STATUS mandatory
			DESCRIPTION
				"This Table describes the common attributes for the creation of 
				user interfaces (ISDNPPTP, PotsPPTP, etc.)"
--DEFAULT next-function-async     fsnUsEntryNext
--DEFAULT get-function-async      fsnUsEntryGet
			::= { msapUserPortObjects 1 }
		
		msapUsEntry OBJECT-TYPE
			SYNTAX MsapUsEntry
			ACCESS not-accessible
			STATUS mandatory
			INDEX { msapUsIndex }
			::= { msapUsTable 1 }
		
		MsapUsEntry ::=
			SEQUENCE { 
				msapUsPptpIfIndex
					MsapUsPptpIfIndexType,
				msapUsType
					MsapUsTypeType,
				msapUsAdminState
					MsapUsAdminStateType,
				msapUsOperState
					Xldv20OperState,
				msapUsIndex
					MsapUsIndexType
			 }

-- info-ROU: GET db
		msapUsPptpIfIndex OBJECT-TYPE
			SYNTAX MsapUsPptpIfIndexType
			ACCESS read-only
			STATUS mandatory
			DESCRIPTION
				"A unique value to identify an entry in one PPTP table 
				(msapPotsPptpTable, msapIsdnPptpTable or 
				xldV20E1nPPTPTable). "
			::= { msapUsEntry 1 }
		
-- info-ROU: GET db
		msapUsType OBJECT-TYPE
			SYNTAX MsapUsTypeType
			ACCESS read-only
			STATUS mandatory
			DESCRIPTION
				"A unique value to identify the type of the user port 
				(pots, ces, isdn-ba, isdn-ll). "
			::= { msapUsEntry 2 }
		
-- info-ROU: GET db
		msapUsAdminState OBJECT-TYPE
			SYNTAX MsapUsAdminStateType
			ACCESS read-only
			STATUS mandatory
			DESCRIPTION
				"This attribute reports whether the US object is 
				unlocked (activated), locked (deactivated) or 
				locked request."
			::= { msapUsEntry 3 }
		
-- info-ROU: GET us
		msapUsOperState OBJECT-TYPE
			SYNTAX Xldv20OperState
			ACCESS read-only
			STATUS mandatory
			DESCRIPTION
				"Identifies whether or not US object is capable of 
				performing it's normal function."
			::= { msapUsEntry 4 }
		
-- info-ROU: GET db
		msapUsIndex OBJECT-TYPE
			SYNTAX MsapUsIndexType
			ACCESS read-only
			STATUS mandatory
			DESCRIPTION
				"A unique value to identify an entry in the msapUsTable."
			::= { msapUsEntry 5 }
		
-- *************************************************************************
-- *************************************************************************
-- MSAP POTS US Table
-- *************************************************************************
-- *************************************************************************
-- 
		msapPstnUsTable OBJECT-TYPE
			SYNTAX SEQUENCE OF MsapPstnUsEntry
			ACCESS not-accessible
			STATUS mandatory
--DEFAULT next-function-async     fsnPstnUsEntryNext
--DEFAULT get-function-async      fsnPstnUsEntryGet
			::= { msapUserPortObjects 2 }
		
		msapPstnUsEntry OBJECT-TYPE
			SYNTAX MsapPstnUsEntry
			ACCESS not-accessible
			STATUS mandatory
			INDEX { msapUsIndex }
			::= { msapPstnUsTable 1 }
		
		MsapPstnUsEntry ::=
			SEQUENCE { 
				msapPstnUsAalxIfIndex
					MsapUsAalxIfIndexType,
				msapPstnUsAalType
					MsapUsAalTypeType,
				msapPstnUsPortNumber
					MsapUsPortNumberType,
				msapPstnUsOperStateCause
					MsapUsOperStateCauseType
			 }

-- info-ROU: GET db
		msapPstnUsAalxIfIndex OBJECT-TYPE
			SYNTAX MsapUsAalxIfIndexType
			ACCESS read-only
			STATUS mandatory
			DESCRIPTION
				"A value to identify an entry in the AAL1/2 
				Interface table."
			::= { msapPstnUsEntry 1 }
		
-- info-ROU: GET db
		msapPstnUsAalType OBJECT-TYPE
			SYNTAX MsapUsAalTypeType
			ACCESS read-only
			STATUS mandatory
			DESCRIPTION
				"Type of the AALxIf for the UsType ISDN_BA and PSTN
				0x01:	AAL1 
				0x02:	AAL2
				"
			::= { msapPstnUsEntry 2 }
		
-- info-ROU: GET db
		msapPstnUsPortNumber OBJECT-TYPE
			SYNTAX MsapUsPortNumberType
			ACCESS read-only
			STATUS mandatory
			DESCRIPTION
				"May be the ElcpPortNumber for AAL2 or the position of 
				the used timeslots within the AAL1 If, according to 
				the AalType;
				
				for the AAL1 interface: 
				   on SU_POTS (1..8)
				   on SU_IVD_POTS 
				for the AAL2 interface: 
				   on SU_POTS (16..223)
				   on SU_IVD_POTS 
				"
			::= { msapPstnUsEntry 3 }
		
-- info-ROU: GET us
		msapPstnUsOperStateCause OBJECT-TYPE
			SYNTAX MsapUsOperStateCauseType
			ACCESS read-only
			STATUS mandatory
			DESCRIPTION
				"1. Desribed the cause for an (disabled) operational state 
				of one PSTN-US. The status information is carried 
				in an array of 85 Bytes 
				
				2. (Meaning of the each bit:
				   0:    the operational state of the US on the SU 
				           (0 = disabled, 1 = enabled)
				   1-6:  not used
				   7:    the existence of the US on the
				         SU (0 = not exists, 1 = exists)
				)
				
				
				3. In case of unreachable SU
				CLU will get following value:
				
				        0x80 
					0x00
					'not available' (20 bytes)
					0x00
					'not available' (20 bytes)
					0x00
					'not available' (20 bytes)
					0x00
					'not available' (20 bytes)
				"
			::= { msapPstnUsEntry 4 }
		
-- *************************************************************************
-- *************************************************************************
-- MSAP ISDN US Table
-- *************************************************************************
-- *************************************************************************
-- 
		msapIsdnBaUsTable OBJECT-TYPE
			SYNTAX SEQUENCE OF MsapIsdnBaUsEntry
			ACCESS not-accessible
			STATUS mandatory
--DEFAULT next-function-async     fsnIsdnBaUsEntryNext
--DEFAULT get-function-async      fsnIsdnBaUsEntryGet
			::= { msapUserPortObjects 3 }
		
		msapIsdnBaUsEntry OBJECT-TYPE
			SYNTAX MsapIsdnBaUsEntry
			ACCESS not-accessible
			STATUS mandatory
			INDEX { msapUsIndex }
			::= { msapIsdnBaUsTable 1 }
		
		MsapIsdnBaUsEntry ::=
			SEQUENCE { 
				msapIsdnBaUsAalxIfIndex
					MsapUsAalxIfIndexType,
				msapIsdnBaUsAalType
					MsapUsAalTypeType,
				msapIsdnBaUsPortNumber
					MsapUsPortNumberType,
				msapIsdnBaUsOperStateCause
					MsapUsOperStateCauseType
			 }

-- info-ROU: GET db
		msapIsdnBaUsAalxIfIndex OBJECT-TYPE
			SYNTAX MsapUsAalxIfIndexType
			ACCESS read-only
			STATUS mandatory
			DESCRIPTION
				"A value to identify an entry in the AAL1/2 Interface 
				table."
			::= { msapIsdnBaUsEntry 1 }
		
-- info-ROU: GET db
		msapIsdnBaUsAalType OBJECT-TYPE
			SYNTAX MsapUsAalTypeType
			ACCESS read-only
			STATUS mandatory
			DESCRIPTION
				"Type of the AALxIf for the UsType ISDN_BA and PSTN
				0x01:	AAL1 (not for SU_IVD_POTS)
				0x02:	AAL2
				"
			::= { msapIsdnBaUsEntry 2 }
		
-- info-ROU: GET db
		msapIsdnBaUsPortNumber OBJECT-TYPE
			SYNTAX MsapUsPortNumberType
			ACCESS read-only
			STATUS mandatory
			DESCRIPTION
				"May be the ElcpPortNumber for AAL2 or the position of 
				the used timeslots within the AAL1 If, according to 
				the AalType;
				
				for the AAL1 interface: 
				on SU_ISDN (1..4) for BA
				for the AAL2 interface: 
				on SU_ISDN (16..223) 
				"
			::= { msapIsdnBaUsEntry 3 }
		
-- info-ROU: GET us
		msapIsdnBaUsOperStateCause OBJECT-TYPE
			SYNTAX MsapUsOperStateCauseType
			ACCESS read-only
			STATUS mandatory
			DESCRIPTION
				"Desribed the cause for an (disabled) operational state 
				of one ISDN-BA-US. The status information is carried 
				in an array of 85 Bytes."
			::= { msapIsdnBaUsEntry 4 }
		
-- *************************************************************************
-- *************************************************************************
-- MSAP ISDN US Table
-- *************************************************************************
-- *************************************************************************
-- 
		msapIsdnLlUsTable OBJECT-TYPE
			SYNTAX SEQUENCE OF MsapIsdnLlUsEntry
			ACCESS not-accessible
			STATUS mandatory
--DEFAULT next-function-async     fsnIsdnLlUsEntryNext
--DEFAULT get-function-async      fsnIsdnLlUsEntryGet
			::= { msapUserPortObjects 4 }
		
		msapIsdnLlUsEntry OBJECT-TYPE
			SYNTAX MsapIsdnLlUsEntry
			ACCESS not-accessible
			STATUS mandatory
			INDEX { msapUsIndex }
			::= { msapIsdnLlUsTable 1 }
		
		MsapIsdnLlUsEntry ::=
			SEQUENCE { 
				msapIsdnLlUsAalxIfIndex
					MsapUsAalxIfIndexType,
				msapIsdnLlUsAalType
					MsapUsAalTypeType,
				msapIsdnLlUsPortNumber
					MsapUsPortNumberType,
				msapIsdnLlUsDChannelMode
					MsapUsIsdnLlDChannelMode
			 }

-- info-ROU: GET db
		msapIsdnLlUsAalxIfIndex OBJECT-TYPE
			SYNTAX MsapUsAalxIfIndexType
			ACCESS read-only
			STATUS mandatory
			DESCRIPTION
				"A value to identify an entry in the AAL1/2 Interface 
				table."
			::= { msapIsdnLlUsEntry 1 }
		
-- info-ROU: GET db
		msapIsdnLlUsAalType OBJECT-TYPE
			SYNTAX MsapUsAalTypeType
			ACCESS read-only
			STATUS mandatory
			DESCRIPTION
				"Type of the AALxIf for the UsType ISDN_BA and PSTN
				0x01:	AAL1 (not for SU_IVD_POTS)
				0x02:	AAL2
				"
			::= { msapIsdnLlUsEntry 2 }
		
-- info-ROU: GET db
		msapIsdnLlUsPortNumber OBJECT-TYPE
			SYNTAX MsapUsPortNumberType
			ACCESS read-only
			STATUS mandatory
			DESCRIPTION
				"May be the ElcpPortNumber for AAL2 or the position 
				of the used timeslots within the AAL1 If, according 
				to the AalType;
				for the AAL1 interface: 
				on SU_ISDN (1..3) for leased lines 
				for the AAL2 interface: 
				on SU_ISDN (16..223)
				"
			::= { msapIsdnLlUsEntry 3 }
		
-- info-ROU: GET db
		msapIsdnLlUsDChannelMode OBJECT-TYPE
			SYNTAX MsapUsIsdnLlDChannelMode
			ACCESS read-only
			STATUS mandatory
			DESCRIPTION
				"Only non multiplexed is supported
				
				0x01:	multiplexed
				0x02:	non multiplexed
				"
			::= { msapIsdnLlUsEntry 4 }
		
-- *************************************************************************
-- *************************************************************************
-- MSAP CES US Table
-- *************************************************************************
-- *************************************************************************
-- 
		msapCesUsTable OBJECT-TYPE
			SYNTAX SEQUENCE OF MsapCesUsEntry
			ACCESS not-accessible
			STATUS mandatory
--DEFAULT next-function-async     fsnCesUsEntryNext
--DEFAULT get-function-async      fsnCesUsEntryGet
			::= { msapUserPortObjects 5 }
		
		msapCesUsEntry OBJECT-TYPE
			SYNTAX MsapCesUsEntry
			ACCESS not-accessible
			STATUS mandatory
			INDEX { msapUsIndex }
			::= { msapCesUsTable 1 }
		
		MsapCesUsEntry ::=
			SEQUENCE { 
				msapCesUsAal1IfIndex
					MsapUsAalxIfIndexType,
				msapCesUsServiceType
					MsapUsCesServiceType,
				msapCesUsTimeSlotMap
					MsapUsTimeSlotMapType
			 }

-- info-ROU: GET db
		msapCesUsAal1IfIndex OBJECT-TYPE
			SYNTAX MsapUsAalxIfIndexType
			ACCESS read-only
			STATUS mandatory
			DESCRIPTION
				"A value to identify an entry in the AAL1 Interface 
				table."
			::= { msapCesUsEntry 1 }
		
-- info-ROU: GET db
		msapCesUsServiceType OBJECT-TYPE
			SYNTAX MsapUsCesServiceType
			ACCESS read-only
			STATUS mandatory
			DESCRIPTION
				"Defines if E1 service is framed or unframed. 
				A framed(2) interface is some nx64Kbps. 
				An unframed(1) interface is 2.048Mbps. 
				Unframed(1) passes all bits through the ATM network. 
				Framed(2) passes data bits through the ATM network, 
				and may also pass signalling bits.
				"
			::= { msapCesUsEntry 2 }
		
-- info-ROU: GET db
		msapCesUsTimeSlotMap OBJECT-TYPE
			SYNTAX MsapUsTimeSlotMapType
			ACCESS read-only
			STATUS mandatory
			DESCRIPTION
				"In framed modes, this value selects the timeslots of 
				the E1 interface that are mapped to ATM. Each bit 
				in this value corresponds to a timeslot
				
				bit0  (LSB) - reserved by E1 frame
				bit1        - timeslot 1
				bit2        - timeslot 2
				etc.
				bit31 (MSB) - timeslot 31
				
				"
			::= { msapCesUsEntry 3 }
		
-- *************************************************************************
-- *************************************************************************
-- MSAP US Control Group
-- *************************************************************************
-- *************************************************************************
-- 
		msapUsControlGroup OBJECT IDENTIFIER ::= { msapUserPortObjects 6 }
		
-- 
-- info-ROU: GET db   SET us
-- 
		msapUsCtrlControlReq OBJECT-TYPE
			SYNTAX MsapUsCtrlControlReqType
			ACCESS read-write
			STATUS mandatory
			DESCRIPTION
				" To activate a configured set of data 
				(command: activateData).  "
--DEFAULT test-function-async     fsnUsCgTest
--DEFAULT next-function-async     fsnUsCgNext
--DEFAULT set-function-async      fsnUsCgSet
--DEFAULT get-function-async      fsnUsCgGet
			::= { msapUsControlGroup 2 }
		
-- 
-- info-ROU: GET db
		msapUsCtrlControlStatus OBJECT-TYPE
			SYNTAX Xldv20ControlStatus
			ACCESS read-only
			STATUS mandatory
			DESCRIPTION
				" Indicates the status of a control request. "
--DEFAULT next-function-async     fsnUsCgNext
--DEFAULT get-function-async      fsnUsCgGet
			::= { msapUsControlGroup 3 }
		
-- 
-- info-ROU: GET db
		msapUsCtrlControlReqResult OBJECT-TYPE
			SYNTAX MsapUsCtrlControlReqType
			ACCESS read-only
			STATUS mandatory
			DESCRIPTION
				" The result of the last user command. "
--DEFAULT next-function-async     fsnUsCgNext
--DEFAULT get-function-async      fsnUsCgGet
			::= { msapUsControlGroup 4 }
		
-- 
-- info-ROU: GET db
		msapUsCtrlControlTimer OBJECT-TYPE
			SYNTAX MsapUsCtrlControlTimerType
			ACCESS read-only
			STATUS mandatory
			DESCRIPTION
				" The time stamp of the last command (end of command). "
--DEFAULT next-function-async     fsnUsCgNext
--DEFAULT get-function-async      fsnUsCgGet
			::= { msapUsControlGroup 5 }
		
-- 
-- info-ROU: GET db  SET db
		msapUsCtrlIndex OBJECT-TYPE
			SYNTAX MsapUsIndexType
			ACCESS read-write
			STATUS mandatory
			DESCRIPTION
				"A unique value to identify an entry in the msapUsTable."
--DEFAULT test-function-async     fsnUsCgTest
--DEFAULT next-function-async     fsnUsCgNext
--DEFAULT set-function-async      fsnUsCgSet
--DEFAULT get-function-async      fsnUsCgGet
			::= { msapUsControlGroup 6 }
		
-- 
-- 
-- info-ROU: GET db  SET db
		msapUsCtrlAdminState OBJECT-TYPE
			SYNTAX MsapUsAdminStateType
			ACCESS read-write
			STATUS mandatory
--DEFAULT test-function-async     fsnUsCgTest
--DEFAULT next-function-async     fsnUsCgNext
--DEFAULT set-function-async      fsnUsCgSet
--DEFAULT get-function-async      fsnUsCgGet
			::= { msapUsControlGroup 7 }
		
-- 
-- 
-- info-ROU: GET db  SET db
		msapUsCtrlType OBJECT-TYPE
			SYNTAX MsapUsTypeType
			ACCESS read-write
			STATUS mandatory
			DESCRIPTION
				"A unique value to identify the type of the user port 
				(pots, ces, isdn-ba, isdn-ll). "
--DEFAULT test-function-async     fsnUsCgTest
--DEFAULT next-function-async     fsnUsCgNext
--DEFAULT set-function-async      fsnUsCgSet
--DEFAULT get-function-async      fsnUsCgGet
			::= { msapUsControlGroup 8 }
		
-- 
-- 
-- info-ROU: GET db  SET db
		msapUsCtrlPptpIfIndex OBJECT-TYPE
			SYNTAX MsapUsPptpIfIndexType
			ACCESS read-write
			STATUS mandatory
			DESCRIPTION
				"A unique value to identify an entry in one PPTP table 
				(msapPotsPptpTable, msapIsdnPptpTable or 
				xldV20E1nPPTPTable). "
--DEFAULT test-function-async     fsnUsCgTest
--DEFAULT next-function-async     fsnUsCgNext
--DEFAULT set-function-async      fsnUsCgSet
--DEFAULT get-function-async      fsnUsCgGet
			::= { msapUsControlGroup 9 }
		
-- 
-- 
-- info-ROU: GET db  SET db
		msapUsCtrlAalxIfIndex OBJECT-TYPE
			SYNTAX MsapUsAalxIfIndexType
			ACCESS read-write
			STATUS mandatory
			DESCRIPTION
				"A value to identify an entry in the AAL1/2 Interface 
				table."
--DEFAULT test-function-async     fsnUsCgTest
--DEFAULT next-function-async     fsnUsCgNext
--DEFAULT set-function-async      fsnUsCgSet
--DEFAULT get-function-async      fsnUsCgGet
			::= { msapUsControlGroup 10 }
		
-- 
-- 
-- info-ROU: GET db  SET db
		msapCesUsCtrlTimeSlotMap OBJECT-TYPE
			SYNTAX MsapUsTimeSlotMapType
			ACCESS read-write
			STATUS mandatory
			DESCRIPTION
				"In framed modes, this value selects the timeslots of 
				the E1 interface that are mapped to ATM. 
				Each bit in this value corresponds to a timeslot
				bit0  (LSB) - reserved by E1 frame
				bit1        - timeslot 1
				bit2        - timeslot 2
				etc.
				bit31 (MSB) - timeslot 31
				
				"
--DEFAULT test-function-async     fsnUsCgTest
--DEFAULT next-function-async     fsnUsCgNext
--DEFAULT set-function-async      fsnUsCgSet
--DEFAULT get-function-async      fsnUsCgGet
			::= { msapUsControlGroup 11 }
		
-- 
-- 
-- info-ROU: GET db  SET db
		msapCesUsCtrlServiceType OBJECT-TYPE
			SYNTAX MsapUsCesServiceType
			ACCESS read-write
			STATUS mandatory
			DESCRIPTION
				"Defines if E1 service is framed or unframed. 
				A framed(2) interface is some nx64Kbps. 
				An unframed(1) interface is 2.048Mbps. 
				Unframed(1) passes all bits through the ATM network. 
				Framed(2) passes data bits through the ATM network, 
				and may also pass signalling bits.
				"
--DEFAULT test-function-async     fsnUsCgTest
--DEFAULT next-function-async     fsnUsCgNext
--DEFAULT set-function-async      fsnUsCgSet
--DEFAULT get-function-async      fsnUsCgGet
			::= { msapUsControlGroup 12 }
		
-- 
-- 
-- info-ROU: GET db  SET db
		msapIsdnLlUsCtrlDChannelMode OBJECT-TYPE
			SYNTAX MsapUsIsdnLlDChannelMode
			ACCESS read-write
			STATUS mandatory
			DESCRIPTION
				"Only non multiplexed is supported
				
				0x01:	multiplexed
				0x02:	non multiplexed
				"
--DEFAULT test-function-async     fsnUsCgTest
--DEFAULT next-function-async     fsnUsCgNext
--DEFAULT set-function-async      fsnUsCgSet
--DEFAULT get-function-async      fsnUsCgGet
			::= { msapUsControlGroup 13 }
		
-- 
-- 
-- info-ROU: GET db  SET db
		msapIsdnPstnUsCtrlPortNumber OBJECT-TYPE
			SYNTAX MsapUsPortNumberType
			ACCESS read-write
			STATUS mandatory
			DESCRIPTION
				"May be the ElcpPortNumber for AAL2 or the position 
				of the used timeslots within the AAL1 If, 
				according to the AalType;
				
				for the AAL1 interface: 
				   on SU_POTS (1..8)
				   on SU_IVD_POTS 
				for the AAL2 interface: 
				   on SU_POTS (16..223)
				   on SU_IVD_POTS 
				"
--DEFAULT test-function-async     fsnUsCgTest
--DEFAULT next-function-async     fsnUsCgNext
--DEFAULT set-function-async      fsnUsCgSet
--DEFAULT get-function-async      fsnUsCgGet
			::= { msapUsControlGroup 14 }
		
-- 
-- 
-- info-ROU: GET db  SET db
		msapIsdnPstnUsCtrlAalType OBJECT-TYPE
			SYNTAX MsapUsAalTypeType
			ACCESS read-write
			STATUS mandatory
			DESCRIPTION
				"Type of the AALxIf for the UsType ISDN_BA and PSTN
				0x01:	AAL1 
				0x02:	AAL2
				"
--DEFAULT test-function-async     fsnUsCgTest
--DEFAULT next-function-async     fsnUsCgNext
--DEFAULT set-function-async      fsnUsCgSet
--DEFAULT get-function-async      fsnUsCgGet
			::= { msapUsControlGroup 15 }
		
-- *************************************************************************
-- *************************************************************************
-- MSAP US Traps
-- *************************************************************************
-- *************************************************************************
-- 
		msapUsTraps OBJECT IDENTIFIER ::= { msapUserPortObjects 7 }
		
		msapUsTrapVars OBJECT IDENTIFIER ::= { msapUsTraps 1 }
		
		msapUsTvTimeAndDate OBJECT-TYPE
			SYNTAX INTEGER
			ACCESS not-accessible
			STATUS mandatory
			DESCRIPTION
				" The time stamp of the last command (end of command). "
			::= { msapUsTrapVars 1 }
		
		msapUsTvIndex OBJECT-TYPE
			SYNTAX MsapUsIndexType
			ACCESS not-accessible
			STATUS mandatory
			DESCRIPTION
				"A unique value to identify an entry in the msapUsTable."
			::= { msapUsTrapVars 2 }
		
		msapUsTvOperState OBJECT-TYPE
			SYNTAX Xldv20OperState
			ACCESS not-accessible
			STATUS mandatory
			DESCRIPTION
				"This attribute shows the operative 
				state of the corss connect (locked or unlocked)"
			::= { msapUsTrapVars 3 }
		
		msapUsTvAdminState OBJECT-TYPE
			SYNTAX MsapUsAdminStateType
			ACCESS not-accessible
			STATUS mandatory
			DESCRIPTION
				"This attribute shows the administrative 
				state of the corss connect (locked or unlocked)"
			::= { msapUsTrapVars 4 }
		
		msapUsTvType OBJECT-TYPE
			SYNTAX MsapUsTypeType
			ACCESS not-accessible
			STATUS mandatory
			DESCRIPTION
				"A unique value to identify the type of the user port 
				(pots, ces, isdn-ba, isdn-ll). "
			::= { msapUsTrapVars 5 }
		
		msapUsTvPptpIfIndex OBJECT-TYPE
			SYNTAX MsapUsPptpIfIndexType
			ACCESS not-accessible
			STATUS mandatory
			DESCRIPTION
				"A unique value to identify an entry in one PPTP table 
				(msapPotsPptpTable, msapIsdnPptpTable or 
				xldV20E1nPPTPTable). "
			::= { msapUsTrapVars 6 }
		
		msapUsTvAalxIfIndex OBJECT-TYPE
			SYNTAX MsapUsAalxIfIndexType
			ACCESS not-accessible
			STATUS mandatory
			DESCRIPTION
				"A value to identify an entry in the AAL1/2 Interface 
				table."
			::= { msapUsTrapVars 7 }
		
		msapCesUsTvTimeSlotMap OBJECT-TYPE
			SYNTAX MsapUsTimeSlotMapType
			ACCESS not-accessible
			STATUS mandatory
			DESCRIPTION
				"In framed modes, this value selects the timeslots of 
				the E1 interface that are mapped to ATM. 
				Each bit in this value corresponds to a timeslot
				bit0  (LSB) - reserved by E1 frame
				bit1        - timeslot 1
				bit2        - timeslot 2
				etc.
				bit31 (MSB) - timeslot 31"
			::= { msapUsTrapVars 8 }
		
		msapCesUsTvServiceType OBJECT-TYPE
			SYNTAX MsapUsCesServiceType
			ACCESS not-accessible
			STATUS mandatory
			DESCRIPTION
				"Defines if E1 service is framed or unframed. 
				A framed(2) interface is some nx64Kbps. 
				An unframed(1) interface is 2.048Mbps. 
				Unframed(1) passes all bits through the ATM network. 
				Framed(2) passes data bits through the ATM network, 
				and may also pass signalling bits.
				"
			::= { msapUsTrapVars 9 }
		
		msapIsdnLlUsTvDChannelMode OBJECT-TYPE
			SYNTAX MsapUsIsdnLlDChannelMode
			ACCESS not-accessible
			STATUS mandatory
			DESCRIPTION
				"Only non multiplexed is supported
				
				0x01:	multiplexed
				0x02:	non multiplexed
				"
			::= { msapUsTrapVars 10 }
		
		msapIsdnPstnUsTvPortNumber OBJECT-TYPE
			SYNTAX MsapUsPortNumberType
			ACCESS not-accessible
			STATUS mandatory
			DESCRIPTION
				"May be the ElcpPortNumber for AAL2 or the position of 
				the used timeslots within the AAL1 If, 
				according to the AalType;
				
				for the AAL1 interface: 
				   on SU_POTS (1..8)
				   on SU_IVD_POTS 
				for the AAL2 interface: 
				   on SU_POTS (16..223)
				   on SU_IVD_POTS 
				"
			::= { msapUsTrapVars 11 }
		
		msapIsdnPstnUsTvAalType OBJECT-TYPE
			SYNTAX MsapUsAalTypeType
			ACCESS not-accessible
			STATUS mandatory
			DESCRIPTION
				"Type of the AALxIf for the UsType ISDN_BA and PSTN
				0x01:	AAL1 
				0x02:	AAL2
				"
			::= { msapUsTrapVars 12 }
		
-- *************************************************************************
-- *************************************************************************
-- *************************************************************************
-- *************************************************************************
-- MSAP LTM Group
-- *************************************************************************
-- *************************************************************************
-- *************************************************************************
-- *************************************************************************
		msapLineTestManagementGroup OBJECT IDENTIFIER ::= { msap 4 }
		
		msapLtmGlobalsTable OBJECT-TYPE
			SYNTAX SEQUENCE OF MsapLtmGlobalsEntry
			ACCESS not-accessible
			STATUS mandatory
--DEFAULT next-function-async     fsnLtmGlobalsEntryNext
--DEFAULT get-function-async      fsnLtmGlobalsEntryGet
			::= { msapLineTestManagementGroup 1 }
		
		msapLtmGlobalsEntry OBJECT-TYPE
			SYNTAX MsapLtmGlobalsEntry
			ACCESS not-accessible
			STATUS mandatory
			INDEX { xldv20IfIndex }
			::= { msapLtmGlobalsTable 1 }
		
		MsapLtmGlobalsEntry ::=
			SEQUENCE { 
				msapLtmSltAutoGlobalThresNumber
					MsapLtmGlobalThresholdType,
				msapLtmSltAutoGlobalNoFeasMeasNumber
					MsapLtmGlobalThresholdType,
				msapLtmSltAutoGlobalPatNumber
					MsapLtmGlobalThresholdType,
				msapLtmSuAckTime
					MsapLtmGlobalTimerType,
				msapLtmAutoMeasDelayTime
					MsapLtmGlobalTimerType
			 }

-- info-ROU: GET pch
		msapLtmSltAutoGlobalThresNumber OBJECT-TYPE
			SYNTAX MsapLtmGlobalThresholdType
			ACCESS read-only
			STATUS mandatory
			DESCRIPTION
				"number of errorous ports per shelf which cause generation of summary alarm "
			::= { msapLtmGlobalsEntry 1 }
		
-- info-ROU: GET pch
		msapLtmSltAutoGlobalNoFeasMeasNumber OBJECT-TYPE
			SYNTAX MsapLtmGlobalThresholdType
			ACCESS read-only
			STATUS mandatory
			DESCRIPTION
				"number of errorous ports per shelf which cause generation of summary alarm "
			::= { msapLtmGlobalsEntry 2 }
		
-- info-ROU: GET pch
		msapLtmSltAutoGlobalPatNumber OBJECT-TYPE
			SYNTAX MsapLtmGlobalThresholdType
			ACCESS read-only
			STATUS mandatory
			DESCRIPTION
				"number of errorous ports per shelf which cause generation of summary alarm "
			::= { msapLtmGlobalsEntry 3 }
		
-- info-ROU: GET pch
		msapLtmSuAckTime OBJECT-TYPE
			SYNTAX MsapLtmGlobalTimerType
			ACCESS read-only
			STATUS mandatory
			DESCRIPTION
				"allowed time for SU to respond to a request from CLU"
			::= { msapLtmGlobalsEntry 4 }
		
-- info-ROU: GET pch
		msapLtmAutoMeasDelayTime OBJECT-TYPE
			SYNTAX MsapLtmGlobalTimerType
			ACCESS read-only
			STATUS mandatory
			DESCRIPTION
				"Time period for which an Auto measurement is delayed, when it cannot be performed at scheduled time.
				This may occur when measurements for several ports on a SU are scheduled at nearly same time. However, only one port per SU can be measured at one time."
			::= { msapLtmGlobalsEntry 5 }
		
		msapLtmControlGroup OBJECT IDENTIFIER ::= { msapLineTestManagementGroup 2 }
		
-- 
-- info-ROU: GET db   SET db
		msapLtmCtrlIfIndex OBJECT-TYPE
			SYNTAX INTEGER
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 1 }
		
-- 
-- info-ROU: GET db   SET ltm
		msapLtmCtrlRequest OBJECT-TYPE
			SYNTAX MsapLtmControlRequestType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 2 }
		
-- 
-- info-ROU: GET db
		msapLtmCtrlTimeStamp OBJECT-TYPE
			SYNTAX TimeTicks
			ACCESS read-only
			STATUS mandatory
--DEFAULT next-function-async     fsnLtmCoNext
--DEFAULT get-function-async      fsnLtmCoGet
			::= { msapLtmControlGroup 3 }
		
-- 
-- info-ROU: GET db
		msapLtmCtrlStatus OBJECT-TYPE
			SYNTAX Xldv20ControlStatus
			ACCESS read-only
			STATUS mandatory
--DEFAULT next-function-async     fsnLtmCoNext
--DEFAULT get-function-async      fsnLtmCoGet
			::= { msapLtmControlGroup 4 }
		
-- 
-- info-ROU: GET db
		msapLtmCtrlReqResult OBJECT-TYPE
			SYNTAX MsapLtmControlRequestType
			ACCESS read-only
			STATUS mandatory
--DEFAULT next-function-async     fsnLtmCoNext
--DEFAULT get-function-async      fsnLtmCoGet
			::= { msapLtmControlGroup 5 }
		
-- 
-- info-ROU: GET db   SET db
		msapLtmSltCtrlAccessLineAccess OBJECT-TYPE
			SYNTAX MsapLtmSltLineAccessType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 6 }
		
-- 
-- info-ROU: GET db   SET db
		msapLtmSltCtrlDmndViaSplitter OBJECT-TYPE
			SYNTAX MsapLtmSltViaSplitterType
			ACCESS read-write
			STATUS mandatory
			DEFVAL { yes }
--DEFAULT test-function-async     fsnLtmCoTest
--DEFAULT next-function-async     fsnLtmCoNext
--DEFAULT set-function-async      fsnLtmCoSet
--DEFAULT get-function-async      fsnLtmCoGet
			::= { msapLtmControlGroup 7 }
		
-- 
-- info-ROU: GET db   SET db
		msapLtmSltCtrlDmndMeasRequest OBJECT-TYPE
			SYNTAX MsapLtmSltMeasRequestType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 8 }
		
-- 
-- info-ROU: GET db   SET db
		msapLtmSltCtrlDmndMeasResIndex OBJECT-TYPE
			SYNTAX INTEGER
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 9 }
		
-- 
-- info-ROU: GET db   SET db
		msapLtmSltCtrlAutoMeasViaSplitter OBJECT-TYPE
			SYNTAX MsapLtmSltViaSplitterType
			ACCESS read-write
			STATUS mandatory
			DEFVAL { yes }
--DEFAULT test-function-async     fsnLtmCoTest
--DEFAULT next-function-async     fsnLtmCoNext
--DEFAULT set-function-async      fsnLtmCoSet
--DEFAULT get-function-async      fsnLtmCoGet
			::= { msapLtmControlGroup 10 }
		
-- 
-- info-ROU: GET db   SET db
		msapLtmSltCtrlAutoGlobalThresNumber OBJECT-TYPE
			SYNTAX MsapLtmGlobalThresholdType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 11 }
		
-- 
-- info-ROU: GET db   SET db
		msapLtmSltCtrlAutoGlobalNoFeasNumber OBJECT-TYPE
			SYNTAX MsapLtmGlobalThresholdType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 12 }
		
-- 
-- info-ROU: GET db   SET db
		msapLtmSltCtrlAutoGlobalPatNumber OBJECT-TYPE
			SYNTAX MsapLtmGlobalThresholdType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 13 }
		
-- 
-- info-ROU: GET db   SET db
		msapLtmSltCtrlAutoMeasThresIndex OBJECT-TYPE
			SYNTAX INTEGER
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 14 }
		
-- 
-- info-ROU: GET db   SET db
		msapLtmSltCtrlAutoMeasTimeHour OBJECT-TYPE
			SYNTAX OCTET STRING (SIZE (3))
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 15 }
		
-- 
-- info-ROU: GET db   SET db
		msapLtmSltCtrlAutoMeasTimeWeekday OBJECT-TYPE
			SYNTAX OCTET STRING (SIZE (1))
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 16 }
		
-- 
-- info-ROU: GET db   SET db
		msapLtmSltCtrlAutoMeasTimePeriod OBJECT-TYPE
			SYNTAX INTEGER
				{
				noMeasurement(1),
				oncePerMonth(2),
				oncePerFortnight(3),
				oncePerWeek(4)
				}
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 17 }
		
-- 
-- info-ROU: GET db   SET db
		msapLtmSltCtrlAutoMeasKind OBJECT-TYPE
			SYNTAX INTEGER
				{
				outward(1),
				inward(2)
				}
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 18 }
		
-- 
-- info-ROU: GET db   SET db
		msapLtmSltCtrlAutoRecordIndex OBJECT-TYPE
			SYNTAX INTEGER
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 19 }
		
-- 
-- info-ROU: GET db   SET db
		msapLtmSltCtrlAutoMeasCheckPpa OBJECT-TYPE
			SYNTAX MsapLtmSltCheckType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 20 }
		
-- 
-- info-ROU: GET db   SET db
		msapLtmSltCtrlAutoMeasCheckRingerLoad OBJECT-TYPE
			SYNTAX MsapLtmSltCheckType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 21 }
		
-- 
-- info-ROU: GET db   SET db
		msapLtmSltCtrlMeasThresValIndex OBJECT-TYPE
			SYNTAX INTEGER
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 23 }
		
-- 
-- info-ROU: GET db   SET db
		msapLtmMaintCtrlCpePotsNumberOfImpulses OBJECT-TYPE
			SYNTAX MsapLtmMaintCpePotsNumberType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 24 }
		
-- 
-- info-ROU: GET db   SET db
		msapLtmMaintCtrlCpePotsNumberOfPeriods OBJECT-TYPE
			SYNTAX MsapLtmMaintCpePotsNumberType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 25 }
		
-- 
-- info-ROU: GET db   SET db
		msapLtmMaintCtrlCpePotsRingingType OBJECT-TYPE
			SYNTAX MsapLtmMaintCpePotsRingingTypeType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 26 }
		
-- 
-- info-ROU: GET db   SET db
		msapLtmMaintCtrlCpeIsdnLineAccess OBJECT-TYPE
			SYNTAX MsapLtmMaintCpeIsdnLineAccessType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 27 }
		
-- 
-- info-ROU: GET db   SET db
		msapLtmMaintCtrlIsdnLoopNtMode OBJECT-TYPE
			SYNTAX MsapLtmMaintIsdnLoopNtModeType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 28 }
		
-- 
-- info-ROU: GET db   SET db
-- 
-- info-ROU: GET db   SET db
		msapLtmMaintCtrlIsdnBerTimer OBJECT-TYPE
			SYNTAX Unsigned16
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 29 }
		
		msapLtmMaintCtrlIsdnBerStart OBJECT-TYPE
			SYNTAX MsapLtmMaintIsdnBerStartType
			ACCESS read-write
			STATUS mandatory
--DEFAULT test-function-async     fsnLtmCoTest
--DEFAULT next-function-async     fsnLtmCoNext
--DEFAULT set-function-async      fsnLtmCoSet
--DEFAULT get-function-async      fsnLtmCoGet
			::= { msapLtmControlGroup 30 }
		
		msapLtmSubscriberLineTest OBJECT IDENTIFIER ::= { msapLineTestManagementGroup 3 }
		
		msapLtmSltTraps OBJECT IDENTIFIER ::= { msapLtmSubscriberLineTest 1 }
		
		msapLtmTvTimeAndDate OBJECT-TYPE
			SYNTAX INTEGER
			ACCESS not-accessible
			STATUS mandatory
			::= { msapLtmSltTraps 1 }
		
		msapLtmTvIfIndex OBJECT-TYPE
			SYNTAX INTEGER
			ACCESS not-accessible
			STATUS mandatory
			::= { msapLtmSltTraps 2 }
		
		msapLtmSltTvAutoMeasKind OBJECT-TYPE
			SYNTAX INTEGER
				{
				outward(1),
				inward(2)
				}
			ACCESS not-accessible
			STATUS mandatory
			::= { msapLtmSltTraps 3 }
		
		msapLtmSltTvAutoMeasTimePeriod OBJECT-TYPE
			SYNTAX INTEGER
				{
				noMeasurement(1),
				oncePerMonth(2),
				oncePerForthight(3),
				oncePerWeek(4)
				}
			ACCESS not-accessible
			STATUS mandatory
			::= { msapLtmSltTraps 4 }
		
		msapLtmSltTvAutoMeasTimeWeekday OBJECT-TYPE
			SYNTAX OCTET STRING (SIZE (1))
			ACCESS not-accessible
			STATUS mandatory
			::= { msapLtmSltTraps 5 }
		
		msapLtmSltTvAutoMeasTimeHour OBJECT-TYPE
			SYNTAX OCTET STRING (SIZE (3))
			ACCESS not-accessible
			STATUS mandatory
			::= { msapLtmSltTraps 6 }
		
		msapLtmSltTvAutoMeasThresIndex OBJECT-TYPE
			SYNTAX INTEGER
			ACCESS not-accessible
			STATUS mandatory
			::= { msapLtmSltTraps 7 }
		
		msapLtmSltTvAutoMeasViaSplitter OBJECT-TYPE
			SYNTAX MsapLtmSltViaSplitterType
			ACCESS not-accessible
			STATUS mandatory
			::= { msapLtmSltTraps 8 }
		
		msapLtmSltTvAutoMeasCheckPpa OBJECT-TYPE
			SYNTAX MsapLtmSltCheckType
			ACCESS not-accessible
			STATUS mandatory
			::= { msapLtmSltTraps 9 }
		
		msapLtmSltTvAutoMeasCheckRingerLoad OBJECT-TYPE
			SYNTAX MsapLtmSltCheckType
			ACCESS not-accessible
			STATUS mandatory
			::= { msapLtmSltTraps 10 }
		
		msapLtmSltTvDmndMeasRequest OBJECT-TYPE
			SYNTAX MsapLtmSltMeasRequestType
			ACCESS not-accessible
			STATUS mandatory
			::= { msapLtmSltTraps 11 }
		
		msapLtmSltTvDmndMeasViaSplitter OBJECT-TYPE
			SYNTAX MsapLtmSltViaSplitterType
			ACCESS read-only
			STATUS mandatory
			::= { msapLtmSltTraps 12 }
		
		msapLtmSltTvDmndLineType OBJECT-TYPE
			SYNTAX MsapLtmSltLineTypeType
			ACCESS not-accessible
			STATUS mandatory
			::= { msapLtmSltTraps 13 }
		
		msapLtmSltTvDmndLineState OBJECT-TYPE
			SYNTAX MsapLtmSltLineStateType
			ACCESS not-accessible
			STATUS mandatory
			::= { msapLtmSltTraps 14 }
		
		msapLtmSltTvDmndMeasResIndex OBJECT-TYPE
			SYNTAX INTEGER
			ACCESS not-accessible
			STATUS mandatory
			::= { msapLtmSltTraps 15 }
		
		msapLtmSltTvAccessLineAccess OBJECT-TYPE
			SYNTAX MsapLtmSltLineAccessType
			ACCESS not-accessible
			STATUS mandatory
			::= { msapLtmSltTraps 16 }
		
		msapLtmSltTvAccessLineType OBJECT-TYPE
			SYNTAX MsapLtmSltLineTypeType
			ACCESS not-accessible
			STATUS mandatory
			::= { msapLtmSltTraps 17 }
		
		msapLtmSltTvAccessLineState OBJECT-TYPE
			SYNTAX MsapLtmSltLineStateType
			ACCESS not-accessible
			STATUS mandatory
			::= { msapLtmSltTraps 18 }
		
		msapLtmSltTvMeasResultStatus OBJECT-TYPE
			SYNTAX MsapLtmSltResultStatusType
			ACCESS not-accessible
			STATUS mandatory
			::= { msapLtmSltTraps 19 }
		
		msapLtmSltTvMeasThresValIndex OBJECT-TYPE
			SYNTAX INTEGER
			ACCESS not-accessible
			STATUS mandatory
			::= { msapLtmSltTraps 20 }
		
		msapLtmSltMeasAutoRequestOutTable OBJECT-TYPE
			SYNTAX SEQUENCE OF MsapLtmSltMeasAutoRequestOutEntry
			ACCESS not-accessible
			STATUS mandatory
			DESCRIPTION
				"contains the necessary configuration data for an automatically and periodically performed measurement on one subscriber line per board at one time"
--DEFAULT next-function-async     fsnLtmAutoReqOutEntryNext
--DEFAULT get-function-async      fsnLtmAutoReqOutEntryGet
			::= { msapLtmSubscriberLineTest 2 }
		
		msapLtmSltMeasAutoRequestOutEntry OBJECT-TYPE
			SYNTAX MsapLtmSltMeasAutoRequestOutEntry
			ACCESS not-accessible
			STATUS mandatory
			INDEX { xldv20IfIndex }
			::= { msapLtmSltMeasAutoRequestOutTable 1 }
		
		MsapLtmSltMeasAutoRequestOutEntry ::=
			SEQUENCE { 
				msapLtmSltAutoMeasKindOut
					INTEGER,
				msapLtmSltAutoMeasTimePeriodOut
					INTEGER,
				msapLtmSltAutoMeasTimeWeekdayOut
					OCTET STRING,
				msapLtmSltAutoMeasTimeHourOut
					OCTET STRING,
				msapLtmSltAutoMeasThresIndexOut
					INTEGER,
				msapLtmSltAutoMeasViaSplitterOut
					MsapLtmSltViaSplitterType,
				msapLtmSltAutoMeasCheckPpaOut
					MsapLtmSltCheckType,
				msapLtmSltAutoMeasCheckRingerLoadOut
					MsapLtmSltCheckType
			 }

-- info-ROU: GET db
		msapLtmSltAutoMeasKindOut OBJECT-TYPE
			SYNTAX INTEGER { outward(1) }
			ACCESS read-only
			STATUS mandatory
			DESCRIPTION
				"Kind of measurement"
			::= { msapLtmSltMeasAutoRequestOutEntry 1 }
		
-- info-ROU: GET db
		msapLtmSltAutoMeasTimePeriodOut OBJECT-TYPE
			SYNTAX INTEGER
				{
				noMeasurement(1),
				oncePerMonth(2),
				oncePerFortnight(3),
				oncePerWeek(4)
				}
			ACCESS read-only
			STATUS mandatory
			DESCRIPTION
				"Interval of automatic measurement"
			::= { msapLtmSltMeasAutoRequestOutEntry 2 }
		
-- info-ROU: GET db
		msapLtmSltAutoMeasTimeWeekdayOut OBJECT-TYPE
			SYNTAX OCTET STRING (SIZE (1))
			ACCESS read-only
			STATUS mandatory
			DESCRIPTION
				"Weekday for interval of automatic measurement"
			::= { msapLtmSltMeasAutoRequestOutEntry 3 }
		
-- info-ROU: GET db
		msapLtmSltAutoMeasTimeHourOut OBJECT-TYPE
			SYNTAX OCTET STRING (SIZE (3))
			ACCESS read-only
			STATUS mandatory
			DESCRIPTION
				"Hour for interval of automatic Measurement"
			::= { msapLtmSltMeasAutoRequestOutEntry 4 }
		
-- info-ROU: GET db
		msapLtmSltAutoMeasThresIndexOut OBJECT-TYPE
			SYNTAX INTEGER
			ACCESS read-only
			STATUS mandatory
			DESCRIPTION
				"Index to the set of thresholds for the measurement values of the current measurement"
			::= { msapLtmSltMeasAutoRequestOutEntry 5 }
		
-- info-ROU: GET db
		msapLtmSltAutoMeasViaSplitterOut OBJECT-TYPE
			SYNTAX MsapLtmSltViaSplitterType
			ACCESS read-only
			STATUS mandatory
			DESCRIPTION
				"The subscriber line includes splitter(s"
			DEFVAL { yes }
			::= { msapLtmSltMeasAutoRequestOutEntry 8 }
		
-- info-ROU: GET db
		msapLtmSltAutoMeasCheckPpaOut OBJECT-TYPE
			SYNTAX MsapLtmSltCheckType
			ACCESS read-only
			STATUS mandatory
			::= { msapLtmSltMeasAutoRequestOutEntry 9 }
		
-- info-ROU: GET db
		msapLtmSltAutoMeasCheckRingerLoadOut OBJECT-TYPE
			SYNTAX MsapLtmSltCheckType
			ACCESS read-only
			STATUS mandatory
			::= { msapLtmSltMeasAutoRequestOutEntry 10 }
		
		msapLtmSltMeasAutoRequestInTable OBJECT-TYPE
			SYNTAX SEQUENCE OF MsapLtmSltMeasAutoRequestInEntry
			ACCESS not-accessible
			STATUS mandatory
--DEFAULT next-function-async     fsnLtmAutoReqInEntryNext
--DEFAULT get-function-async      fsnLtmAutoReqInEntryGet
			::= { msapLtmSubscriberLineTest 3 }
		
		msapLtmSltMeasAutoRequestInEntry OBJECT-TYPE
			SYNTAX MsapLtmSltMeasAutoRequestInEntry
			ACCESS not-accessible
			STATUS mandatory
			INDEX { xldv20IfIndex }
			::= { msapLtmSltMeasAutoRequestInTable 1 }
		
		MsapLtmSltMeasAutoRequestInEntry ::=
			SEQUENCE { 
				msapLtmSltAutoMeasKindIn
					INTEGER,
				msapLtmSltAutoMeasTimePeriodIn
					INTEGER,
				msapLtmSltAutoMeasTimeWeekdayIn
					INTEGER,
				msapLtmSltAutoMeasTimeHourIn
					INTEGER,
				msapLtmSltAutoMeasThresIndexIn
					INTEGER,
				msapLtmSltAutoMeasViaSplitterIn
					MsapLtmSltViaSplitterType
			 }

-- info-ROU: GET db
		msapLtmSltAutoMeasKindIn OBJECT-TYPE
			SYNTAX INTEGER { inward(2) }
			ACCESS read-only
			STATUS mandatory
			::= { msapLtmSltMeasAutoRequestInEntry 1 }
		
-- info-ROU: GET db
		msapLtmSltAutoMeasTimePeriodIn OBJECT-TYPE
			SYNTAX INTEGER
			ACCESS read-only
			STATUS mandatory
			::= { msapLtmSltMeasAutoRequestInEntry 2 }
		
-- info-ROU: GET db
		msapLtmSltAutoMeasTimeWeekdayIn OBJECT-TYPE
			SYNTAX INTEGER
			ACCESS read-only
			STATUS mandatory
			::= { msapLtmSltMeasAutoRequestInEntry 3 }
		
-- info-ROU: GET db
		msapLtmSltAutoMeasTimeHourIn OBJECT-TYPE
			SYNTAX INTEGER
			ACCESS read-only
			STATUS mandatory
			::= { msapLtmSltMeasAutoRequestInEntry 4 }
		
-- info-ROU: GET db
		msapLtmSltAutoMeasThresIndexIn OBJECT-TYPE
			SYNTAX INTEGER
			ACCESS read-only
			STATUS mandatory
			::= { msapLtmSltMeasAutoRequestInEntry 5 }
		
-- info-ROU: GET db
		msapLtmSltAutoMeasViaSplitterIn OBJECT-TYPE
			SYNTAX MsapLtmSltViaSplitterType
			ACCESS read-only
			STATUS mandatory
			DEFVAL { yes }
			::= { msapLtmSltMeasAutoRequestInEntry 6 }
		
		msapLtmSltMeasAutoResponseOutTable OBJECT-TYPE
			SYNTAX SEQUENCE OF MsapLtmSltMeasAutoResponseOutEntry
			ACCESS not-accessible
			STATUS mandatory
			DESCRIPTION
				"contains indicators to the success of the last performed automatic measurement."
--DEFAULT next-function-async     fsnLtmAutoRespOutEntryNext
--DEFAULT get-function-async      fsnLtmAutoRespOutEntryGet
			::= { msapLtmSubscriberLineTest 4 }
		
		msapLtmSltMeasAutoResponseOutEntry OBJECT-TYPE
			SYNTAX MsapLtmSltMeasAutoResponseOutEntry
			ACCESS not-accessible
			STATUS mandatory
			INDEX { xldv20IfIndex }
			::= { msapLtmSltMeasAutoResponseOutTable 1 }
		
		MsapLtmSltMeasAutoResponseOutEntry ::=
			SEQUENCE { 
				msapLtmSltAutoLineTypeOut
					MsapLtmSltLineTypeType,
				msapLtmSltAutoLineStateOut
					MsapLtmSltLineStateType,
				msapLtmSltAutoMeasResultStatusOut
					MsapLtmSltResultStatusType,
				msapLtmSltAutoMeasResIndexOut
					INTEGER,
				msapLtmSltAutoThresAlarmOut
					MsapLtmSltAutoAlarmType,
				msapLtmSltAutoThresAlarmResIndexOut
					INTEGER,
				msapLtmSltAutoNoFeasAlarmOut
					MsapLtmSltAutoAlarmType,
				msapLtmSltAutoNoFeasAlarmResIndexOut
					INTEGER,
				msapLtmSltAutoAlarmSeverityIndexOut
					INTEGER
			 }

-- info-ROU: GET db
		msapLtmSltAutoLineTypeOut OBJECT-TYPE
			SYNTAX MsapLtmSltLineTypeType
			ACCESS read-only
			STATUS mandatory
			DESCRIPTION
				"Line Type"
			::= { msapLtmSltMeasAutoResponseOutEntry 1 }
		
-- info-ROU: GET db
		msapLtmSltAutoLineStateOut OBJECT-TYPE
			SYNTAX MsapLtmSltLineStateType
			ACCESS read-only
			STATUS mandatory
			::= { msapLtmSltMeasAutoResponseOutEntry 2 }
		
-- info-ROU: GET db
		msapLtmSltAutoMeasResultStatusOut OBJECT-TYPE
			SYNTAX MsapLtmSltResultStatusType
			ACCESS read-only
			STATUS mandatory
			DESCRIPTION
				"Measurement Result Status"
			::= { msapLtmSltMeasAutoResponseOutEntry 3 }
		
-- info-ROU: GET db
		msapLtmSltAutoMeasResIndexOut OBJECT-TYPE
			SYNTAX INTEGER
			ACCESS read-only
			STATUS mandatory
			DESCRIPTION
				"A unique value to identify the results for the current measurement "
			::= { msapLtmSltMeasAutoResponseOutEntry 4 }
		
-- info-ROU: GET db
		msapLtmSltAutoThresAlarmOut OBJECT-TYPE
			SYNTAX MsapLtmSltAutoAlarmType
			ACCESS read-write
			STATUS mandatory
			DESCRIPTION
				"Threshold Violation Alarm has occurred"
			::= { msapLtmSltMeasAutoResponseOutEntry 5 }
		
-- info-ROU: GET db
		msapLtmSltAutoThresAlarmResIndexOut OBJECT-TYPE
			SYNTAX INTEGER
			ACCESS read-only
			STATUS mandatory
			DESCRIPTION
				"A unique value to identify the sltMeasAutoThresRecordInward/OutwardTable entry"
			::= { msapLtmSltMeasAutoResponseOutEntry 6 }
		
-- info-ROU: GET db
		msapLtmSltAutoNoFeasAlarmOut OBJECT-TYPE
			SYNTAX MsapLtmSltAutoAlarmType
			ACCESS read-only
			STATUS mandatory
			DESCRIPTION
				"No Feasible Measurement Alarm has occurred"
			::= { msapLtmSltMeasAutoResponseOutEntry 7 }
		
-- info-ROU: GET db
		msapLtmSltAutoNoFeasAlarmResIndexOut OBJECT-TYPE
			SYNTAX INTEGER
			ACCESS read-only
			STATUS mandatory
			DESCRIPTION
				"A unique value to identify the sltMeasAutoNoFeasibleMeasRecordInward/OutwardTable entry"
			::= { msapLtmSltMeasAutoResponseOutEntry 8 }
		
-- info-ROU: GET db
		msapLtmSltAutoAlarmSeverityIndexOut OBJECT-TYPE
			SYNTAX INTEGER
			ACCESS read-only
			STATUS mandatory
			DESCRIPTION
				"A unique value to identify the alarm severity table entry"
			::= { msapLtmSltMeasAutoResponseOutEntry 9 }
		
		msapLtmSltMeasAutoResponseInTable OBJECT-TYPE
			SYNTAX SEQUENCE OF MsapLtmSltMeasAutoResponseInEntry
			ACCESS not-accessible
			STATUS mandatory
--DEFAULT next-function-async     fsnLtmAutoRespInEntryNext
--DEFAULT get-function-async      fsnLtmAutoRespInEntryGet
			::= { msapLtmSubscriberLineTest 5 }
		
		msapLtmSltMeasAutoResponseInEntry OBJECT-TYPE
			SYNTAX MsapLtmSltMeasAutoResponseInEntry
			ACCESS not-accessible
			STATUS mandatory
			INDEX { xldv20IfIndex }
			::= { msapLtmSltMeasAutoResponseInTable 1 }
		
		MsapLtmSltMeasAutoResponseInEntry ::=
			SEQUENCE { 
				msapLtmSltAutoLineTypeIn
					MsapLtmSltLineTypeType,
				msapLtmSltAutoLineStateIn
					MsapLtmSltLineStateType,
				msapLtmSltAutoMeasResultStatusIn
					MsapLtmSltResultStatusType,
				msapLtmSltAutoMeasResIndexIn
					INTEGER,
				msapLtmSltAutoThresAlarmIn
					MsapLtmSltAutoAlarmType,
				msapLtmSltAutoThresAlarmResIndexIn
					INTEGER,
				msapLtmSltAutoNoFeasAlarmIn
					MsapLtmSltAutoAlarmType,
				msapLtmSltAutoNoFeasAlarmResIndexIn
					INTEGER,
				msapLtmSltAutoAlarmSeverityIndexIn
					INTEGER
			 }

-- info-ROU: GET db
		msapLtmSltAutoLineTypeIn OBJECT-TYPE
			SYNTAX MsapLtmSltLineTypeType
			ACCESS read-only
			STATUS mandatory
			::= { msapLtmSltMeasAutoResponseInEntry 1 }
		
-- info-ROU: GET db
		msapLtmSltAutoLineStateIn OBJECT-TYPE
			SYNTAX MsapLtmSltLineStateType
			ACCESS read-only
			STATUS mandatory
			::= { msapLtmSltMeasAutoResponseInEntry 2 }
		
-- info-ROU: GET db
		msapLtmSltAutoMeasResultStatusIn OBJECT-TYPE
			SYNTAX MsapLtmSltResultStatusType
			ACCESS read-only
			STATUS mandatory
			::= { msapLtmSltMeasAutoResponseInEntry 3 }
		
-- info-ROU: GET db
		msapLtmSltAutoMeasResIndexIn OBJECT-TYPE
			SYNTAX INTEGER
			ACCESS read-only
			STATUS mandatory
			::= { msapLtmSltMeasAutoResponseInEntry 4 }
		
-- info-ROU: GET db
		msapLtmSltAutoThresAlarmIn OBJECT-TYPE
			SYNTAX MsapLtmSltAutoAlarmType
			ACCESS read-only
			STATUS mandatory
			::= { msapLtmSltMeasAutoResponseInEntry 5 }
		
-- info-ROU: GET db
		msapLtmSltAutoThresAlarmResIndexIn OBJECT-TYPE
			SYNTAX INTEGER
			ACCESS read-only
			STATUS mandatory
			::= { msapLtmSltMeasAutoResponseInEntry 6 }
		
-- info-ROU: GET db
		msapLtmSltAutoNoFeasAlarmIn OBJECT-TYPE
			SYNTAX MsapLtmSltAutoAlarmType
			ACCESS read-only
			STATUS mandatory
			::= { msapLtmSltMeasAutoResponseInEntry 7 }
		
-- info-ROU: GET db
		msapLtmSltAutoNoFeasAlarmResIndexIn OBJECT-TYPE
			SYNTAX INTEGER
			ACCESS read-only
			STATUS mandatory
			::= { msapLtmSltMeasAutoResponseInEntry 8 }
		
-- info-ROU: GET db
		msapLtmSltAutoAlarmSeverityIndexIn OBJECT-TYPE
			SYNTAX INTEGER
			ACCESS read-only
			STATUS mandatory
			::= { msapLtmSltMeasAutoResponseInEntry 9 }
		
		msapLtmSltMeasAutoThresRecordOutTable OBJECT-TYPE
			SYNTAX SEQUENCE OF MsapLtmSltMeasAutoThresRecordOutEntry
			ACCESS not-accessible
			STATUS mandatory
			DESCRIPTION
				"contains the threshold for the summary alarm on errorous ports. The rest of the configuration for PAT is not in scope of management"
--DEFAULT next-function-async     fsnLtmAutoThresRecOutEntryNext
--DEFAULT get-function-async      fsnLtmAutoThresRecOutEntryGet
			::= { msapLtmSubscriberLineTest 6 }
		
		msapLtmSltMeasAutoThresRecordOutEntry OBJECT-TYPE
			SYNTAX MsapLtmSltMeasAutoThresRecordOutEntry
			ACCESS not-accessible
			STATUS mandatory
			INDEX { xldv20IfIndex, msapLtmSltAutoThresAlarmResIndexOut }
			::= { msapLtmSltMeasAutoThresRecordOutTable 1 }
		
		MsapLtmSltMeasAutoThresRecordOutEntry ::=
			SEQUENCE { 
				msapLtmSltMeasAutoResultTimestampOut
					TimeTicks,
				msapLtmSltAutoThresAlarmMeasValIndex1Out
					INTEGER,
				msapLtmSltAutoThresAlarmMeasValue1Out
					INTEGER,
				msapLtmSltAutoThresAlarmMeasThreshold1Out
					INTEGER,
				msapLtmSltAutoThresAlarmMeasValIndex2Out
					INTEGER,
				msapLtmSltAutoThresAlarmMeasValue2Out
					INTEGER,
				msapLtmSltAutoThresAlarmMeasThreshold2Out
					INTEGER,
				msapLtmSltAutoThresAlarmMeasValIndex3Out
					INTEGER,
				msapLtmSltAutoThresAlarmMeasValue3Out
					INTEGER,
				msapLtmSltAutoThresAlarmMeasThreshold3Out
					INTEGER,
				msapLtmSltAutoThresAlarmMeasValIndex4Out
					INTEGER,
				msapLtmSltAutoThresAlarmMeasValue4Out
					INTEGER,
				msapLtmSltAutoThresAlarmMeasThreshold4Out
					INTEGER,
				msapLtmSltAutoThresAlarmMeasValIndex5Out
					INTEGER,
				msapLtmSltAutoThresAlarmMeasValue5Out
					INTEGER,
				msapLtmSltAutoThresAlarmMeasThreshold5Out
					INTEGER,
				msapLtmSltAutoThresAlarmMeasValIndex6Out
					INTEGER,
				msapLtmSltAutoThresAlarmMeasValue6Out
					INTEGER,
				msapLtmSltAutoThresAlarmMeasThreshold6Out
					INTEGER,
				msapLtmSltAutoThresAlarmMeasValIndex7Out
					INTEGER,
				msapLtmSltAutoThresAlarmMeasValue7Out
					INTEGER,
				msapLtmSltAutoThresAlarmMeasThreshold7Out
					INTEGER,
				msapLtmSltAutoThresAlarmMeasValIndex8Out
					INTEGER,
				msapLtmSltAutoThresAlarmMeasValue8Out
					INTEGER,
				msapLtmSltAutoThresAlarmMeasThreshold8Out
					INTEGER,
				msapLtmSltAutoThresAlarmMeasValIndex9Out
					INTEGER,
				msapLtmSltAutoThresAlarmMeasValue9Out
					INTEGER,
				msapLtmSltAutoThresAlarmMeasThreshold9Out
					INTEGER,
				msapLtmSltAutoThresAlarmMeasValIndex10Out
					INTEGER,
				msapLtmSltAutoThresAlarmMeasValue10Out
					INTEGER,
				msapLtmSltAutoThresAlarmMeasThreshold10Out
					INTEGER,
				msapLtmSltAutoThresAlarmMeasValIndex11Out
					INTEGER,
				msapLtmSltAutoThresAlarmMeasValue11Out
					INTEGER,
				msapLtmSltAutoThresAlarmMeasThreshold11Out
					INTEGER,
				msapLtmSltAutoThresAlarmMeasValIndex12Out
					INTEGER,
				msapLtmSltAutoThresAlarmMeasValue12Out
					INTEGER,
				msapLtmSltAutoThresAlarmMeasThreshold12Out
					INTEGER,
				msapLtmSltAutoThresAlarmMeasValIndex13Out
					INTEGER,
				msapLtmSltAutoThresAlarmMeasValue13Out
					INTEGER,
				msapLtmSltAutoThresAlarmMeasThreshold13Out
					INTEGER,
				msapLtmSltAutoThresAlarmMeasValIndex14Out
					INTEGER,
				msapLtmSltAutoThresAlarmMeasValue14Out
					INTEGER,
				msapLtmSltAutoThresAlarmMeasThreshold14Out
					INTEGER,
				msapLtmSltAutoThresAlarmMeasValIndex15Out
					INTEGER,
				msapLtmSltAutoThresAlarmMeasValue15Out
					INTEGER,
				msapLtmSltAutoThresAlarmMeasThreshold15Out
					INTEGER,
				msapLtmSltAutoThresAlarmMeasValIndex16Out
					INTEGER,
				msapLtmSltAutoThresAlarmMeasValue16Out
					INTEGER,
				msapLtmSltAutoThresAlarmMeasThreshold16Out
					INTEGER,
				msapLtmSltAutoThresAlarmMeasValIndex17Out
					INTEGER,
				msapLtmSltAutoThresAlarmMeasValue17Out
					INTEGER,
				msapLtmSltAutoThresAlarmMeasThreshold17Out
					INTEGER,
				msapLtmSltAutoThresAlarmMeasValIndex18Out
					INTEGER,
				msapLtmSltAutoThresAlarmMeasValue18Out
					INTEGER,
				msapLtmSltAutoThresAlarmMeasThreshold18Out
					INTEGER
			 }

-- info-ROU: GET db
		msapLtmSltMeasAutoResultTimestampOut OBJECT-TYPE
			SYNTAX TimeTicks
			ACCESS read-only
			STATUS mandatory
			DESCRIPTION
				"Timestamp of the measurement"
			::= { msapLtmSltMeasAutoThresRecordOutEntry 1 }
		
-- info-ROU: GET db
		msapLtmSltAutoThresAlarmMeasValIndex1Out OBJECT-TYPE
			SYNTAX INTEGER
			ACCESS read-only
			STATUS mandatory
			DESCRIPTION
				"A unique value to identify a measurement value (QD2 identifier)"
			::= { msapLtmSltMeasAutoThresRecordOutEntry 3 }
		
-- info-ROU: GET db
		msapLtmSltAutoThresAlarmMeasValue1Out OBJECT-TYPE
			SYNTAX INTEGER
			ACCESS read-only
			STATUS mandatory
			DESCRIPTION
				"The measured value"
			::= { msapLtmSltMeasAutoThresRecordOutEntry 4 }
		
-- info-ROU: GET db
		msapLtmSltAutoThresAlarmMeasThreshold1Out OBJECT-TYPE
			SYNTAX INTEGER
			ACCESS read-only
			STATUS mandatory
			DESCRIPTION
				"The value of the violated threshold"
			::= { msapLtmSltMeasAutoThresRecordOutEntry 5 }
		
-- info-ROU: GET db
		msapLtmSltAutoThresAlarmMeasValIndex2Out OBJECT-TYPE
			SYNTAX INTEGER
			ACCESS read-only
			STATUS mandatory
			::= { msapLtmSltMeasAutoThresRecordOutEntry 6 }
		
-- info-ROU: GET db
		msapLtmSltAutoThresAlarmMeasValue2Out OBJECT-TYPE
			SYNTAX INTEGER
			ACCESS read-only
			STATUS mandatory
			::= { msapLtmSltMeasAutoThresRecordOutEntry 7 }
		
-- info-ROU: GET db
		msapLtmSltAutoThresAlarmMeasThreshold2Out OBJECT-TYPE
			SYNTAX INTEGER
			ACCESS read-only
			STATUS mandatory
			::= { msapLtmSltMeasAutoThresRecordOutEntry 8 }
		
-- info-ROU: GET db
		msapLtmSltAutoThresAlarmMeasValIndex3Out OBJECT-TYPE
			SYNTAX INTEGER
			ACCESS read-only
			STATUS mandatory
			::= { msapLtmSltMeasAutoThresRecordOutEntry 9 }
		
-- info-ROU: GET db
		msapLtmSltAutoThresAlarmMeasValue3Out OBJECT-TYPE
			SYNTAX INTEGER
			ACCESS read-only
			STATUS mandatory
			::= { msapLtmSltMeasAutoThresRecordOutEntry 10 }
		
-- info-ROU: GET db
		msapLtmSltAutoThresAlarmMeasThreshold3Out OBJECT-TYPE
			SYNTAX INTEGER
			ACCESS read-only
			STATUS mandatory
			::= { msapLtmSltMeasAutoThresRecordOutEntry 11 }
		
-- info-ROU: GET db
		msapLtmSltAutoThresAlarmMeasValIndex4Out OBJECT-TYPE
			SYNTAX INTEGER
			ACCESS read-only
			STATUS mandatory
			::= { msapLtmSltMeasAutoThresRecordOutEntry 12 }
		
-- info-ROU: GET db
		msapLtmSltAutoThresAlarmMeasValue4Out OBJECT-TYPE
			SYNTAX INTEGER
			ACCESS read-only
			STATUS mandatory
			::= { msapLtmSltMeasAutoThresRecordOutEntry 13 }
		
-- info-ROU: GET db
		msapLtmSltAutoThresAlarmMeasThreshold4Out OBJECT-TYPE
			SYNTAX INTEGER
			ACCESS read-only
			STATUS mandatory
			::= { msapLtmSltMeasAutoThresRecordOutEntry 14 }
		
-- info-ROU: GET db
		msapLtmSltAutoThresAlarmMeasValIndex5Out OBJECT-TYPE
			SYNTAX INTEGER
			ACCESS read-only
			STATUS mandatory
			::= { msapLtmSltMeasAutoThresRecordOutEntry 15 }
		
-- info-ROU: GET db
		msapLtmSltAutoThresAlarmMeasValue5Out OBJECT-TYPE
			SYNTAX INTEGER
			ACCESS read-only
			STATUS mandatory
			::= { msapLtmSltMeasAutoThresRecordOutEntry 16 }
		
-- info-ROU: GET db
		msapLtmSltAutoThresAlarmMeasThreshold5Out OBJECT-TYPE
			SYNTAX INTEGER
			ACCESS read-only
			STATUS mandatory
			::= { msapLtmSltMeasAutoThresRecordOutEntry 17 }
		
-- info-ROU: GET db
		msapLtmSltAutoThresAlarmMeasValIndex6Out OBJECT-TYPE
			SYNTAX INTEGER
			ACCESS read-only
			STATUS mandatory
			::= { msapLtmSltMeasAutoThresRecordOutEntry 18 }
		
-- info-ROU: GET db
		msapLtmSltAutoThresAlarmMeasValue6Out OBJECT-TYPE
			SYNTAX INTEGER
			ACCESS read-only
			STATUS mandatory
			::= { msapLtmSltMeasAutoThresRecordOutEntry 19 }
		
-- info-ROU: GET db
		msapLtmSltAutoThresAlarmMeasThreshold6Out OBJECT-TYPE
			SYNTAX INTEGER
			ACCESS read-only
			STATUS mandatory
			::= { msapLtmSltMeasAutoThresRecordOutEntry 20 }
		
-- info-ROU: GET db
		msapLtmSltAutoThresAlarmMeasValIndex7Out OBJECT-TYPE
			SYNTAX INTEGER
			ACCESS read-only
			STATUS mandatory
			::= { msapLtmSltMeasAutoThresRecordOutEntry 21 }
		
-- info-ROU: GET db
		msapLtmSltAutoThresAlarmMeasValue7Out OBJECT-TYPE
			SYNTAX INTEGER
			ACCESS read-only
			STATUS mandatory
			::= { msapLtmSltMeasAutoThresRecordOutEntry 22 }
		
-- info-ROU: GET db
		msapLtmSltAutoThresAlarmMeasThreshold7Out OBJECT-TYPE
			SYNTAX INTEGER
			ACCESS read-only
			STATUS mandatory
			::= { msapLtmSltMeasAutoThresRecordOutEntry 23 }
		
-- info-ROU: GET db
		msapLtmSltAutoThresAlarmMeasValIndex8Out OBJECT-TYPE
			SYNTAX INTEGER
			ACCESS read-only
			STATUS mandatory
			::= { msapLtmSltMeasAutoThresRecordOutEntry 24 }
		
-- info-ROU: GET db
		msapLtmSltAutoThresAlarmMeasValue8Out OBJECT-TYPE
			SYNTAX INTEGER
			ACCESS read-only
			STATUS mandatory
			::= { msapLtmSltMeasAutoThresRecordOutEntry 25 }
		
-- info-ROU: GET db
		msapLtmSltAutoThresAlarmMeasThreshold8Out OBJECT-TYPE
			SYNTAX INTEGER
			ACCESS read-only
			STATUS mandatory
			::= { msapLtmSltMeasAutoThresRecordOutEntry 26 }
		
-- info-ROU: GET db
		msapLtmSltAutoThresAlarmMeasValIndex9Out OBJECT-TYPE
			SYNTAX INTEGER
			ACCESS read-only
			STATUS mandatory
			::= { msapLtmSltMeasAutoThresRecordOutEntry 27 }
		
-- info-ROU: GET db
		msapLtmSltAutoThresAlarmMeasValue9Out OBJECT-TYPE
			SYNTAX INTEGER
			ACCESS read-only
			STATUS mandatory
			::= { msapLtmSltMeasAutoThresRecordOutEntry 28 }
		
-- info-ROU: GET db
		msapLtmSltAutoThresAlarmMeasThreshold9Out OBJECT-TYPE
			SYNTAX INTEGER
			ACCESS read-only
			STATUS mandatory
			::= { msapLtmSltMeasAutoThresRecordOutEntry 29 }
		
-- info-ROU: GET db
		msapLtmSltAutoThresAlarmMeasValIndex10Out OBJECT-TYPE
			SYNTAX INTEGER
			ACCESS read-only
			STATUS mandatory
			::= { msapLtmSltMeasAutoThresRecordOutEntry 30 }
		
-- info-ROU: GET db
		msapLtmSltAutoThresAlarmMeasValue10Out OBJECT-TYPE
			SYNTAX INTEGER
			ACCESS read-only
			STATUS mandatory
			::= { msapLtmSltMeasAutoThresRecordOutEntry 31 }
		
-- info-ROU: GET db
		msapLtmSltAutoThresAlarmMeasThreshold10Out OBJECT-TYPE
			SYNTAX INTEGER
			ACCESS read-only
			STATUS mandatory
			::= { msapLtmSltMeasAutoThresRecordOutEntry 32 }
		
-- info-ROU: GET db
		msapLtmSltAutoThresAlarmMeasValIndex11Out OBJECT-TYPE
			SYNTAX INTEGER
			ACCESS read-only
			STATUS mandatory
			::= { msapLtmSltMeasAutoThresRecordOutEntry 33 }
		
-- info-ROU: GET db
		msapLtmSltAutoThresAlarmMeasValue11Out OBJECT-TYPE
			SYNTAX INTEGER
			ACCESS read-only
			STATUS mandatory
			::= { msapLtmSltMeasAutoThresRecordOutEntry 34 }
		
-- info-ROU: GET db
		msapLtmSltAutoThresAlarmMeasThreshold11Out OBJECT-TYPE
			SYNTAX INTEGER
			ACCESS read-only
			STATUS mandatory
			::= { msapLtmSltMeasAutoThresRecordOutEntry 35 }
		
-- info-ROU: GET db
		msapLtmSltAutoThresAlarmMeasValIndex12Out OBJECT-TYPE
			SYNTAX INTEGER
			ACCESS read-only
			STATUS mandatory
			::= { msapLtmSltMeasAutoThresRecordOutEntry 36 }
		
-- info-ROU: GET db
		msapLtmSltAutoThresAlarmMeasValue12Out OBJECT-TYPE
			SYNTAX INTEGER
			ACCESS read-only
			STATUS mandatory
			::= { msapLtmSltMeasAutoThresRecordOutEntry 37 }
		
-- info-ROU: GET db
		msapLtmSltAutoThresAlarmMeasThreshold12Out OBJECT-TYPE
			SYNTAX INTEGER
			ACCESS read-only
			STATUS mandatory
			::= { msapLtmSltMeasAutoThresRecordOutEntry 38 }
		
-- info-ROU: GET db
		msapLtmSltAutoThresAlarmMeasValIndex13Out OBJECT-TYPE
			SYNTAX INTEGER
			ACCESS read-only
			STATUS mandatory
			::= { msapLtmSltMeasAutoThresRecordOutEntry 39 }
		
-- info-ROU: GET db
		msapLtmSltAutoThresAlarmMeasValue13Out OBJECT-TYPE
			SYNTAX INTEGER
			ACCESS read-only
			STATUS mandatory
			::= { msapLtmSltMeasAutoThresRecordOutEntry 40 }
		
-- info-ROU: GET db
		msapLtmSltAutoThresAlarmMeasThreshold13Out OBJECT-TYPE
			SYNTAX INTEGER
			ACCESS read-only
			STATUS mandatory
			::= { msapLtmSltMeasAutoThresRecordOutEntry 41 }
		
-- info-ROU: GET db
		msapLtmSltAutoThresAlarmMeasValIndex14Out OBJECT-TYPE
			SYNTAX INTEGER
			ACCESS read-only
			STATUS mandatory
			::= { msapLtmSltMeasAutoThresRecordOutEntry 42 }
		
-- info-ROU: GET db
		msapLtmSltAutoThresAlarmMeasValue14Out OBJECT-TYPE
			SYNTAX INTEGER
			ACCESS read-only
			STATUS mandatory
			::= { msapLtmSltMeasAutoThresRecordOutEntry 43 }
		
-- info-ROU: GET db
		msapLtmSltAutoThresAlarmMeasThreshold14Out OBJECT-TYPE
			SYNTAX INTEGER
			ACCESS read-only
			STATUS mandatory
			::= { msapLtmSltMeasAutoThresRecordOutEntry 44 }
		
-- info-ROU: GET db
		msapLtmSltAutoThresAlarmMeasValIndex15Out OBJECT-TYPE
			SYNTAX INTEGER
			ACCESS read-only
			STATUS mandatory
			::= { msapLtmSltMeasAutoThresRecordOutEntry 45 }
		
-- info-ROU: GET db
		msapLtmSltAutoThresAlarmMeasValue15Out OBJECT-TYPE
			SYNTAX INTEGER
			ACCESS read-only
			STATUS mandatory
			::= { msapLtmSltMeasAutoThresRecordOutEntry 46 }
		
-- info-ROU: GET db
		msapLtmSltAutoThresAlarmMeasThreshold15Out OBJECT-TYPE
			SYNTAX INTEGER
			ACCESS read-only
			STATUS mandatory
			::= { msapLtmSltMeasAutoThresRecordOutEntry 47 }
		
-- info-ROU: GET db
		msapLtmSltAutoThresAlarmMeasValIndex16Out OBJECT-TYPE
			SYNTAX INTEGER
			ACCESS read-only
			STATUS mandatory
			::= { msapLtmSltMeasAutoThresRecordOutEntry 48 }
		
-- info-ROU: GET db
		msapLtmSltAutoThresAlarmMeasValue16Out OBJECT-TYPE
			SYNTAX INTEGER
			ACCESS read-only
			STATUS mandatory
			::= { msapLtmSltMeasAutoThresRecordOutEntry 49 }
		
-- info-ROU: GET db
		msapLtmSltAutoThresAlarmMeasThreshold16Out OBJECT-TYPE
			SYNTAX INTEGER
			ACCESS read-only
			STATUS mandatory
			::= { msapLtmSltMeasAutoThresRecordOutEntry 50 }
		
-- info-ROU: GET db
		msapLtmSltAutoThresAlarmMeasValIndex17Out OBJECT-TYPE
			SYNTAX INTEGER
			ACCESS read-only
			STATUS mandatory
			::= { msapLtmSltMeasAutoThresRecordOutEntry 51 }
		
-- info-ROU: GET db
		msapLtmSltAutoThresAlarmMeasValue17Out OBJECT-TYPE
			SYNTAX INTEGER
			ACCESS read-only
			STATUS mandatory
			::= { msapLtmSltMeasAutoThresRecordOutEntry 52 }
		
-- info-ROU: GET db
		msapLtmSltAutoThresAlarmMeasThreshold17Out OBJECT-TYPE
			SYNTAX INTEGER
			ACCESS read-only
			STATUS mandatory
			::= { msapLtmSltMeasAutoThresRecordOutEntry 53 }
		
-- info-ROU: GET db
		msapLtmSltAutoThresAlarmMeasValIndex18Out OBJECT-TYPE
			SYNTAX INTEGER
			ACCESS read-only
			STATUS mandatory
			::= { msapLtmSltMeasAutoThresRecordOutEntry 54 }
		
-- info-ROU: GET db
		msapLtmSltAutoThresAlarmMeasValue18Out OBJECT-TYPE
			SYNTAX INTEGER
			ACCESS read-only
			STATUS mandatory
			::= { msapLtmSltMeasAutoThresRecordOutEntry 55 }
		
-- info-ROU: GET db
		msapLtmSltAutoThresAlarmMeasThreshold18Out OBJECT-TYPE
			SYNTAX INTEGER
			ACCESS read-only
			STATUS mandatory
			::= { msapLtmSltMeasAutoThresRecordOutEntry 56 }
		
		msapLtmSltMeasAutoThresRecordInTable OBJECT-TYPE
			SYNTAX SEQUENCE OF MsapLtmSltMeasAutoThresRecordInEntry
			ACCESS not-accessible
			STATUS mandatory
--DEFAULT next-function-async     fsnLtmAutoThresRecInEntryNext
--DEFAULT get-function-async      fsnLtmAutoThresRecInEntryGet
			::= { msapLtmSubscriberLineTest 7 }
		
		msapLtmSltMeasAutoThresRecordInEntry OBJECT-TYPE
			SYNTAX MsapLtmSltMeasAutoThresRecordInEntry
			ACCESS not-accessible
			STATUS mandatory
			INDEX { xldv20IfIndex, msapLtmSltAutoThresAlarmResIndexIn }
			::= { msapLtmSltMeasAutoThresRecordInTable 1 }
		
		MsapLtmSltMeasAutoThresRecordInEntry ::=
			SEQUENCE { 
				msapLtmSltMeasAutoResultTimestampIn
					TimeTicks,
				msapLtmSltAutoThresAlarmMeasValIndex1In
					INTEGER,
				msapLtmSltAutoThresAlarmMeasValue1In
					INTEGER,
				msapLtmSltAutoThresAlarmMeasThreshold1In
					INTEGER,
				msapLtmSltAutoThresAlarmMeasValIndex2In
					INTEGER,
				msapLtmSltAutoThresAlarmMeasValue2In
					INTEGER,
				msapLtmSltAutoThresAlarmMeasThreshold2In
					INTEGER,
				msapLtmSltAutoThresAlarmMeasValIndex3In
					INTEGER,
				msapLtmSltAutoThresAlarmMeasValue3In
					INTEGER,
				msapLtmSltAutoThresAlarmMeasThreshold3In
					INTEGER,
				msapLtmSltAutoThresAlarmMeasValIndex4In
					INTEGER,
				msapLtmSltAutoThresAlarmMeasValue4In
					INTEGER,
				msapLtmSltAutoThresAlarmMeasThreshold4In
					INTEGER,
				msapLtmSltAutoThresAlarmMeasValIndex5In
					INTEGER,
				msapLtmSltAutoThresAlarmMeasValue5In
					INTEGER,
				msapLtmSltAutoThresAlarmMeasThreshold5In
					INTEGER,
				msapLtmSltAutoThresAlarmMeasValIndex6In
					INTEGER,
				msapLtmSltAutoThresAlarmMeasValue6In
					INTEGER,
				msapLtmSltAutoThresAlarmMeasThreshold6In
					INTEGER,
				msapLtmSltAutoThresAlarmMeasValIndex7In
					INTEGER,
				msapLtmSltAutoThresAlarmMeasValue7In
					INTEGER,
				msapLtmSltAutoThresAlarmMeasThreshold7In
					INTEGER,
				msapLtmSltAutoThresAlarmMeasValIndex8In
					INTEGER,
				msapLtmSltAutoThresAlarmMeasValue8In
					INTEGER,
				msapLtmSltAutoThresAlarmMeasThreshold8In
					INTEGER,
				msapLtmSltAutoThresAlarmMeasValIndex9In
					INTEGER,
				msapLtmSltAutoThresAlarmMeasValue9In
					INTEGER,
				msapLtmSltAutoThresAlarmMeasThreshold9In
					INTEGER
			 }

-- info-ROU: GET db
		msapLtmSltMeasAutoResultTimestampIn OBJECT-TYPE
			SYNTAX TimeTicks
			ACCESS read-only
			STATUS mandatory
			::= { msapLtmSltMeasAutoThresRecordInEntry 1 }
		
-- info-ROU: GET db
		msapLtmSltAutoThresAlarmMeasValIndex1In OBJECT-TYPE
			SYNTAX INTEGER
			ACCESS read-only
			STATUS mandatory
			::= { msapLtmSltMeasAutoThresRecordInEntry 2 }
		
-- info-ROU: GET db
		msapLtmSltAutoThresAlarmMeasValue1In OBJECT-TYPE
			SYNTAX INTEGER
			ACCESS read-only
			STATUS mandatory
			::= { msapLtmSltMeasAutoThresRecordInEntry 3 }
		
-- info-ROU: GET db
		msapLtmSltAutoThresAlarmMeasThreshold1In OBJECT-TYPE
			SYNTAX INTEGER
			ACCESS read-only
			STATUS mandatory
			::= { msapLtmSltMeasAutoThresRecordInEntry 4 }
		
-- info-ROU: GET db
		msapLtmSltAutoThresAlarmMeasValIndex2In OBJECT-TYPE
			SYNTAX INTEGER
			ACCESS read-only
			STATUS mandatory
			::= { msapLtmSltMeasAutoThresRecordInEntry 5 }
		
-- info-ROU: GET db
		msapLtmSltAutoThresAlarmMeasValue2In OBJECT-TYPE
			SYNTAX INTEGER
			ACCESS read-only
			STATUS mandatory
			::= { msapLtmSltMeasAutoThresRecordInEntry 6 }
		
-- info-ROU: GET db
		msapLtmSltAutoThresAlarmMeasThreshold2In OBJECT-TYPE
			SYNTAX INTEGER
			ACCESS read-only
			STATUS mandatory
			::= { msapLtmSltMeasAutoThresRecordInEntry 7 }
		
-- info-ROU: GET db
		msapLtmSltAutoThresAlarmMeasValIndex3In OBJECT-TYPE
			SYNTAX INTEGER
			ACCESS read-only
			STATUS mandatory
			::= { msapLtmSltMeasAutoThresRecordInEntry 8 }
		
-- info-ROU: GET db
		msapLtmSltAutoThresAlarmMeasValue3In OBJECT-TYPE
			SYNTAX INTEGER
			ACCESS read-only
			STATUS mandatory
			::= { msapLtmSltMeasAutoThresRecordInEntry 9 }
		
-- info-ROU: GET db
		msapLtmSltAutoThresAlarmMeasThreshold3In OBJECT-TYPE
			SYNTAX INTEGER
			ACCESS read-only
			STATUS mandatory
			::= { msapLtmSltMeasAutoThresRecordInEntry 10 }
		
-- info-ROU: GET db
		msapLtmSltAutoThresAlarmMeasValIndex4In OBJECT-TYPE
			SYNTAX INTEGER
			ACCESS read-only
			STATUS mandatory
			::= { msapLtmSltMeasAutoThresRecordInEntry 11 }
		
-- info-ROU: GET db
		msapLtmSltAutoThresAlarmMeasValue4In OBJECT-TYPE
			SYNTAX INTEGER
			ACCESS read-only
			STATUS mandatory
			::= { msapLtmSltMeasAutoThresRecordInEntry 12 }
		
-- info-ROU: GET db
		msapLtmSltAutoThresAlarmMeasThreshold4In OBJECT-TYPE
			SYNTAX INTEGER
			ACCESS read-only
			STATUS mandatory
			::= { msapLtmSltMeasAutoThresRecordInEntry 14 }
		
-- info-ROU: GET db
		msapLtmSltAutoThresAlarmMeasValIndex5In OBJECT-TYPE
			SYNTAX INTEGER
			ACCESS read-only
			STATUS mandatory
			::= { msapLtmSltMeasAutoThresRecordInEntry 15 }
		
-- info-ROU: GET db
		msapLtmSltAutoThresAlarmMeasValue5In OBJECT-TYPE
			SYNTAX INTEGER
			ACCESS read-only
			STATUS mandatory
			::= { msapLtmSltMeasAutoThresRecordInEntry 16 }
		
-- info-ROU: GET db
		msapLtmSltAutoThresAlarmMeasThreshold5In OBJECT-TYPE
			SYNTAX INTEGER
			ACCESS read-only
			STATUS mandatory
			::= { msapLtmSltMeasAutoThresRecordInEntry 17 }
		
-- info-ROU: GET db
		msapLtmSltAutoThresAlarmMeasValIndex6In OBJECT-TYPE
			SYNTAX INTEGER
			ACCESS read-only
			STATUS mandatory
			::= { msapLtmSltMeasAutoThresRecordInEntry 18 }
		
-- info-ROU: GET db
		msapLtmSltAutoThresAlarmMeasValue6In OBJECT-TYPE
			SYNTAX INTEGER
			ACCESS read-only
			STATUS mandatory
			::= { msapLtmSltMeasAutoThresRecordInEntry 19 }
		
-- info-ROU: GET db
		msapLtmSltAutoThresAlarmMeasThreshold6In OBJECT-TYPE
			SYNTAX INTEGER
			ACCESS read-only
			STATUS mandatory
			::= { msapLtmSltMeasAutoThresRecordInEntry 20 }
		
-- info-ROU: GET db
		msapLtmSltAutoThresAlarmMeasValIndex7In OBJECT-TYPE
			SYNTAX INTEGER
			ACCESS read-only
			STATUS mandatory
			::= { msapLtmSltMeasAutoThresRecordInEntry 21 }
		
-- info-ROU: GET db
		msapLtmSltAutoThresAlarmMeasValue7In OBJECT-TYPE
			SYNTAX INTEGER
			ACCESS read-only
			STATUS mandatory
			::= { msapLtmSltMeasAutoThresRecordInEntry 22 }
		
-- info-ROU: GET db
		msapLtmSltAutoThresAlarmMeasThreshold7In OBJECT-TYPE
			SYNTAX INTEGER
			ACCESS read-only
			STATUS mandatory
			::= { msapLtmSltMeasAutoThresRecordInEntry 23 }
		
-- info-ROU: GET db
		msapLtmSltAutoThresAlarmMeasValIndex8In OBJECT-TYPE
			SYNTAX INTEGER
			ACCESS read-only
			STATUS mandatory
			::= { msapLtmSltMeasAutoThresRecordInEntry 24 }
		
-- info-ROU: GET db
		msapLtmSltAutoThresAlarmMeasValue8In OBJECT-TYPE
			SYNTAX INTEGER
			ACCESS read-only
			STATUS mandatory
			::= { msapLtmSltMeasAutoThresRecordInEntry 25 }
		
-- info-ROU: GET db
		msapLtmSltAutoThresAlarmMeasThreshold8In OBJECT-TYPE
			SYNTAX INTEGER
			ACCESS read-only
			STATUS mandatory
			::= { msapLtmSltMeasAutoThresRecordInEntry 26 }
		
-- info-ROU: GET db
		msapLtmSltAutoThresAlarmMeasValIndex9In OBJECT-TYPE
			SYNTAX INTEGER
			ACCESS read-only
			STATUS mandatory
			::= { msapLtmSltMeasAutoThresRecordInEntry 27 }
		
-- info-ROU: GET db
		msapLtmSltAutoThresAlarmMeasValue9In OBJECT-TYPE
			SYNTAX INTEGER
			ACCESS read-only
			STATUS mandatory
			::= { msapLtmSltMeasAutoThresRecordInEntry 28 }
		
-- info-ROU: GET db
		msapLtmSltAutoThresAlarmMeasThreshold9In OBJECT-TYPE
			SYNTAX INTEGER
			ACCESS read-only
			STATUS mandatory
			::= { msapLtmSltMeasAutoThresRecordInEntry 29 }
		
		msapLtmSltMeasAutoNoFeasibleRecordOutTable OBJECT-TYPE
			SYNTAX SEQUENCE OF MsapLtmSltMeasAutoNoFeasibleRecordOutEntry
			ACCESS not-accessible
			STATUS mandatory
--DEFAULT next-function-async     fsnLtmAutoNoFeaRecOutEntryNext
--DEFAULT get-function-async      fsnLtmAutoNoFeaRecOutEntryGet
			::= { msapLtmSubscriberLineTest 8 }
		
		msapLtmSltMeasAutoNoFeasibleRecordOutEntry OBJECT-TYPE
			SYNTAX MsapLtmSltMeasAutoNoFeasibleRecordOutEntry
			ACCESS not-accessible
			STATUS mandatory
			INDEX { xldv20IfIndex, msapLtmSltAutoNoFeasAlarmResIndexOut }
			::= { msapLtmSltMeasAutoNoFeasibleRecordOutTable 1 }
		
		MsapLtmSltMeasAutoNoFeasibleRecordOutEntry ::=
			SEQUENCE { 
				msapLtmSltMeasNoFeasResultTimestampOut
					TimeTicks,
				msapLtmSltMeasNoFeasReasonOut
					MsapLtmSltMeasNoFeasReasonType
			 }

-- info-ROU: GET db
		msapLtmSltMeasNoFeasResultTimestampOut OBJECT-TYPE
			SYNTAX TimeTicks
			ACCESS read-only
			STATUS mandatory
			DESCRIPTION
				"Timestamp of the measurement"
			::= { msapLtmSltMeasAutoNoFeasibleRecordOutEntry 1 }
		
-- info-ROU: GET db
		msapLtmSltMeasNoFeasReasonOut OBJECT-TYPE
			SYNTAX MsapLtmSltMeasNoFeasReasonType
			ACCESS read-only
			STATUS mandatory
			::= { msapLtmSltMeasAutoNoFeasibleRecordOutEntry 3 }
		
		msapLtmSltMeasAutoNoFeasibleRecordInTable OBJECT-TYPE
			SYNTAX SEQUENCE OF MsapLtmSltMeasAutoNoFeasibleRecordInEntry
			ACCESS not-accessible
			STATUS mandatory
--DEFAULT next-function-async     fsnLtmAutoNoFeaRecInEntryNext
--DEFAULT get-function-async      fsnLtmAutoNoFeaRecInEntryGet
			::= { msapLtmSubscriberLineTest 9 }
		
		msapLtmSltMeasAutoNoFeasibleRecordInEntry OBJECT-TYPE
			SYNTAX MsapLtmSltMeasAutoNoFeasibleRecordInEntry
			ACCESS not-accessible
			STATUS mandatory
			INDEX { xldv20IfIndex, msapLtmSltAutoNoFeasAlarmResIndexIn }
			::= { msapLtmSltMeasAutoNoFeasibleRecordInTable 1 }
		
		MsapLtmSltMeasAutoNoFeasibleRecordInEntry ::=
			SEQUENCE { 
				msapLtmSltMeasNoFeasResultTimestampIn
					TimeTicks,
				msapLtmSltMeasNoFeasReasonIn
					MsapLtmSltMeasNoFeasReasonType
			 }

-- info-ROU: GET db
		msapLtmSltMeasNoFeasResultTimestampIn OBJECT-TYPE
			SYNTAX TimeTicks
			ACCESS read-only
			STATUS mandatory
			::= { msapLtmSltMeasAutoNoFeasibleRecordInEntry 1 }
		
-- info-ROU: GET db
		msapLtmSltMeasNoFeasReasonIn OBJECT-TYPE
			SYNTAX MsapLtmSltMeasNoFeasReasonType
			ACCESS read-only
			STATUS mandatory
			::= { msapLtmSltMeasAutoNoFeasibleRecordInEntry 2 }
		
		msapLtmSltPatPotsRequestTable OBJECT-TYPE
			SYNTAX SEQUENCE OF MsapLtmSltPatPotsRequestEntry
			ACCESS not-accessible
			STATUS mandatory
			DESCRIPTION
				"contains the threshold for the summary alarm on errorous ports. The rest of the configuration for PAT is not in scope of management"
--DEFAULT next-function-async     fsnLtmAutoPatPotsReqEntryNext
--DEFAULT get-function-async      fsnLtmAutoPatPotsReqEntryGet
			::= { msapLtmSubscriberLineTest 10 }
		
		msapLtmSltPatPotsRequestEntry OBJECT-TYPE
			SYNTAX MsapLtmSltPatPotsRequestEntry
			ACCESS not-accessible
			STATUS mandatory
			INDEX { xldv20IfIndex }
			::= { msapLtmSltPatPotsRequestTable 1 }
		
		MsapLtmSltPatPotsRequestEntry ::=
			SEQUENCE { 
				msapLtmPatStatus
					INTEGER
			 }

-- info-ROU: GET db
		msapLtmPatStatus OBJECT-TYPE
			SYNTAX INTEGER
				{
				disabled(0),
				enabled(1)
				}
			ACCESS read-only
			STATUS mandatory
			DESCRIPTION
				"This attribute denotes the status of the PAT for the port indicated by index."
			::= { msapLtmSltPatPotsRequestEntry 1 }
		
		msapLtmSltPatPotsResponseTable OBJECT-TYPE
			SYNTAX SEQUENCE OF MsapLtmSltPatPotsResponseEntry
			ACCESS not-accessible
			STATUS mandatory
			DESCRIPTION
				"contains the reference to the measurement results stored in the sltMeasAutoPatRecordTable. This reference is only valid, if the sltPATalarm = ON. "
--DEFAULT next-function-async     fsnLtmAutoPatPotsRespEntryNext
--DEFAULT get-function-async      fsnLtmAutoPatPotsRespEntryGet
			::= { msapLtmSubscriberLineTest 11 }
		
		msapLtmSltPatPotsResponseEntry OBJECT-TYPE
			SYNTAX MsapLtmSltPatPotsResponseEntry
			ACCESS not-accessible
			STATUS mandatory
			INDEX { xldv20IfIndex }
			::= { msapLtmSltPatPotsResponseTable 1 }
		
		MsapLtmSltPatPotsResponseEntry ::=
			SEQUENCE { 
				msapLtmSltPatAlarm
					INTEGER,
				msapLtmSltPatAlarmResIndex
					INTEGER,
				msapLtmSltPatAlarmSeverityIndex
					INTEGER
			 }

-- info-ROU: GET db
		msapLtmSltPatAlarm OBJECT-TYPE
			SYNTAX INTEGER
				{
				on(1),
				off(2)
				}
			ACCESS read-only
			STATUS mandatory
			DESCRIPTION
				"PAT Alarm. This alarm is active as long as a PAT limit violation exists"
			::= { msapLtmSltPatPotsResponseEntry 1 }
		
-- info-ROU: GET db
		msapLtmSltPatAlarmResIndex OBJECT-TYPE
			SYNTAX INTEGER
			ACCESS read-only
			STATUS mandatory
			DESCRIPTION
				"A unique value to identify the msapSltMeasAutoPatRecordTable[] entry"
			::= { msapLtmSltPatPotsResponseEntry 2 }
		
-- info-ROU: GET db
		msapLtmSltPatAlarmSeverityIndex OBJECT-TYPE
			SYNTAX INTEGER
			ACCESS read-only
			STATUS mandatory
			DESCRIPTION
				"A unique value to identify the alarm severity table entry"
			::= { msapLtmSltPatPotsResponseEntry 3 }
		
		msapLtmSltMeasAutoPatRecordTable OBJECT-TYPE
			SYNTAX SEQUENCE OF MsapLtmSltMeasAutoPatRecordEntry
			ACCESS not-accessible
			STATUS mandatory
--DEFAULT next-function-async     fsnLtmAutoPatRecEntryNext
--DEFAULT get-function-async      fsnLtmAutoPatRecEntryGet
			::= { msapLtmSubscriberLineTest 12 }
		
		msapLtmSltMeasAutoPatRecordEntry OBJECT-TYPE
			SYNTAX MsapLtmSltMeasAutoPatRecordEntry
			ACCESS not-accessible
			STATUS mandatory
			INDEX { xldv20IfIndex, msapLtmSltPatAlarmResIndex }
			::= { msapLtmSltMeasAutoPatRecordTable 1 }
		
		MsapLtmSltMeasAutoPatRecordEntry ::=
			SEQUENCE { 
				msapLtmSltMeasPatResultTimestamp
					TimeTicks
			 }

-- info-ROU: GET db
		msapLtmSltMeasPatResultTimestamp OBJECT-TYPE
			SYNTAX TimeTicks
			ACCESS read-only
			STATUS mandatory
			DESCRIPTION
				"Timestamp when the alarm was set to ON"
			::= { msapLtmSltMeasAutoPatRecordEntry 1 }
		
		msapLtmSltMeasDemandRequestTable OBJECT-TYPE
			SYNTAX SEQUENCE OF MsapLtmSltMeasDemandRequestEntry
			ACCESS not-accessible
			STATUS mandatory
			DESCRIPTION
				"contains the necessary configuration data for an explicitely demanded measurement on one subscriber line per board or shelf. "
--DEFAULT next-function-async     fsnLtmDmndReqEntryNext
--DEFAULT get-function-async      fsnLtmDmndReqEntryGet
			::= { msapLtmSubscriberLineTest 13 }
		
		msapLtmSltMeasDemandRequestEntry OBJECT-TYPE
			SYNTAX MsapLtmSltMeasDemandRequestEntry
			ACCESS not-accessible
			STATUS mandatory
			INDEX { xldv20IfIndex }
			::= { msapLtmSltMeasDemandRequestTable 1 }
		
		MsapLtmSltMeasDemandRequestEntry ::=
			SEQUENCE { 
				msapLtmSltDmndMeasRequest
					MsapLtmSltMeasRequestType,
				msapLtmSltDmndMeasViaSplitter
					MsapLtmSltViaSplitterType
			 }

-- info-ROU: GET db
		msapLtmSltDmndMeasRequest OBJECT-TYPE
			SYNTAX MsapLtmSltMeasRequestType
			ACCESS read-only
			STATUS mandatory
			DESCRIPTION
				"Measuring request"
			::= { msapLtmSltMeasDemandRequestEntry 1 }
		
-- info-ROU: GET db
		msapLtmSltDmndMeasViaSplitter OBJECT-TYPE
			SYNTAX MsapLtmSltViaSplitterType
			ACCESS read-only
			STATUS mandatory
			DESCRIPTION
				"The subscriber line includes splitter(s):"
			DEFVAL { yes }
			::= { msapLtmSltMeasDemandRequestEntry 2 }
		
		msapLtmSltMeasResultTable OBJECT-TYPE
			SYNTAX SEQUENCE OF MsapLtmSltMeasResultEntry
			ACCESS not-accessible
			STATUS mandatory
			DESCRIPTION
				"contains general data about On-Demand measurements. There is one entry per port interface. The table is referenced by the related configuration tables (see above) and has a reference to the detailed measurement result values temporarily stored in the sltMeasValxxx tables."
--DEFAULT next-function-async     fsnLtmResultEntryNext
--DEFAULT get-function-async      fsnLtmResultEntryGet
			::= { msapLtmSubscriberLineTest 15 }
		
		msapLtmSltMeasResultEntry OBJECT-TYPE
			SYNTAX MsapLtmSltMeasResultEntry
			ACCESS not-accessible
			STATUS mandatory
			INDEX { msapLtmSltMeasResIndex, xldv20IfIndex }
			::= { msapLtmSltMeasResultTable 1 }
		
		MsapLtmSltMeasResultEntry ::=
			SEQUENCE { 
				msapLtmSltMeasResIndex
					INTEGER,
				msapLtmSltMeasResultTimestamp
					TimeTicks,
				msapLtmSltMeasResultType
					INTEGER,
				msapLtmSltMeasResultValIndex
					INTEGER,
				msapLtmSltMeasResultStatus
					MsapLtmSltResultStatusType,
				msapLtmSltMeasResultValType
					INTEGER
			 }

-- info-ROU: GET db
		msapLtmSltMeasResIndex OBJECT-TYPE
			SYNTAX INTEGER (1..99999)
			ACCESS read-only
			STATUS mandatory
			DESCRIPTION
				"A unique value to identify the measurement"
			::= { msapLtmSltMeasResultEntry 1 }
		
-- info-ROU: GET db
		msapLtmSltMeasResultTimestamp OBJECT-TYPE
			SYNTAX TimeTicks
			ACCESS read-write
			STATUS mandatory
			DESCRIPTION
				"Timestamp of the measurement"
			::= { msapLtmSltMeasResultEntry 2 }
		
-- info-ROU: GET db
		msapLtmSltMeasResultType OBJECT-TYPE
			SYNTAX INTEGER
				{
				auto(1),
				onDemand(2),
				noFeas(3)
				}
			ACCESS read-only
			STATUS mandatory
			DESCRIPTION
				"the kind of referenced measurement "
			::= { msapLtmSltMeasResultEntry 3 }
		
-- info-ROU: GET db
		msapLtmSltMeasResultValIndex OBJECT-TYPE
			SYNTAX INTEGER
			ACCESS read-only
			STATUS mandatory
			DESCRIPTION
				"A unique value to identify the desired measurement value table. 
				All detail result tables are stored consecutively.
				"
			::= { msapLtmSltMeasResultEntry 4 }
		
-- info-ROU: GET db
		msapLtmSltMeasResultStatus OBJECT-TYPE
			SYNTAX MsapLtmSltResultStatusType
			ACCESS read-only
			STATUS mandatory
			DESCRIPTION
				"Indicator for the success of the measurement"
			::= { msapLtmSltMeasResultEntry 5 }
		
-- info-ROU: GET db
		msapLtmSltMeasResultValType OBJECT-TYPE
			SYNTAX INTEGER
				{
				potsOut(1),
				potsIn(2),
				isdnOut(3)
				}
			ACCESS read-only
			STATUS mandatory
			DESCRIPTION
				"The value belongs to the following measusement "
			::= { msapLtmSltMeasResultEntry 6 }
		
		msapLtmSltMeasValPotsOutTable OBJECT-TYPE
			SYNTAX SEQUENCE OF MsapLtmSltMeasValPotsOutEntry
			ACCESS not-accessible
			STATUS mandatory
--DEFAULT next-function-async     fsnLtmValPoutEntryNext
--DEFAULT get-function-async      fsnLtmValPoutEntryGet
			::= { msapLtmSubscriberLineTest 16 }
		
		msapLtmSltMeasValPotsOutEntry OBJECT-TYPE
			SYNTAX MsapLtmSltMeasValPotsOutEntry
			ACCESS not-accessible
			STATUS mandatory
			INDEX { msapLtmSltMeasResultValIndex }
			::= { msapLtmSltMeasValPotsOutTable 1 }
		
		MsapLtmSltMeasValPotsOutEntry ::=
			SEQUENCE { 
				msapLtmSltPoutForeignVoltageFrequencyAe
					Counter,
				msapLtmSltPoutForeignVoltageFrequencyAb
					Counter,
				msapLtmSltPoutForeignVoltageFrequencyBe
					Counter,
				msapLtmSltPoutForeignVoltageDcAe
					Counter,
				msapLtmSltPoutForeignVoltageDcAb
					Counter,
				msapLtmSltPoutForeignVoltageDcBe
					Counter,
				msapLtmSltPoutForeignVoltageAcAe
					Counter,
				msapLtmSltPoutForeignVoltageAcAb
					Counter,
				msapLtmSltPoutForeignVoltageAcBe
					Counter,
				msapLtmSltPoutResistanceAe
					Counter,
				msapLtmSltPoutResistanceAb
					Counter,
				msapLtmSltPoutResistanceBa
					Counter,
				msapLtmSltPoutResistanceBe
					Counter,
				msapLtmSltPoutCapacityAe
					Counter,
				msapLtmSltPoutCapacityAb
					Counter,
				msapLtmSltPoutCapacityBe
					Counter,
				msapLtmSltPoutCheckPpa
					Gauge,
				msapLtmSltPoutCheckRingerLoad
					Gauge
			 }

-- info-ROU: GET db
		msapLtmSltPoutForeignVoltageFrequencyAe OBJECT-TYPE
			SYNTAX Counter
			ACCESS read-only
			STATUS mandatory
			DESCRIPTION
				"Hz"
			::= { msapLtmSltMeasValPotsOutEntry 1 }
		
-- info-ROU: GET db
		msapLtmSltPoutForeignVoltageFrequencyAb OBJECT-TYPE
			SYNTAX Counter
			ACCESS read-only
			STATUS mandatory
			DESCRIPTION
				"Hz"
			::= { msapLtmSltMeasValPotsOutEntry 2 }
		
-- info-ROU: GET db
		msapLtmSltPoutForeignVoltageFrequencyBe OBJECT-TYPE
			SYNTAX Counter
			ACCESS read-only
			STATUS mandatory
			DESCRIPTION
				"Hz"
			::= { msapLtmSltMeasValPotsOutEntry 3 }
		
-- info-ROU: GET db
		msapLtmSltPoutForeignVoltageDcAe OBJECT-TYPE
			SYNTAX Counter
			ACCESS read-only
			STATUS mandatory
			DESCRIPTION
				"V"
			::= { msapLtmSltMeasValPotsOutEntry 4 }
		
-- info-ROU: GET db
		msapLtmSltPoutForeignVoltageDcAb OBJECT-TYPE
			SYNTAX Counter
			ACCESS read-only
			STATUS mandatory
			DESCRIPTION
				"V"
			::= { msapLtmSltMeasValPotsOutEntry 5 }
		
-- info-ROU: GET db
		msapLtmSltPoutForeignVoltageDcBe OBJECT-TYPE
			SYNTAX Counter
			ACCESS read-only
			STATUS mandatory
			DESCRIPTION
				"V"
			::= { msapLtmSltMeasValPotsOutEntry 6 }
		
-- info-ROU: GET db
		msapLtmSltPoutForeignVoltageAcAe OBJECT-TYPE
			SYNTAX Counter
			ACCESS read-only
			STATUS mandatory
			DESCRIPTION
				"Veff"
			::= { msapLtmSltMeasValPotsOutEntry 7 }
		
-- info-ROU: GET db
		msapLtmSltPoutForeignVoltageAcAb OBJECT-TYPE
			SYNTAX Counter
			ACCESS read-only
			STATUS mandatory
			DESCRIPTION
				"Veff"
			::= { msapLtmSltMeasValPotsOutEntry 8 }
		
-- info-ROU: GET db
		msapLtmSltPoutForeignVoltageAcBe OBJECT-TYPE
			SYNTAX Counter
			ACCESS read-only
			STATUS mandatory
			DESCRIPTION
				"Veff"
			::= { msapLtmSltMeasValPotsOutEntry 9 }
		
-- info-ROU: GET db
		msapLtmSltPoutResistanceAe OBJECT-TYPE
			SYNTAX Counter
			ACCESS read-only
			STATUS mandatory
			DESCRIPTION
				"ohm"
			::= { msapLtmSltMeasValPotsOutEntry 10 }
		
-- info-ROU: GET db
		msapLtmSltPoutResistanceAb OBJECT-TYPE
			SYNTAX Counter
			ACCESS read-only
			STATUS mandatory
			DESCRIPTION
				"ohm"
			::= { msapLtmSltMeasValPotsOutEntry 11 }
		
-- info-ROU: GET db
		msapLtmSltPoutResistanceBa OBJECT-TYPE
			SYNTAX Counter
			ACCESS read-only
			STATUS mandatory
			DESCRIPTION
				"ohm"
			::= { msapLtmSltMeasValPotsOutEntry 12 }
		
-- info-ROU: GET db
		msapLtmSltPoutResistanceBe OBJECT-TYPE
			SYNTAX Counter
			ACCESS read-only
			STATUS mandatory
			DESCRIPTION
				"ohm"
			::= { msapLtmSltMeasValPotsOutEntry 13 }
		
-- info-ROU: GET db
		msapLtmSltPoutCapacityAe OBJECT-TYPE
			SYNTAX Counter
			ACCESS read-only
			STATUS mandatory
			DESCRIPTION
				"nF"
			::= { msapLtmSltMeasValPotsOutEntry 14 }
		
-- info-ROU: GET db
		msapLtmSltPoutCapacityAb OBJECT-TYPE
			SYNTAX Counter
			ACCESS read-only
			STATUS mandatory
			DESCRIPTION
				"nF"
			::= { msapLtmSltMeasValPotsOutEntry 15 }
		
-- info-ROU: GET db
		msapLtmSltPoutCapacityBe OBJECT-TYPE
			SYNTAX Counter
			ACCESS read-only
			STATUS mandatory
			DESCRIPTION
				"nF"
			::= { msapLtmSltMeasValPotsOutEntry 16 }
		
-- info-ROU: GET db
		msapLtmSltPoutCheckPpa OBJECT-TYPE
			SYNTAX Gauge (13..223)
			ACCESS read-only
			STATUS mandatory
			::= { msapLtmSltMeasValPotsOutEntry 17 }
		
-- info-ROU: GET db
		msapLtmSltPoutCheckRingerLoad OBJECT-TYPE
			SYNTAX Gauge (13..223)
			ACCESS read-only
			STATUS mandatory
			::= { msapLtmSltMeasValPotsOutEntry 18 }
		
		msapLtmSltMeasValPotsInTable OBJECT-TYPE
			SYNTAX SEQUENCE OF MsapLtmSltMeasValPotsInEntry
			ACCESS not-accessible
			STATUS mandatory
--DEFAULT next-function-async     fsnLtmValPinEntryNext
--DEFAULT get-function-async      fsnLtmValPinEntryGet
			::= { msapLtmSubscriberLineTest 17 }
		
		msapLtmSltMeasValPotsInEntry OBJECT-TYPE
			SYNTAX MsapLtmSltMeasValPotsInEntry
			ACCESS not-accessible
			STATUS mandatory
			INDEX { msapLtmSltMeasResultValIndex }
			::= { msapLtmSltMeasValPotsInTable 1 }
		
		MsapLtmSltMeasValPotsInEntry ::=
			SEQUENCE { 
				msapLtmSltPinOpenCirciutVoltage
					Counter,
				msapLtmSltPinFeedingCurrent
					Counter,
				msapLtmSltPinRingingVoltage
					Counter,
				msapLtmSltPinMeteringVoltage
					Counter,
				msapLtmSltPinCheckTestTone
					Gauge,
				msapLtmSltPinCheckOffHookDetection
					Gauge,
				msapLtmSltPinCheckCodec
					Gauge,
				msapLtmSltPinIdleChannelNoise
					Counter,
				msapLtmSltPinCheckOverVoltageProtection
					Gauge
			 }

-- info-ROU: GET db
		msapLtmSltPinOpenCirciutVoltage OBJECT-TYPE
			SYNTAX Counter
			ACCESS read-only
			STATUS mandatory
			DESCRIPTION
				"V"
			::= { msapLtmSltMeasValPotsInEntry 1 }
		
-- info-ROU: GET db
		msapLtmSltPinFeedingCurrent OBJECT-TYPE
			SYNTAX Counter
			ACCESS read-only
			STATUS mandatory
			DESCRIPTION
				"mA"
			::= { msapLtmSltMeasValPotsInEntry 2 }
		
-- info-ROU: GET db
		msapLtmSltPinRingingVoltage OBJECT-TYPE
			SYNTAX Counter
			ACCESS read-only
			STATUS mandatory
			DESCRIPTION
				"Veff"
			::= { msapLtmSltMeasValPotsInEntry 3 }
		
-- info-ROU: GET db
		msapLtmSltPinMeteringVoltage OBJECT-TYPE
			SYNTAX Counter
			ACCESS read-only
			STATUS mandatory
			DESCRIPTION
				"Veff"
			::= { msapLtmSltMeasValPotsInEntry 4 }
		
-- info-ROU: GET db
		msapLtmSltPinCheckTestTone OBJECT-TYPE
			SYNTAX Gauge (13..223)
			ACCESS read-only
			STATUS mandatory
			::= { msapLtmSltMeasValPotsInEntry 5 }
		
-- info-ROU: GET db
		msapLtmSltPinCheckOffHookDetection OBJECT-TYPE
			SYNTAX Gauge (0..15)
			ACCESS read-only
			STATUS mandatory
			::= { msapLtmSltMeasValPotsInEntry 6 }
		
-- info-ROU: GET db
		msapLtmSltPinCheckCodec OBJECT-TYPE
			SYNTAX Gauge (0..15)
			ACCESS read-only
			STATUS mandatory
			::= { msapLtmSltMeasValPotsInEntry 7 }
		
-- info-ROU: GET db
		msapLtmSltPinIdleChannelNoise OBJECT-TYPE
			SYNTAX Counter
			ACCESS read-only
			STATUS mandatory
			DESCRIPTION
				"dBm"
			::= { msapLtmSltMeasValPotsInEntry 8 }
		
-- info-ROU: GET db
		msapLtmSltPinCheckOverVoltageProtection OBJECT-TYPE
			SYNTAX Gauge (0..15)
			ACCESS read-only
			STATUS mandatory
			::= { msapLtmSltMeasValPotsInEntry 9 }
		
		msapLtmSltMeasValIsdnOutTable OBJECT-TYPE
			SYNTAX SEQUENCE OF MsapLtmSltMeasValIsdnOutEntry
			ACCESS not-accessible
			STATUS mandatory
--DEFAULT next-function-async     fsnLtmValIoutEntryNext
--DEFAULT get-function-async      fsnLtmValIoutEntryGet
			::= { msapLtmSubscriberLineTest 18 }
		
		msapLtmSltMeasValIsdnOutEntry OBJECT-TYPE
			SYNTAX MsapLtmSltMeasValIsdnOutEntry
			ACCESS not-accessible
			STATUS mandatory
			INDEX { msapLtmSltMeasResultValIndex }
			::= { msapLtmSltMeasValIsdnOutTable 1 }
		
		MsapLtmSltMeasValIsdnOutEntry ::=
			SEQUENCE { 
				msapLtmSltIoutForeignVoltageFrequencyAe
					Counter,
				msapLtmSltIoutForeignVoltageFrequencyAb
					Counter,
				msapLtmSltIoutForeignVoltageFrequencyBe
					Counter,
				msapLtmSltIoutForeignVoltageDcAe
					Counter,
				msapLtmSltIoutForeignVoltageDcAb
					Counter,
				msapLtmSltIoutForeignVoltageDcBe
					Counter,
				msapLtmSltIoutForeignVoltageAcAe
					Counter,
				msapLtmSltIoutForeignVoltageAcAb
					Counter,
				msapLtmSltIoutForeignVoltageAcBe
					Counter,
				msapLtmSltIoutResistanceAe
					Counter,
				msapLtmSltIoutResistanceAb
					Counter,
				msapLtmSltIoutResistanceBa
					Counter,
				msapLtmSltIoutResistanceBe
					Counter,
				msapLtmSltIoutCapacityAe
					Counter,
				msapLtmSltIoutCapacityAb
					Counter,
				msapLtmSltIoutCapacityBe
					Counter
			 }

-- info-ROU: GET db
		msapLtmSltIoutForeignVoltageFrequencyAe OBJECT-TYPE
			SYNTAX Counter
			ACCESS read-only
			STATUS mandatory
			DESCRIPTION
				"Hz"
			::= { msapLtmSltMeasValIsdnOutEntry 1 }
		
-- info-ROU: GET db
		msapLtmSltIoutForeignVoltageFrequencyAb OBJECT-TYPE
			SYNTAX Counter
			ACCESS read-only
			STATUS mandatory
			DESCRIPTION
				"Hz"
			::= { msapLtmSltMeasValIsdnOutEntry 2 }
		
-- info-ROU: GET db
		msapLtmSltIoutForeignVoltageFrequencyBe OBJECT-TYPE
			SYNTAX Counter
			ACCESS read-only
			STATUS mandatory
			DESCRIPTION
				"Hz"
			::= { msapLtmSltMeasValIsdnOutEntry 3 }
		
-- info-ROU: GET db
		msapLtmSltIoutForeignVoltageDcAe OBJECT-TYPE
			SYNTAX Counter
			ACCESS read-only
			STATUS mandatory
			DESCRIPTION
				"V"
			::= { msapLtmSltMeasValIsdnOutEntry 4 }
		
-- info-ROU: GET db
		msapLtmSltIoutForeignVoltageDcAb OBJECT-TYPE
			SYNTAX Counter
			ACCESS read-only
			STATUS mandatory
			DESCRIPTION
				"V"
			::= { msapLtmSltMeasValIsdnOutEntry 5 }
		
-- info-ROU: GET db
		msapLtmSltIoutForeignVoltageDcBe OBJECT-TYPE
			SYNTAX Counter
			ACCESS read-only
			STATUS mandatory
			DESCRIPTION
				"V"
			::= { msapLtmSltMeasValIsdnOutEntry 6 }
		
-- info-ROU: GET db
		msapLtmSltIoutForeignVoltageAcAe OBJECT-TYPE
			SYNTAX Counter
			ACCESS read-only
			STATUS mandatory
			DESCRIPTION
				"Veff"
			::= { msapLtmSltMeasValIsdnOutEntry 7 }
		
-- info-ROU: GET db
		msapLtmSltIoutForeignVoltageAcAb OBJECT-TYPE
			SYNTAX Counter
			ACCESS read-only
			STATUS mandatory
			DESCRIPTION
				"Veff"
			::= { msapLtmSltMeasValIsdnOutEntry 8 }
		
-- info-ROU: GET db
		msapLtmSltIoutForeignVoltageAcBe OBJECT-TYPE
			SYNTAX Counter
			ACCESS read-only
			STATUS mandatory
			DESCRIPTION
				"Veff"
			::= { msapLtmSltMeasValIsdnOutEntry 9 }
		
-- info-ROU: GET db
		msapLtmSltIoutResistanceAe OBJECT-TYPE
			SYNTAX Counter
			ACCESS read-only
			STATUS mandatory
			DESCRIPTION
				"ohm"
			::= { msapLtmSltMeasValIsdnOutEntry 10 }
		
-- info-ROU: GET db
		msapLtmSltIoutResistanceAb OBJECT-TYPE
			SYNTAX Counter
			ACCESS read-only
			STATUS mandatory
			DESCRIPTION
				"ohm"
			::= { msapLtmSltMeasValIsdnOutEntry 11 }
		
-- info-ROU: GET db
		msapLtmSltIoutResistanceBa OBJECT-TYPE
			SYNTAX Counter
			ACCESS read-only
			STATUS mandatory
			DESCRIPTION
				"ohm"
			::= { msapLtmSltMeasValIsdnOutEntry 12 }
		
-- info-ROU: GET db
		msapLtmSltIoutResistanceBe OBJECT-TYPE
			SYNTAX Counter
			ACCESS read-only
			STATUS mandatory
			DESCRIPTION
				"ohm"
			::= { msapLtmSltMeasValIsdnOutEntry 13 }
		
-- info-ROU: GET db
		msapLtmSltIoutCapacityAe OBJECT-TYPE
			SYNTAX Counter
			ACCESS read-only
			STATUS mandatory
			DESCRIPTION
				"nF"
			::= { msapLtmSltMeasValIsdnOutEntry 14 }
		
-- info-ROU: GET db
		msapLtmSltIoutCapacityAb OBJECT-TYPE
			SYNTAX Counter
			ACCESS read-only
			STATUS mandatory
			DESCRIPTION
				"nF"
			::= { msapLtmSltMeasValIsdnOutEntry 15 }
		
-- info-ROU: GET db
		msapLtmSltIoutCapacityBe OBJECT-TYPE
			SYNTAX Counter
			ACCESS read-only
			STATUS mandatory
			DESCRIPTION
				"nF"
			::= { msapLtmSltMeasValIsdnOutEntry 16 }
		
		msapLtmSltLineAccessRequestTable OBJECT-TYPE
			SYNTAX SEQUENCE OF MsapLtmSltLineAccessRequestEntry
			ACCESS not-accessible
			STATUS mandatory
			DESCRIPTION
				"[] contains the necessary configuration data for a explicitly demanded inward or outward line access on one ISDN/SHDSL subscriber line per shelf. No result is stored "
--DEFAULT next-function-async     fsnLtmAccReqEntryNext
--DEFAULT get-function-async      fsnLtmAccReqEntryGet
			::= { msapLtmSubscriberLineTest 19 }
		
		msapLtmSltLineAccessRequestEntry OBJECT-TYPE
			SYNTAX MsapLtmSltLineAccessRequestEntry
			ACCESS not-accessible
			STATUS mandatory
			INDEX { xldv20IfIndex }
			::= { msapLtmSltLineAccessRequestTable 1 }
		
		MsapLtmSltLineAccessRequestEntry ::=
			SEQUENCE { 
				msapLtmSltAccessLineAccess
					MsapLtmSltLineAccessType
			 }

-- info-ROU: GET db
		msapLtmSltAccessLineAccess OBJECT-TYPE
			SYNTAX MsapLtmSltLineAccessType
			ACCESS read-only
			STATUS mandatory
			DESCRIPTION
				"Line access"
			::= { msapLtmSltLineAccessRequestEntry 1 }
		
		msapLtmSltThresPotsOutTable OBJECT-TYPE
			SYNTAX SEQUENCE OF MsapLtmSltThresPotsOutEntry
			ACCESS not-accessible
			STATUS mandatory
			DESCRIPTION
				"units as for measurement values"
--DEFAULT next-function-async     fsnLtmThresPoutEntryNext
--DEFAULT get-function-async      fsnLtmThresPoutEntryGet
			::= { msapLtmSubscriberLineTest 21 }
		
		msapLtmSltThresPotsOutEntry OBJECT-TYPE
			SYNTAX MsapLtmSltThresPotsOutEntry
			ACCESS not-accessible
			STATUS mandatory
			INDEX { msapLtmSltPoutMeasThresValIndex, xldv20IfIndex }
			::= { msapLtmSltThresPotsOutTable 1 }
		
		MsapLtmSltThresPotsOutEntry ::=
			SEQUENCE { 
				msapLtmSltPoutMeasThresValIndex
					INTEGER,
				msapLtmSltPoutForeignVoltageFrequencyAeThresMin
					MsapLtmSltPoutForeignVoltageFrequencyAeType,
				msapLtmSltPoutForeignVoltageFrequencyAeThresMax
					MsapLtmSltPoutForeignVoltageFrequencyAeType,
				msapLtmSltPoutForeignVoltageFrequencyAbThresMin
					MsapLtmSltPoutForeignVoltageFrequencyAbType,
				msapLtmSltPoutForeignVoltageFrequencyAbThresMax
					MsapLtmSltPoutForeignVoltageFrequencyAbType,
				msapLtmSltPoutForeignVoltageFrequencyBeThresMin
					MsapLtmSltPoutForeignVoltageFrequencyBeType,
				msapLtmSltPoutForeignVoltageFrequencyBeThresMax
					MsapLtmSltPoutForeignVoltageFrequencyBeType,
				msapLtmSltPoutForeignVoltageDcAeThresMin
					MsapLtmSltPoutForeignVoltageDcAeType,
				msapLtmSltPoutForeignVoltageDcAeThresMax
					MsapLtmSltPoutForeignVoltageDcAeType,
				msapLtmSltPoutForeignVoltageDcAbThresMin
					MsapLtmSltPoutForeignVoltageDcAbType,
				msapLtmSltPoutForeignVoltageDcAbThresMax
					MsapLtmSltPoutForeignVoltageDcAbType,
				msapLtmSltPoutForeignVoltageDcBeThresMin
					MsapLtmSltPoutForeignVoltageDcBeType,
				msapLtmSltPoutForeignVoltageDcBeThresMax
					MsapLtmSltPoutForeignVoltageDcBeType,
				msapLtmSltPoutForeignVoltageAcAeThresMin
					MsapLtmSltPoutForeignVoltageAcAeType,
				msapLtmSltPoutForeignVoltageAcAeThresMax
					MsapLtmSltPoutForeignVoltageAcAeType,
				msapLtmSltPoutForeignVoltageAcAbThresMin
					MsapLtmSltPoutForeignVoltageAcAbType,
				msapLtmSltPoutForeignVoltageAcAbThresMax
					MsapLtmSltPoutForeignVoltageAcAbType,
				msapLtmSltPoutForeignVoltageAcBeThresMin
					MsapLtmSltPoutForeignVoltageAcBeType,
				msapLtmSltPoutForeignVoltageAcBeThresMax
					MsapLtmSltPoutForeignVoltageAcBeType,
				msapLtmSltPoutResistanceAeThresMin
					MsapLtmSltPoutResistanceAeType,
				msapLtmSltPoutResistanceAeThresMax
					MsapLtmSltPoutResistanceAeType,
				msapLtmSltPoutResistanceAbThresMin
					MsapLtmSltPoutResistanceAbType,
				msapLtmSltPoutResistanceAbThresMax
					MsapLtmSltPoutResistanceAbType,
				msapLtmSltPoutResistanceBaThresMin
					MsapLtmSltPoutResistanceBaType,
				msapLtmSltPoutResistanceBaThresMax
					MsapLtmSltPoutResistanceBaType,
				msapLtmSltPoutResistanceBeThresMin
					MsapLtmSltPoutResistanceBeType,
				msapLtmSltPoutResistanceBeThresMax
					MsapLtmSltPoutResistanceBeType,
				msapLtmSltPoutCapacityAeThresMin
					MsapLtmSltPoutCapacityAeType,
				msapLtmSltPoutCapacityAeThresMax
					MsapLtmSltPoutCapacityAeType,
				msapLtmSltPoutCapacityAbThresMin
					MsapLtmSltPoutCapacityAbType,
				msapLtmSltPoutCapacityAbThresMax
					MsapLtmSltPoutCapacityAbType,
				msapLtmSltPoutCapacityBeThresMin
					MsapLtmSltPoutCapacityBeType,
				msapLtmSltPoutCapacityBeThresMax
					MsapLtmSltPoutCapacityBeType,
				msapLtmSltPoutCheckPpaThresMin
					MsapLtmSltPoutCheckPpaType,
				msapLtmSltPoutCheckPpaThresMax
					MsapLtmSltPoutCapacityBeType,
				msapLtmSltPoutCheckRingerLoadThres
					MsapLtmSltPoutCheckRingerLoadType
			 }

-- info-ROU: GET db
		msapLtmSltPoutMeasThresValIndex OBJECT-TYPE
			SYNTAX INTEGER (1..123456)
			ACCESS read-only
			STATUS mandatory
			::= { msapLtmSltThresPotsOutEntry 1 }
		
-- info-ROU: GET db
		msapLtmSltPoutForeignVoltageFrequencyAeThresMin OBJECT-TYPE
			SYNTAX MsapLtmSltPoutForeignVoltageFrequencyAeType
			ACCESS read-only
			STATUS mandatory
			::= { msapLtmSltThresPotsOutEntry 2 }
		
-- info-ROU: GET db
		msapLtmSltPoutForeignVoltageFrequencyAeThresMax OBJECT-TYPE
			SYNTAX MsapLtmSltPoutForeignVoltageFrequencyAeType
			ACCESS read-only
			STATUS mandatory
			::= { msapLtmSltThresPotsOutEntry 3 }
		
-- info-ROU: GET db
		msapLtmSltPoutForeignVoltageFrequencyAbThresMin OBJECT-TYPE
			SYNTAX MsapLtmSltPoutForeignVoltageFrequencyAbType
			ACCESS read-only
			STATUS mandatory
			::= { msapLtmSltThresPotsOutEntry 4 }
		
-- info-ROU: GET db
		msapLtmSltPoutForeignVoltageFrequencyAbThresMax OBJECT-TYPE
			SYNTAX MsapLtmSltPoutForeignVoltageFrequencyAbType
			ACCESS read-only
			STATUS mandatory
			::= { msapLtmSltThresPotsOutEntry 5 }
		
-- info-ROU: GET db
		msapLtmSltPoutForeignVoltageFrequencyBeThresMin OBJECT-TYPE
			SYNTAX MsapLtmSltPoutForeignVoltageFrequencyBeType
			ACCESS read-only
			STATUS mandatory
			::= { msapLtmSltThresPotsOutEntry 6 }
		
-- info-ROU: GET db
		msapLtmSltPoutForeignVoltageFrequencyBeThresMax OBJECT-TYPE
			SYNTAX MsapLtmSltPoutForeignVoltageFrequencyBeType
			ACCESS read-only
			STATUS mandatory
			::= { msapLtmSltThresPotsOutEntry 7 }
		
-- info-ROU: GET db
		msapLtmSltPoutForeignVoltageDcAeThresMin OBJECT-TYPE
			SYNTAX MsapLtmSltPoutForeignVoltageDcAeType
			ACCESS read-only
			STATUS mandatory
			::= { msapLtmSltThresPotsOutEntry 8 }
		
-- info-ROU: GET db
		msapLtmSltPoutForeignVoltageDcAeThresMax OBJECT-TYPE
			SYNTAX MsapLtmSltPoutForeignVoltageDcAeType
			ACCESS read-only
			STATUS mandatory
			::= { msapLtmSltThresPotsOutEntry 9 }
		
-- info-ROU: GET db
		msapLtmSltPoutForeignVoltageDcAbThresMin OBJECT-TYPE
			SYNTAX MsapLtmSltPoutForeignVoltageDcAbType
			ACCESS read-only
			STATUS mandatory
			::= { msapLtmSltThresPotsOutEntry 10 }
		
-- info-ROU: GET db
		msapLtmSltPoutForeignVoltageDcAbThresMax OBJECT-TYPE
			SYNTAX MsapLtmSltPoutForeignVoltageDcAbType
			ACCESS read-only
			STATUS mandatory
			::= { msapLtmSltThresPotsOutEntry 11 }
		
-- info-ROU: GET db
		msapLtmSltPoutForeignVoltageDcBeThresMin OBJECT-TYPE
			SYNTAX MsapLtmSltPoutForeignVoltageDcBeType
			ACCESS read-only
			STATUS mandatory
			::= { msapLtmSltThresPotsOutEntry 12 }
		
-- info-ROU: GET db
		msapLtmSltPoutForeignVoltageDcBeThresMax OBJECT-TYPE
			SYNTAX MsapLtmSltPoutForeignVoltageDcBeType
			ACCESS read-only
			STATUS mandatory
			::= { msapLtmSltThresPotsOutEntry 13 }
		
-- info-ROU: GET db
		msapLtmSltPoutForeignVoltageAcAeThresMin OBJECT-TYPE
			SYNTAX MsapLtmSltPoutForeignVoltageAcAeType
			ACCESS read-only
			STATUS mandatory
			::= { msapLtmSltThresPotsOutEntry 14 }
		
-- info-ROU: GET db
		msapLtmSltPoutForeignVoltageAcAeThresMax OBJECT-TYPE
			SYNTAX MsapLtmSltPoutForeignVoltageAcAeType
			ACCESS read-only
			STATUS mandatory
			::= { msapLtmSltThresPotsOutEntry 15 }
		
-- info-ROU: GET db
		msapLtmSltPoutForeignVoltageAcAbThresMin OBJECT-TYPE
			SYNTAX MsapLtmSltPoutForeignVoltageAcAbType
			ACCESS read-only
			STATUS mandatory
			::= { msapLtmSltThresPotsOutEntry 16 }
		
-- info-ROU: GET db
		msapLtmSltPoutForeignVoltageAcAbThresMax OBJECT-TYPE
			SYNTAX MsapLtmSltPoutForeignVoltageAcAbType
			ACCESS read-only
			STATUS mandatory
			::= { msapLtmSltThresPotsOutEntry 17 }
		
-- info-ROU: GET db
		msapLtmSltPoutForeignVoltageAcBeThresMin OBJECT-TYPE
			SYNTAX MsapLtmSltPoutForeignVoltageAcBeType
			ACCESS read-only
			STATUS mandatory
			::= { msapLtmSltThresPotsOutEntry 18 }
		
-- info-ROU: GET db
		msapLtmSltPoutForeignVoltageAcBeThresMax OBJECT-TYPE
			SYNTAX MsapLtmSltPoutForeignVoltageAcBeType
			ACCESS read-only
			STATUS mandatory
			::= { msapLtmSltThresPotsOutEntry 19 }
		
-- info-ROU: GET db
		msapLtmSltPoutResistanceAeThresMin OBJECT-TYPE
			SYNTAX MsapLtmSltPoutResistanceAeType
			ACCESS read-only
			STATUS mandatory
			::= { msapLtmSltThresPotsOutEntry 20 }
		
-- info-ROU: GET db
		msapLtmSltPoutResistanceAeThresMax OBJECT-TYPE
			SYNTAX MsapLtmSltPoutResistanceAeType
			ACCESS read-only
			STATUS mandatory
			::= { msapLtmSltThresPotsOutEntry 21 }
		
-- info-ROU: GET db
		msapLtmSltPoutResistanceAbThresMin OBJECT-TYPE
			SYNTAX MsapLtmSltPoutResistanceAbType
			ACCESS read-only
			STATUS mandatory
			::= { msapLtmSltThresPotsOutEntry 22 }
		
-- info-ROU: GET db
		msapLtmSltPoutResistanceAbThresMax OBJECT-TYPE
			SYNTAX MsapLtmSltPoutResistanceAbType
			ACCESS read-only
			STATUS mandatory
			::= { msapLtmSltThresPotsOutEntry 23 }
		
-- info-ROU: GET db
		msapLtmSltPoutResistanceBaThresMin OBJECT-TYPE
			SYNTAX MsapLtmSltPoutResistanceBaType
			ACCESS read-only
			STATUS mandatory
			::= { msapLtmSltThresPotsOutEntry 24 }
		
-- info-ROU: GET db
		msapLtmSltPoutResistanceBaThresMax OBJECT-TYPE
			SYNTAX MsapLtmSltPoutResistanceBaType
			ACCESS read-only
			STATUS mandatory
			::= { msapLtmSltThresPotsOutEntry 25 }
		
-- info-ROU: GET db
		msapLtmSltPoutResistanceBeThresMin OBJECT-TYPE
			SYNTAX MsapLtmSltPoutResistanceBeType
			ACCESS read-only
			STATUS mandatory
			::= { msapLtmSltThresPotsOutEntry 26 }
		
-- info-ROU: GET db
		msapLtmSltPoutResistanceBeThresMax OBJECT-TYPE
			SYNTAX MsapLtmSltPoutResistanceBeType
			ACCESS read-only
			STATUS mandatory
			::= { msapLtmSltThresPotsOutEntry 27 }
		
-- info-ROU: GET db
		msapLtmSltPoutCapacityAeThresMin OBJECT-TYPE
			SYNTAX MsapLtmSltPoutCapacityAeType
			ACCESS read-only
			STATUS mandatory
			::= { msapLtmSltThresPotsOutEntry 28 }
		
-- info-ROU: GET db
		msapLtmSltPoutCapacityAeThresMax OBJECT-TYPE
			SYNTAX MsapLtmSltPoutCapacityAeType
			ACCESS read-only
			STATUS mandatory
			::= { msapLtmSltThresPotsOutEntry 29 }
		
-- info-ROU: GET db
		msapLtmSltPoutCapacityAbThresMin OBJECT-TYPE
			SYNTAX MsapLtmSltPoutCapacityAbType
			ACCESS read-only
			STATUS mandatory
			::= { msapLtmSltThresPotsOutEntry 30 }
		
-- info-ROU: GET db
		msapLtmSltPoutCapacityAbThresMax OBJECT-TYPE
			SYNTAX MsapLtmSltPoutCapacityAbType
			ACCESS read-only
			STATUS mandatory
			::= { msapLtmSltThresPotsOutEntry 32 }
		
-- info-ROU: GET db
		msapLtmSltPoutCapacityBeThresMin OBJECT-TYPE
			SYNTAX MsapLtmSltPoutCapacityBeType
			ACCESS read-only
			STATUS mandatory
			::= { msapLtmSltThresPotsOutEntry 33 }
		
-- info-ROU: GET db
		msapLtmSltPoutCapacityBeThresMax OBJECT-TYPE
			SYNTAX MsapLtmSltPoutCapacityBeType
			ACCESS read-only
			STATUS mandatory
			::= { msapLtmSltThresPotsOutEntry 34 }
		
-- info-ROU: GET db
		msapLtmSltPoutCheckPpaThresMin OBJECT-TYPE
			SYNTAX MsapLtmSltPoutCheckPpaType
			ACCESS read-only
			STATUS mandatory
			DEFVAL { ok }
			::= { msapLtmSltThresPotsOutEntry 35 }
		
-- info-ROU: GET db
		msapLtmSltPoutCheckPpaThresMax OBJECT-TYPE
			SYNTAX MsapLtmSltPoutCapacityBeType
			ACCESS read-only
			STATUS mandatory
			::= { msapLtmSltThresPotsOutEntry 36 }
		
-- info-ROU: GET db
		msapLtmSltPoutCheckRingerLoadThres OBJECT-TYPE
			SYNTAX MsapLtmSltPoutCheckRingerLoadType
			ACCESS read-only
			STATUS mandatory
			DEFVAL { ok }
			::= { msapLtmSltThresPotsOutEntry 37 }
		
		msapLtmSltThresPotsInTable OBJECT-TYPE
			SYNTAX SEQUENCE OF MsapLtmSltThresPotsInEntry
			ACCESS not-accessible
			STATUS mandatory
			DESCRIPTION
				"units as for measurement values"
--DEFAULT next-function-async     fsnLtmThresPinEntryNext
--DEFAULT get-function-async      fsnLtmThresPinEntryGet
			::= { msapLtmSubscriberLineTest 22 }
		
		msapLtmSltThresPotsInEntry OBJECT-TYPE
			SYNTAX MsapLtmSltThresPotsInEntry
			ACCESS not-accessible
			STATUS mandatory
			INDEX { msapLtmSltPinMeasThresValIndex, xldv20IfIndex }
			::= { msapLtmSltThresPotsInTable 1 }
		
		MsapLtmSltThresPotsInEntry ::=
			SEQUENCE { 
				msapLtmSltPinMeasThresValIndex
					INTEGER,
				msapLtmSltPinOpenCircuitVoltageThresMin
					MsapLtmSltPinOpenCircuitVoltageType,
				msapLtmSltPinOpenCircuitVoltageThresMax
					MsapLtmSltPinOpenCircuitVoltageType,
				msapLtmSltPinFeedingCurrentThresMin
					MsapLtmSltPinFeedingCurrentType,
				msapLtmSltPinFeedingCurrentThresMax
					MsapLtmSltPinFeedingCurrentType,
				msapLtmSltPinRingingVoltageThresMin
					MsapLtmSltPinRingingVoltageType,
				msapLtmSltPinRingingVoltageThresMax
					MsapLtmSltPinRingingVoltageType,
				msapLtmSltPinMeteringVoltageThresMin
					MsapLtmSltPinMeteringVoltageType,
				msapLtmSltPinMeteringVoltageThresMax
					MsapLtmSltPinMeteringVoltageType,
				msapLtmSltPinIdleChannelNoiseThresMin
					MsapLtmSltPinIdleChannelNoiseType,
				msapLtmSltPinIdleChannelNoiseThresMax
					MsapLtmSltPinIdleChannelNoiseType,
				msapLtmSltPinCheckTestToneThres
					MsapLtmSltPinCheckTestToneType,
				msapLtmSltPinCheckOffHookDetectionThres
					MsapLtmSltPinCheckOffHookDetectionType,
				msapLtmSltPinCheckCodecThres
					MsapLtmSltPinCheckCodecType,
				msapLtmSltPinCheckOverVoltageProtectionThres
					MsapLtmSltPinCheckOverVoltageProtectionType
			 }

-- info-ROU: GET db
		msapLtmSltPinMeasThresValIndex OBJECT-TYPE
			SYNTAX INTEGER (1..123456)
			ACCESS read-only
			STATUS mandatory
			::= { msapLtmSltThresPotsInEntry 1 }
		
-- info-ROU: GET db
		msapLtmSltPinOpenCircuitVoltageThresMin OBJECT-TYPE
			SYNTAX MsapLtmSltPinOpenCircuitVoltageType
			ACCESS read-only
			STATUS mandatory
			::= { msapLtmSltThresPotsInEntry 2 }
		
-- info-ROU: GET db
		msapLtmSltPinOpenCircuitVoltageThresMax OBJECT-TYPE
			SYNTAX MsapLtmSltPinOpenCircuitVoltageType
			ACCESS read-only
			STATUS mandatory
			::= { msapLtmSltThresPotsInEntry 3 }
		
-- info-ROU: GET db
		msapLtmSltPinFeedingCurrentThresMin OBJECT-TYPE
			SYNTAX MsapLtmSltPinFeedingCurrentType
			ACCESS read-only
			STATUS mandatory
			::= { msapLtmSltThresPotsInEntry 4 }
		
-- info-ROU: GET db
		msapLtmSltPinFeedingCurrentThresMax OBJECT-TYPE
			SYNTAX MsapLtmSltPinFeedingCurrentType
			ACCESS read-only
			STATUS mandatory
			::= { msapLtmSltThresPotsInEntry 5 }
		
-- info-ROU: GET db
		msapLtmSltPinRingingVoltageThresMin OBJECT-TYPE
			SYNTAX MsapLtmSltPinRingingVoltageType
			ACCESS read-only
			STATUS mandatory
			::= { msapLtmSltThresPotsInEntry 6 }
		
-- info-ROU: GET db
		msapLtmSltPinRingingVoltageThresMax OBJECT-TYPE
			SYNTAX MsapLtmSltPinRingingVoltageType
			ACCESS read-only
			STATUS mandatory
			::= { msapLtmSltThresPotsInEntry 7 }
		
-- info-ROU: GET db
		msapLtmSltPinMeteringVoltageThresMin OBJECT-TYPE
			SYNTAX MsapLtmSltPinMeteringVoltageType
			ACCESS read-only
			STATUS mandatory
			::= { msapLtmSltThresPotsInEntry 8 }
		
-- info-ROU: GET db
		msapLtmSltPinMeteringVoltageThresMax OBJECT-TYPE
			SYNTAX MsapLtmSltPinMeteringVoltageType
			ACCESS read-only
			STATUS mandatory
			::= { msapLtmSltThresPotsInEntry 9 }
		
-- info-ROU: GET db
		msapLtmSltPinIdleChannelNoiseThresMin OBJECT-TYPE
			SYNTAX MsapLtmSltPinIdleChannelNoiseType
			ACCESS read-only
			STATUS mandatory
			::= { msapLtmSltThresPotsInEntry 10 }
		
-- info-ROU: GET db
		msapLtmSltPinIdleChannelNoiseThresMax OBJECT-TYPE
			SYNTAX MsapLtmSltPinIdleChannelNoiseType
			ACCESS read-only
			STATUS mandatory
			::= { msapLtmSltThresPotsInEntry 11 }
		
-- info-ROU: GET db
		msapLtmSltPinCheckTestToneThres OBJECT-TYPE
			SYNTAX MsapLtmSltPinCheckTestToneType
			ACCESS read-only
			STATUS mandatory
			DEFVAL { ok }
			::= { msapLtmSltThresPotsInEntry 12 }
		
-- info-ROU: GET db
		msapLtmSltPinCheckOffHookDetectionThres OBJECT-TYPE
			SYNTAX MsapLtmSltPinCheckOffHookDetectionType
			ACCESS read-only
			STATUS mandatory
			DEFVAL { ok }
			::= { msapLtmSltThresPotsInEntry 13 }
		
-- info-ROU: GET db
		msapLtmSltPinCheckCodecThres OBJECT-TYPE
			SYNTAX MsapLtmSltPinCheckCodecType
			ACCESS read-only
			STATUS mandatory
			DEFVAL { ok }
			::= { msapLtmSltThresPotsInEntry 14 }
		
-- info-ROU: GET db
		msapLtmSltPinCheckOverVoltageProtectionThres OBJECT-TYPE
			SYNTAX MsapLtmSltPinCheckOverVoltageProtectionType
			ACCESS read-only
			STATUS mandatory
			DEFVAL { ok }
			::= { msapLtmSltThresPotsInEntry 15 }
		
		msapLtmSltMeasValPatTable OBJECT-TYPE
			SYNTAX SEQUENCE OF MsapLtmSltMeasValPatEntry
			ACCESS not-accessible
			STATUS mandatory
--DEFAULT next-function-async     fsnLtmValPatEntryNext
--DEFAULT get-function-async      fsnLtmValPatEntryGet
			::= { msapLtmSubscriberLineTest 23 }
		
		msapLtmSltMeasValPatEntry OBJECT-TYPE
			SYNTAX MsapLtmSltMeasValPatEntry
			ACCESS not-accessible
			STATUS mandatory
			INDEX { msapLtmSltMeasResultValIndex }
			::= { msapLtmSltMeasValPatTable 1 }
		
		MsapLtmSltMeasValPatEntry ::=
			SEQUENCE { 
				msapLtmSltPatOK
					INTEGER
			 }

-- info-ROU: GET db
		msapLtmSltPatOK OBJECT-TYPE
			SYNTAX INTEGER { ok(1) }
			ACCESS read-only
			STATUS mandatory
			DESCRIPTION
				"Indicator for PAT alarm status"
			::= { msapLtmSltMeasValPatEntry 1 }
		
		msapLtmMaintanance OBJECT IDENTIFIER ::= { msapLineTestManagementGroup 4 }
		
		msapLtmMaintTraps OBJECT IDENTIFIER ::= { msapLtmMaintanance 1 }
		
		msapLtmMaintTvCpePotsTtLoopState OBJECT-TYPE
			SYNTAX INTEGER
				{
				empty(1),
				off-Hook(2),
				on-Hook(3)
				}
			ACCESS not-accessible
			STATUS mandatory
			::= { msapLtmMaintTraps 1 }
		
		msapLtmMaintTvCpePotsTtLoopResistance OBJECT-TYPE
			SYNTAX INTEGER
			ACCESS not-accessible
			STATUS mandatory
			::= { msapLtmMaintTraps 2 }
		
		msapLtmMaintTvCpePotsTtNumberOfImpulses OBJECT-TYPE
			SYNTAX Gauge (1..15)
			ACCESS not-accessible
			STATUS mandatory
			::= { msapLtmMaintTraps 3 }
		
		msapLtmMaintTvCpePotsTtImpulseDuration OBJECT-TYPE
			SYNTAX INTEGER
			ACCESS not-accessible
			STATUS mandatory
			::= { msapLtmMaintTraps 4 }
		
		msapLtmMaintTvCpePotsTtPauseDuration OBJECT-TYPE
			SYNTAX INTEGER
			ACCESS not-accessible
			STATUS mandatory
			::= { msapLtmMaintTraps 5 }
		
		msapLtmMaintTvCpePotsTtHookFlashDuration OBJECT-TYPE
			SYNTAX INTEGER
			ACCESS not-accessible
			STATUS mandatory
			::= { msapLtmMaintTraps 6 }
		
		msapLtmMaintTvIsdnLoopNtMode OBJECT-TYPE
			SYNTAX MsapLtmMaintIsdnLoopNtModeType
			ACCESS not-accessible
			STATUS mandatory
			::= { msapLtmMaintTraps 7 }
		
		msapLtmMaintTvIsdnBerStart OBJECT-TYPE
			SYNTAX MsapLtmMaintIsdnBerStartType
			ACCESS not-accessible
			STATUS mandatory
			::= { msapLtmMaintTraps 8 }
		
		msapLtmMaintTvIsdnBerResultAvailable OBJECT-TYPE
			SYNTAX INTEGER
				{
				no(1),
				yes(2)
				}
			ACCESS not-accessible
			STATUS mandatory
			::= { msapLtmMaintTraps 9 }
		
		msapLtmMaintTvIsdnBerResultDuration OBJECT-TYPE
			SYNTAX OCTET STRING (SIZE (2))
			ACCESS not-accessible
			STATUS mandatory
			::= { msapLtmMaintTraps 10 }
		
		msapLtmMaintTvIsdnBerResultErrors OBJECT-TYPE
			SYNTAX OCTET STRING (SIZE (4))
			ACCESS not-accessible
			STATUS mandatory
			::= { msapLtmMaintTraps 11 }
		
		msapLtmMaintTvIsdnBerResultErrorRate OBJECT-TYPE
			SYNTAX OCTET STRING (SIZE (4))
			ACCESS not-accessible
			STATUS mandatory
			::= { msapLtmMaintTraps 12 }
		
		msapLtmMaintTvCpeIsdnLineAccess OBJECT-TYPE
			SYNTAX MsapLtmMaintCpeIsdnLineAccessType
			ACCESS not-accessible
			STATUS mandatory
			DEFVAL { off }
			::= { msapLtmMaintTraps 13 }
		
		msapLtmMaintPotsRequestTable OBJECT-TYPE
			SYNTAX SEQUENCE OF MsapLtmMaintPotsRequestEntry
			ACCESS not-accessible
			STATUS mandatory
			DESCRIPTION
				"contains the necessary configuration data for outward maintenance. No result is stored, except for Terminal Test "
--DEFAULT next-function-async     fsnLtmMaintPotsReqEntryNext
--DEFAULT get-function-async      fsnLtmMaintPotsReqEntryGet
			::= { msapLtmMaintanance 2 }
		
		msapLtmMaintPotsRequestEntry OBJECT-TYPE
			SYNTAX MsapLtmMaintPotsRequestEntry
			ACCESS not-accessible
			STATUS mandatory
			INDEX { xldv20IfIndex }
			::= { msapLtmMaintPotsRequestTable 1 }
		
		MsapLtmMaintPotsRequestEntry ::=
			SEQUENCE { 
				msapLtmMaintPotsLoopIf
					MsapLtmMaintIsdnSwitchType,
				msapLtmMaintCpePotsKind
					MsapLtmMaintCpePotsKindType,
				msapLtmMaintCpePotsNumberOfImpulses
					MsapLtmMaintCpePotsNumberType,
				msapLtmMaintCpePotsNumberOfPeriods
					MsapLtmMaintCpePotsNumberType,
				msapLtmMaintCpePotsRingingType
					MsapLtmMaintCpePotsRingingTypeType
			 }

-- info-ROU: GET db
		msapLtmMaintPotsLoopIf OBJECT-TYPE
			SYNTAX MsapLtmMaintIsdnSwitchType
			ACCESS read-only
			STATUS mandatory
			::= { msapLtmMaintPotsRequestEntry 1 }
		
-- info-ROU: GET db
		msapLtmMaintCpePotsKind OBJECT-TYPE
			SYNTAX MsapLtmMaintCpePotsKindType
			ACCESS read-only
			STATUS mandatory
			DESCRIPTION
				"Kind of CPE Test / Wiring Test"
			::= { msapLtmMaintPotsRequestEntry 2 }
		
-- info-ROU: GET db
		msapLtmMaintCpePotsNumberOfImpulses OBJECT-TYPE
			SYNTAX MsapLtmMaintCpePotsNumberType
			ACCESS read-only
			STATUS mandatory
			DESCRIPTION
				"Number Of Metering Impulses to send"
			::= { msapLtmMaintPotsRequestEntry 3 }
		
-- info-ROU: GET db
		msapLtmMaintCpePotsNumberOfPeriods OBJECT-TYPE
			SYNTAX MsapLtmMaintCpePotsNumberType
			ACCESS read-only
			STATUS mandatory
			DESCRIPTION
				"Number Of Ringing Periods to send"
			::= { msapLtmMaintPotsRequestEntry 4 }
		
-- info-ROU: GET db
		msapLtmMaintCpePotsRingingType OBJECT-TYPE
			SYNTAX MsapLtmMaintCpePotsRingingTypeType
			ACCESS read-only
			STATUS mandatory
			DESCRIPTION
				"Ringing type"
			::= { msapLtmMaintPotsRequestEntry 5 }
		
		msapLtmMaintIsdnRequestTable OBJECT-TYPE
			SYNTAX SEQUENCE OF MsapLtmMaintIsdnRequestEntry
			ACCESS not-accessible
			STATUS mandatory
			DESCRIPTION
				"contains the necessary configuration data for interface maintenance "
--DEFAULT next-function-async     fsnLtmMaintIsdnReqEntryNext
--DEFAULT get-function-async      fsnLtmMaintIsdnReqEntryGet
			::= { msapLtmMaintanance 4 }
		
		msapLtmMaintIsdnRequestEntry OBJECT-TYPE
			SYNTAX MsapLtmMaintIsdnRequestEntry
			ACCESS not-accessible
			STATUS mandatory
			INDEX { xldv20IfIndex }
			::= { msapLtmMaintIsdnRequestTable 1 }
		
		MsapLtmMaintIsdnRequestEntry ::=
			SEQUENCE { 
				msapLtmMaintIsdnReset
					MsapLtmMaintIsdnSwitchType,
				msapLtmMaintIsdnTestSignal
					INTEGER,
				msapLtmMaintIsdnLoopIf
					MsapLtmMaintIsdnSwitchType,
				msapLtmMaintIsdnLoopNt
					MsapLtmMaintIsdnSwitchType,
				msapLtmMaintIsdnLoopNtMode
					MsapLtmMaintIsdnLoopNtModeType,
				msapLtmMaintIsdnForcedAct
					MsapLtmMaintIsdnSwitchType,
				msapLtmMaintIsdnBerTimer
					Unsigned16,
				msapLtmMaintIsdnBerStart
					MsapLtmMaintIsdnBerStartType,
				msapLtmMaintIsdnBerResultAvailable
					INTEGER,
				msapLtmMaintCpeIsdnKind
					MsapLtmMaintCpeIsdnKindType,
				msapLtmMaintCpeIsdnLineAccess
					MsapLtmMaintCpeIsdnLineAccessType
			 }

-- info-ROU: GET db
		msapLtmMaintIsdnReset OBJECT-TYPE
			SYNTAX MsapLtmMaintIsdnSwitchType
			ACCESS read-only
			STATUS mandatory
			DESCRIPTION
				"Interface reset command"
			::= { msapLtmMaintIsdnRequestEntry 1 }
		
-- info-ROU: GET db
		msapLtmMaintIsdnTestSignal OBJECT-TYPE
			SYNTAX INTEGER
				{
				off(1),
				singlePulses(2)
				}
			ACCESS read-only
			STATUS mandatory
			DESCRIPTION
				"Interface test signal command"
			::= { msapLtmMaintIsdnRequestEntry 2 }
		
-- info-ROU: GET db
		msapLtmMaintIsdnLoopIf OBJECT-TYPE
			SYNTAX MsapLtmMaintIsdnSwitchType
			ACCESS read-only
			STATUS mandatory
			DESCRIPTION
				"Local Loop on the ISDN interface "
			::= { msapLtmMaintIsdnRequestEntry 4 }
		
-- info-ROU: GET db
		msapLtmMaintIsdnLoopNt OBJECT-TYPE
			SYNTAX MsapLtmMaintIsdnSwitchType
			ACCESS read-only
			STATUS mandatory
			DESCRIPTION
				"NT-Loop "
			::= { msapLtmMaintIsdnRequestEntry 5 }
		
-- info-ROU: GET db
		msapLtmMaintIsdnLoopNtMode OBJECT-TYPE
			SYNTAX MsapLtmMaintIsdnLoopNtModeType
			ACCESS read-only
			STATUS mandatory
			DESCRIPTION
				"NT-Loop mode"
			DEFVAL { complete }
			::= { msapLtmMaintIsdnRequestEntry 6 }
		
-- info-ROU: GET db
		msapLtmMaintIsdnForcedAct OBJECT-TYPE
			SYNTAX MsapLtmMaintIsdnSwitchType
			ACCESS read-only
			STATUS mandatory
			DESCRIPTION
				"Forced activation of the user port"
			::= { msapLtmMaintIsdnRequestEntry 7 }
		
-- info-ROU: GET db
		msapLtmMaintIsdnBerTimer OBJECT-TYPE
			SYNTAX Unsigned16
			ACCESS read-only
			STATUS mandatory
			DESCRIPTION
				"Timer for BER test in minutes "
			::= { msapLtmMaintIsdnRequestEntry 8 }
		
-- info-ROU: GET db
		msapLtmMaintIsdnBerStart OBJECT-TYPE
			SYNTAX MsapLtmMaintIsdnBerStartType
			ACCESS read-only
			STATUS mandatory
			DESCRIPTION
				"Start BER test "
			DEFVAL { off }
			::= { msapLtmMaintIsdnRequestEntry 9 }
		
-- info-ROU: GET db
		msapLtmMaintIsdnBerResultAvailable OBJECT-TYPE
			SYNTAX INTEGER
				{
				no(1),
				yes(2)
				}
			ACCESS read-only
			STATUS mandatory
			DESCRIPTION
				"BER test results available"
			::= { msapLtmMaintIsdnRequestEntry 10 }
		
-- info-ROU: GET db
		msapLtmMaintCpeIsdnKind OBJECT-TYPE
			SYNTAX MsapLtmMaintCpeIsdnKindType
			ACCESS read-only
			STATUS mandatory
			::= { msapLtmMaintIsdnRequestEntry 11 }
		
-- info-ROU: GET db
		msapLtmMaintCpeIsdnLineAccess OBJECT-TYPE
			SYNTAX MsapLtmMaintCpeIsdnLineAccessType
			ACCESS read-only
			STATUS mandatory
			DEFVAL { off }
			::= { msapLtmMaintIsdnRequestEntry 12 }
		
-- *************************************************************************
-- *************************************************************************
-- *************************************************************************
-- *************************************************************************
-- MSAP TLM Group
-- *************************************************************************
-- *************************************************************************
-- *************************************************************************
-- *************************************************************************
-- 
		msapTlm OBJECT IDENTIFIER ::= { msap 5 }
		
-- *************************************************************************
-- *************************************************************************
-- MSAP POTS TLM Table
-- *************************************************************************
-- *************************************************************************
-- 
		msapPotsPptpTable OBJECT-TYPE
			SYNTAX SEQUENCE OF MsapPotsPptpEntry
			ACCESS not-accessible
			STATUS mandatory
--DEFAULT next-function-async     fsnPotsPptpEntryNext
--DEFAULT get-function-async      fsnPotsPptpEntryGet
			::= { msapTlm 1 }
		
		msapPotsPptpEntry OBJECT-TYPE
			SYNTAX MsapPotsPptpEntry
			ACCESS not-accessible
			STATUS mandatory
			INDEX { xldv20IfIndex }
			::= { msapPotsPptpTable 1 }
		
		MsapPotsPptpEntry ::=
			SEQUENCE { 
				msapPotsPptpPortData
					MsapPptpPortDataType,
				msapPotsPptpIfOperState
					MsapNbOperStateType,
				msapPotsPptpChannelConnection
					MsapPptpConnectionType,
				msapPotsPptpAdditionalStateInformation
					MsapPotsAdditionalStateInformationType,
				msapPotsPptpKindOfPort
					MsapPotsKindOfPortType,
				msapPotsPptpInputLevelF2
					MsapPotsInputLevelF2Type,
				msapPotsPptpOutputLevelF2
					MsapPotsOutputLevelF2Type,
				msapPotsPptpImpedance
					MsapPotsImpedanceType,
				msapPotsPptpMeteringSignalType
					MsapPotsMeteringSignalTypeType,
				msapPotsPptpFeeding
					MsapPotsFeedingType,
				msapPotsPptpGroundKey
					MsapPotsGroundKeyType,
				msapPotsPptpMeteringVoltage
					MsapPotsMeteringVoltageType,
				msapPotsPptpMeteringFrequency
					MsapPotsMeteringFrequencyType,
				msapPotsPptpRingingFrequency
					MsapPotsRingingFrequencyType
			 }

-- info-ROU: GET db
		msapPotsPptpPortData OBJECT-TYPE
			SYNTAX MsapPptpPortDataType
			ACCESS read-only
			STATUS mandatory
			DESCRIPTION
				"Port specific ASCII  identification"
			::= { msapPotsPptpEntry 1 }
		
-- info-ROU: GET tlm
		msapPotsPptpIfOperState OBJECT-TYPE
			SYNTAX MsapNbOperStateType
			ACCESS read-only
			STATUS mandatory
			DESCRIPTION
				"Pots specific Operational state:
				_: Blocked
				_: Idle
				_: Busy                                            
				"
			::= { msapPotsPptpEntry 2 }
		
-- info-ROU: GET db
		msapPotsPptpChannelConnection OBJECT-TYPE
			SYNTAX MsapPptpConnectionType
			ACCESS read-only
			STATUS mandatory
			DESCRIPTION
				"Channel Connection:
				_: To wire
				_: No
				"
			::= { msapPotsPptpEntry 3 }
		
-- info-ROU: GET tlm
		msapPotsPptpAdditionalStateInformation OBJECT-TYPE
			SYNTAX MsapPotsAdditionalStateInformationType
			ACCESS read-only
			STATUS mandatory
			DESCRIPTION
				"In case of unreachable SU_POTS,SU_ISDN and SU_IVD_POTS
				CLU will get following value:
				
					0x00
					'not available'
					0x00
					'not available' 
					0x00
					'not available'  
					(unused octest of the string will be set to 0x00)"
			::= { msapPotsPptpEntry 4 }
		
-- info-ROU: GET db
		msapPotsPptpKindOfPort OBJECT-TYPE
			SYNTAX MsapPotsKindOfPortType
			ACCESS read-only
			STATUS mandatory
			DESCRIPTION
				"Kind Of Port:
				Special purpose of certain ports (according to PCF):
				- POTS interface
				- emergency equipment port to work with emergency 
				  telephone set (DTAG only) (on SU_POTS only)
				- Special measurement purpose of one port (TPP) 
				  (on SU_POTS only)
				"
			::= { msapPotsPptpEntry 8 }
		
-- info-ROU: GET db
		msapPotsPptpInputLevelF2 OBJECT-TYPE
			SYNTAX MsapPotsInputLevelF2Type
			ACCESS read-only
			STATUS mandatory
			DESCRIPTION
				"Input Level F2 [dBr]:
				-20 ... +10; step: 0,5 
				"
			::= { msapPotsPptpEntry 9 }
		
-- info-ROU: GET db
		msapPotsPptpOutputLevelF2 OBJECT-TYPE
			SYNTAX MsapPotsOutputLevelF2Type
			ACCESS read-only
			STATUS mandatory
			DESCRIPTION
				"Output Level F2 [dBr] (according to PCF):
				-20 ... +10; step: 0,5 
				"
			::= { msapPotsPptpEntry 10 }
		
-- info-ROU: GET db
		msapPotsPptpImpedance OBJECT-TYPE
			SYNTAX MsapPotsImpedanceType
			ACCESS read-only
			STATUS mandatory
			DESCRIPTION
				"Impedance (according to PCF):
				_: 600 ohms
				_: 900 ohms
				_: complex                                                  
				"
			::= { msapPotsPptpEntry 11 }
		
-- info-ROU: GET db
		msapPotsPptpMeteringSignalType OBJECT-TYPE
			SYNTAX MsapPotsMeteringSignalTypeType
			ACCESS read-only
			STATUS mandatory
			DESCRIPTION
				"Metering Signal Type (according to PCF):
				_: No
				_: Depending on message
				_: Silent reversal only
				_: Frequency only                                        
				"
			::= { msapPotsPptpEntry 12 }
		
-- info-ROU: GET db
		msapPotsPptpFeeding OBJECT-TYPE
			SYNTAX MsapPotsFeedingType
			ACCESS read-only
			STATUS mandatory
			DESCRIPTION
				"Feeding (according to PCF):
				_: Ordinary phone
				_: Payphone 
				"
			::= { msapPotsPptpEntry 13 }
		
-- info-ROU: GET db
		msapPotsPptpGroundKey OBJECT-TYPE
			SYNTAX MsapPotsGroundKeyType
			ACCESS read-only
			STATUS mandatory
			DESCRIPTION
				"Ground Key (according to PCF):
				_: disabled
				_: enabled                                  
				"
			::= { msapPotsPptpEntry 14 }
		
-- info-ROU: GET db
		msapPotsPptpMeteringVoltage OBJECT-TYPE
			SYNTAX MsapPotsMeteringVoltageType
			ACCESS read-only
			STATUS mandatory
			DESCRIPTION
				"Metering Voltage (according to PCF):
				_: Project specific
				_: 2 Vrms                                                     
				"
			::= { msapPotsPptpEntry 15 }
		
-- info-ROU: GET db
		msapPotsPptpMeteringFrequency OBJECT-TYPE
			SYNTAX MsapPotsMeteringFrequencyType
			ACCESS read-only
			STATUS mandatory
			DESCRIPTION
				"Metering Frequency (according to PCF):
				_: 12 kHz
				_: 16 kHz                                                     
				"
			::= { msapPotsPptpEntry 16 }
		
-- info-ROU: GET db
		msapPotsPptpRingingFrequency OBJECT-TYPE
			SYNTAX MsapPotsRingingFrequencyType
			ACCESS read-only
			STATUS mandatory
			DESCRIPTION
				"Ringing Frequency (according to PCF):
				_: Project specific
				_: 25 Hz
				_: 50 Hz                                     
				"
			::= { msapPotsPptpEntry 17 }
		
-- *************************************************************************
-- *************************************************************************
-- MSAP POTS TLM Control Group
-- *************************************************************************
-- *************************************************************************
-- 
		msapPotsPptpControlGroup OBJECT IDENTIFIER ::= { msapTlm 2 }
		
-- 
-- info-ROU: GET db SET tlm
		msapPotsPptpCtrlControlReq OBJECT-TYPE
			SYNTAX MsapPotsCtrlControlReqType
			ACCESS read-write
			STATUS mandatory
			DESCRIPTION
				"Pots PPTP control request object to activate a 
				configured set of data (command: changeData) as 
				PortData, 
				ChannelConnection, 
				KindOfPort,
				InputLevelF2, 
				OutPutLevelF2,
				Impedance, 
				MeteringSignalType, 
				Feeding and
				GroundKey.
				
				"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 1 }
		
-- 
-- info-ROU: GET db
		msapPotsPptpCtrlControlStatus OBJECT-TYPE
			SYNTAX Xldv20ControlStatus
			ACCESS read-only
			STATUS mandatory
			DESCRIPTION
				" Indicates the status of a control request. "
--DEFAULT next-function-async     fsnPotsPptpCtrlNext
--DEFAULT get-function-async      fsnPotsPptpCtrlGet
			::= { msapPotsPptpControlGroup 2 }
		
-- 
-- info-ROU: GET db
		msapPotsPptpCtrlControlReqResult OBJECT-TYPE
			SYNTAX MsapPotsCtrlControlReqType
			ACCESS read-only
			STATUS mandatory
			DESCRIPTION
				" The result of the last user command. "
--DEFAULT next-function-async     fsnPotsPptpCtrlNext
--DEFAULT get-function-async      fsnPotsPptpCtrlGet
			::= { msapPotsPptpControlGroup 3 }
		
-- 
-- info-ROU: GET db
		msapPotsPptpCtrlControlTimer OBJECT-TYPE
			SYNTAX MsapPotsCtrlControlTimerType
			ACCESS read-only
			STATUS mandatory
			DESCRIPTION
				" The time stamp of the last command (end of command). "
--DEFAULT next-function-async     fsnPotsPptpCtrlNext
--DEFAULT get-function-async      fsnPotsPptpCtrlGet
			::= { msapPotsPptpControlGroup 4 }
		
-- 
-- info-ROU: GET db SET db
		msapPotsPptpCtrlIfIndex OBJECT-TYPE
			SYNTAX INTEGER
			ACCESS read-write
			STATUS mandatory
			DESCRIPTION
				"msapIfIndex of the msapIfTable[] (Entry pointed 
				by this index is to be changed)
				
				Command parameter for command:
				msapPotsPptpChangeData"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 5 }
		
-- 
-- info-ROU: GET db SET db
		msapPotsPptpCtrlPortData OBJECT-TYPE
			SYNTAX MsapPptpPortDataType
			ACCESS read-write
			STATUS mandatory
			DESCRIPTION
				"Port specific ASCII  identification
				
				Command parameter for command:
				msapPotsPptpChangeData"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 6 }
		
-- 
-- info-ROU: GET db SET db
		msapPotsPptpCtrlChannelConnection OBJECT-TYPE
			SYNTAX MsapPptpConnectionType
			ACCESS read-write
			STATUS mandatory
			DESCRIPTION
				"Channel Connection:
				_: To wire
				_: No
				
				Command parameter for command:
				msapPotsPptpChangeData"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 7 }
		
-- 
-- info-ROU: GET db SET db
		msapPotsPptpCtrlKindOfPort OBJECT-TYPE
			SYNTAX MsapPotsKindOfPortType
			ACCESS read-write
			STATUS mandatory
			DESCRIPTION
				"Kind Of Port:
				Special purpose of certain ports (according to PCF):
				- POTS interface
				- emergency equipment port to work with emergency 
				  telephone set (DTAG only) (on SU_POTS only)
				- Special measurement purpose of one port (TPP) 
				  (on SU_POTS only)
				
				Command parameter for command:
				msapPotsPptpChangeData"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 8 }
		
-- 
-- info-ROU: GET db SET db
		msapPotsPptpCtrlInputLevelF2 OBJECT-TYPE
			SYNTAX MsapPotsInputLevelF2Type
			ACCESS read-write
			STATUS mandatory
			DESCRIPTION
				"Input Level F2 [dBr]:
				-20 ... +10; step: 0,5 
				
				Command parameter for command:
				msapPotsPptpChangeData"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 9 }
		
-- 
-- info-ROU: GET db SET db
		msapPotsPptpCtrlOutputLevelF2 OBJECT-TYPE
			SYNTAX MsapPotsOutputLevelF2Type
			ACCESS read-write
			STATUS mandatory
			DESCRIPTION
				"Output Level F2 [dBr] (according to PCF):
				-20 ... +10; step: 0,5 
				
				Command parameter for command:
				msapPotsPptpChangeData
				"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 10 }
		
-- 
-- info-ROU: GET db SET db
		msapPotsPptpCtrlImpedance OBJECT-TYPE
			SYNTAX MsapPotsImpedanceType
			ACCESS read-write
			STATUS mandatory
			DESCRIPTION
				"Impedance (according to PCF):
				_: 600 ohms
				_: 900 ohms
				_: complex                                                  
				
				Command parameter for command:
				msapPotsPptpChangeData"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 11 }
		
-- 
-- info-ROU: GET db SET db
		msapPotsPptpCtrlMeteringSignalType OBJECT-TYPE
			SYNTAX MsapPotsMeteringSignalTypeType
			ACCESS read-write
			STATUS mandatory
			DESCRIPTION
				"Metering Signal Type (according to PCF):
				_: No
				_: Depending on message
				_: Silent reversal only
				_: Frequency only                                        
				
				Command parameter for command:
				msapPotsPptpChangeData"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 12 }
		
-- 
-- info-ROU: GET db SET db
		msapPotsPptpCtrlFeeding OBJECT-TYPE
			SYNTAX MsapPotsFeedingType
			ACCESS read-write
			STATUS mandatory
			DESCRIPTION
				"Feeding (according to PCF):
				_: Ordinary phone
				_: Payphone (port 1 and 2 only) 
				
				Command parameter for command:
				msapPotsPptpChangeData"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 13 }
		
-- 
-- info-ROU: GET db SET db
		msapPotsPptpCtrlGroundKey OBJECT-TYPE
			SYNTAX MsapPotsGroundKeyType
			ACCESS read-write
			STATUS mandatory
			DESCRIPTION
				"Ground Key (according to PCF):
				_: disabled
				_: enabled                                  
				
				Command parameter for command:
				msapPotsPptpChangeData"
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 14 }
		
-- 
-- info-ROU: GET db SET db
		msapPotsPptpCtrlMeteringVoltage OBJECT-TYPE
			SYNTAX MsapPotsMeteringVoltageType
			ACCESS read-write
			STATUS mandatory
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 15 }
		
-- 
-- info-ROU: GET db SET db
		msapPotsPptpCtrlMeteringFrequency OBJECT-TYPE
			SYNTAX MsapPotsMeteringFrequencyType
			ACCESS read-write
			STATUS mandatory
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 16 }
		
-- 
-- info-ROU: GET db SET db
		msapPotsPptpCtrlRingingFrequency OBJECT-TYPE
			SYNTAX MsapPotsRingingFrequencyType
			ACCESS read-write
			STATUS mandatory
--DEFAULT test-function-async     fsnPotsPptpCtrlTest
--DEFAULT next-function-async     fsnPotsPptpCtrlNext
--DEFAULT set-function-async      fsnPotsPptpCtrlSet
--DEFAULT get-function-async      fsnPotsPptpCtrlGet
			::= { msapPotsPptpControlGroup 17 }
		
-- *************************************************************************
-- *************************************************************************
-- MSAP ISDN TLM Table
-- *************************************************************************
-- *************************************************************************
-- 
		msapIsdnPptpTable OBJECT-TYPE
			SYNTAX SEQUENCE OF MsapIsdnPptpEntry
			ACCESS not-accessible
			STATUS mandatory
--DEFAULT next-function-async     fsnIsdnPptpEntryNext
--DEFAULT get-function-async      fsnIsdnPptpEntryGet
			::= { msapTlm 3 }
		
		msapIsdnPptpEntry OBJECT-TYPE
			SYNTAX MsapIsdnPptpEntry
			ACCESS not-accessible
			STATUS mandatory
			INDEX { xldv20IfIndex }
			::= { msapIsdnPptpTable 1 }
		
		MsapIsdnPptpEntry ::=
			SEQUENCE { 
				msapIsdnPptpPortData
					MsapPptpPortDataType,
				msapIsdnPptpIfOperState
					MsapNbOperStateType,
				msapIsdnPptpChannelConnection
					MsapPptpConnectionType,
				msapIsdnPptpAdditionalStateInformation
					MsapIsdnAdditionalStateInformationType,
				msapIsdnPptpLinecode
					INTEGER,
				msapIsdnPptpIfMode
					INTEGER,
				msapIsdnPptpFeeding
					MsapIsdnOnOffType,
				msapIsdnPptp1Tr6Conversion
					MsapIsdnOnOffType,
				msapIsdnPptpB1Service
					MsapIsdnB1ServiceType,
				msapIsdnPptpB1Loop
					MsapIsdnLoopType,
				msapIsdnPptpB2Service
					MsapIsdnB2ServiceType,
				msapIsdnPptpB2Loop
					MsapIsdnLoopType,
				msapIsdnPptpDService
					MsapIsdnDServiceType,
				msapIsdnPptpDLoop
					MsapIsdnLoopType,
				msapIsdnPptpAutoact
					MsapIsdnOnOffType,
				msapIsdnPptpEnablePfReset
					MsapIsdnYesNoType,
				msapIsdnPptpEocSend
					MsapIsdnEocSendType,
				msapIsdnPptpEocRecRecord
					OCTET STRING
			 }

-- info-ROU: GET db
		msapIsdnPptpPortData OBJECT-TYPE
			SYNTAX MsapPptpPortDataType
			ACCESS read-only
			STATUS mandatory
			DESCRIPTION
				"Port specific ASCII  identification"
			::= { msapIsdnPptpEntry 1 }
		
-- info-ROU: GET tlm
		msapIsdnPptpIfOperState OBJECT-TYPE
			SYNTAX MsapNbOperStateType
			ACCESS read-only
			STATUS mandatory
			DESCRIPTION
				"Isdn specific Operational state:
				_: Blocked
				_: Idle
				_: Busy                                            
				"
			::= { msapIsdnPptpEntry 2 }
		
-- info-ROU: GET db
		msapIsdnPptpChannelConnection OBJECT-TYPE
			SYNTAX MsapPptpConnectionType
			ACCESS read-only
			STATUS mandatory
			DESCRIPTION
				"Channel Connection: 
				_: ToWire
				_: No"
			::= { msapIsdnPptpEntry 3 }
		
-- info-ROU: GET tlm
		msapIsdnPptpAdditionalStateInformation OBJECT-TYPE
			SYNTAX MsapIsdnAdditionalStateInformationType
			ACCESS read-only
			STATUS mandatory
			DESCRIPTION
				"In case of unreachable SU_POTS,SU_ISDN and SU_IVD_POTS
				CLU will get following value:
				
					0x00
					'not available'
					0x00
					'not available' 
					0x00
					'not available'  
					(unused octest of the string will be set to 0x00)"
			::= { msapIsdnPptpEntry 4 }
		
-- info-ROU: GET db
		msapIsdnPptpLinecode OBJECT-TYPE
			SYNTAX INTEGER
				{
				isdn2B1Q(1),
				isdn4B3T(2)
				}
			ACCESS read-only
			STATUS mandatory
			DESCRIPTION
				"Access line coding method:
				_: 2B1Q
				_: 4B3T
				"
			::= { msapIsdnPptpEntry 8 }
		
-- info-ROU: GET db
		msapIsdnPptpIfMode OBJECT-TYPE
			SYNTAX INTEGER { isdnLT(1) }
			ACCESS read-only
			STATUS mandatory
			DESCRIPTION
				"Interface mode of the port:
				_: LT
				"
			::= { msapIsdnPptpEntry 9 }
		
-- info-ROU: GET db
		msapIsdnPptpFeeding OBJECT-TYPE
			SYNTAX MsapIsdnOnOffType
			ACCESS read-only
			STATUS mandatory
			DESCRIPTION
				"Feeding power supply for user port:
				_: on
				_: off
				"
			::= { msapIsdnPptpEntry 10 }
		
-- info-ROU: GET db
		msapIsdnPptp1Tr6Conversion OBJECT-TYPE
			SYNTAX MsapIsdnOnOffType
			ACCESS read-only
			STATUS mandatory
			DESCRIPTION
				"D channel protocol conversion between DSS1 on the 
				network and 1TR6 on the subscriber side:
				_: off
				_: on
				"
			::= { msapIsdnPptpEntry 11 }
		
-- info-ROU: GET db
		msapIsdnPptpB1Service OBJECT-TYPE
			SYNTAX MsapIsdnB1ServiceType
			ACCESS read-only
			STATUS mandatory
			DESCRIPTION
				"Supplied B1 service (adjustment is dependent from 
				UserPort/AAL1/2 configuration):
				_: NoConf
				_: BRA
				_: PLC
				_: LL
				"
			::= { msapIsdnPptpEntry 12 }
		
-- info-ROU: GET db
		msapIsdnPptpB1Loop OBJECT-TYPE
			SYNTAX MsapIsdnLoopType
			ACCESS read-only
			STATUS mandatory
			DESCRIPTION
				"B1 loop back mode:
				_: No
				_: AccessLoop
				"
			::= { msapIsdnPptpEntry 13 }
		
-- info-ROU: GET db
		msapIsdnPptpB2Service OBJECT-TYPE
			SYNTAX MsapIsdnB2ServiceType
			ACCESS read-only
			STATUS mandatory
			DESCRIPTION
				"Supplied B2 service (adjustment is dependent from 
				UserPort/AAL1/2 configuration):
				_: NoConf
				_: BRA
				_: LL
				"
			::= { msapIsdnPptpEntry 14 }
		
-- info-ROU: GET db
		msapIsdnPptpB2Loop OBJECT-TYPE
			SYNTAX MsapIsdnLoopType
			ACCESS read-only
			STATUS mandatory
			DESCRIPTION
				"B2 loop back mode:
				_: No
				_: AccessLoop
				"
			::= { msapIsdnPptpEntry 15 }
		
-- info-ROU: GET db
		msapIsdnPptpDService OBJECT-TYPE
			SYNTAX MsapIsdnDServiceType
			ACCESS read-only
			STATUS mandatory
			DESCRIPTION
				"Supplied D-channel service (adjustment is dependent 
				from UserPort/AAL1/2 configuration):
				_: NoConf
				_: V5
				_: Transparent
				"
			::= { msapIsdnPptpEntry 16 }
		
-- info-ROU: GET db
		msapIsdnPptpDLoop OBJECT-TYPE
			SYNTAX MsapIsdnLoopType
			ACCESS read-only
			STATUS mandatory
			DESCRIPTION
				"Internal D-channel loop back to user port:
				_: No
				_: AccessLoop
				"
			::= { msapIsdnPptpEntry 17 }
		
-- info-ROU: GET db
		msapIsdnPptpAutoact OBJECT-TYPE
			SYNTAX MsapIsdnOnOffType
			ACCESS read-only
			STATUS mandatory
			DESCRIPTION
				"Steady layer 1 activation from the interface:
				_: off 
				_: on
				"
			::= { msapIsdnPptpEntry 18 }
		
-- info-ROU: GET db
		msapIsdnPptpEnablePfReset OBJECT-TYPE
			SYNTAX MsapIsdnYesNoType
			ACCESS read-only
			STATUS mandatory
			DESCRIPTION
				"Enable parameter for power feed reset for NT's in L1 
				error cases:
				
				_: off 
				_: on
				"
			::= { msapIsdnPptpEntry 19 }
		
-- info-ROU: GET tlm
		msapIsdnPptpEocSend OBJECT-TYPE
			SYNTAX MsapIsdnEocSendType
			ACCESS read-only
			STATUS mandatory
			DESCRIPTION
				"EOC send record (see Table 6-8)"
			::= { msapIsdnPptpEntry 22 }
		
-- info-ROU: GET tlm
		msapIsdnPptpEocRecRecord OBJECT-TYPE
			SYNTAX OCTET STRING (SIZE (0..20))
			ACCESS read-only
			STATUS mandatory
			DESCRIPTION
				"EOC message record (see Table 6-7)
				
				In case of unreachable SU_POTS,SU_ISDN and SU_IVD_POTS
				CLU will get following value:
				
				  0x00, ...
				  the complete record is set to 0x00"
			::= { msapIsdnPptpEntry 24 }
		
-- *************************************************************************
-- *************************************************************************
-- MSAP ISDN TLM Control Group
-- *************************************************************************
-- *************************************************************************
-- 
		msapIsdnPptpControlGroup OBJECT IDENTIFIER ::= { msapTlm 4 }
		
-- 
-- info-ROU: GET db SET tlm
		msapIsdnPptpCtrlControlReq OBJECT-TYPE
			SYNTAX MsapIsdnCtrlControlReqType
			ACCESS read-write
			STATUS mandatory
			DESCRIPTION
				"ISDN PPTP control request object to activate a 
				configured set of data (command: changeData) as
				
				PortData, 
				ChannelConnection, 
				Feeding, 
				1TR6Conversion, 
				B1Loop, 
				B2Loop, 
				DLoop, 
				Autoact, 
				EnablePFReset, 
				and EOCSend."
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 1 }
		
-- 
-- info-ROU: GET db
		msapIsdnPptpCtrlControlStatus OBJECT-TYPE
			SYNTAX Xldv20ControlStatus
			ACCESS read-only
			STATUS mandatory
			DESCRIPTION
				" Indicates the status of a control request. "
--DEFAULT next-function-async     fsnIsdnPptpCtrlNext
--DEFAULT get-function-async      fsnIsdnPptpCtrlGet
			::= { msapIsdnPptpControlGroup 2 }
		
-- 
-- info-ROU: GET db
		msapIsdnPptpCtrlControlReqResult OBJECT-TYPE
			SYNTAX MsapIsdnCtrlControlReqType
			ACCESS read-only
			STATUS mandatory
			DESCRIPTION
				" The result of the last user command. "
--DEFAULT next-function-async     fsnIsdnPptpCtrlNext
--DEFAULT get-function-async      fsnIsdnPptpCtrlGet
			::= { msapIsdnPptpControlGroup 3 }
		
-- 
-- info-ROU: GET db
		msapIsdnPptpCtrlControlTimer OBJECT-TYPE
			SYNTAX MsapIsdnCtrlControlTimerType
			ACCESS read-only
			STATUS mandatory
			DESCRIPTION
				" The time stamp of the last command (end of command). "
--DEFAULT next-function-async     fsnIsdnPptpCtrlNext
--DEFAULT get-function-async      fsnIsdnPptpCtrlGet
			::= { msapIsdnPptpControlGroup 4 }
		
-- 
-- info-ROU: GET db SET db
		msapIsdnPptpCtrlIfIndex OBJECT-TYPE
			SYNTAX INTEGER
			ACCESS read-write
			STATUS mandatory
			DESCRIPTION
				"msapIfIndex of the msapIfTable[] (Entry pointed 
				by this index is to be changed)
				
				Command parameter for command:
				msapIsdnPptpChangeData"
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 5 }
		
-- 
-- info-ROU: GET db SET db
		msapIsdnPptpCtrlPortData OBJECT-TYPE
			SYNTAX MsapPptpPortDataType
			ACCESS read-write
			STATUS mandatory
			DESCRIPTION
				"Command parameter for command:
				msapIsdnPptpChangeData
				
				Port specific ASCII  identification."
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 6 }
		
-- 
-- info-ROU: GET db SET db
		msapIsdnPptpCtrlChannelConnection OBJECT-TYPE
			SYNTAX MsapPptpConnectionType
			ACCESS read-write
			STATUS mandatory
			DESCRIPTION
				"Command parameter for command:
				msapIsdnPptpChangeData
				
				Channel Connection: At isdnChannelConnection = No: 
				the alarm 'No connection to subscriber line' 
				(isdnNoConAlarm) is activated."
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 7 }
		
-- 
-- info-ROU: GET db SET db
		msapIsdnPptpCtrlFeeding OBJECT-TYPE
			SYNTAX MsapIsdnOnOffType
			ACCESS read-write
			STATUS mandatory
			DESCRIPTION
				"Command parameter for command:
				msapIsdnPptpChangeData
				
				Feeding power supply for user port:
				_: on
				_: off
				"
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 8 }
		
-- 
-- info-ROU: GET db SET db
		msapIsdnPptpCtrl1Tr6Conversion OBJECT-TYPE
			SYNTAX MsapIsdnOnOffType
			ACCESS read-write
			STATUS mandatory
			DESCRIPTION
				"Command parameter for command:
				msapIsdnPptpChangeData
				
				D channel protocol conversion between DSS1 on the 
				network and 1TR6 on the subscriber side:
				
				_: off
				_: on
				"
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 9 }
		
-- 
-- info-ROU: GET db SET db
		msapIsdnPptpCtrlB1Service OBJECT-TYPE
			SYNTAX MsapIsdnB1ServiceType
			ACCESS read-write
			STATUS mandatory
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 10 }
		
-- 
-- info-ROU: GET db SET db
		msapIsdnPptpCtrlB1Loop OBJECT-TYPE
			SYNTAX MsapIsdnLoopType
			ACCESS read-write
			STATUS mandatory
			DESCRIPTION
				"Command parameter for command:
				msapIsdnPptpChangeData
				
				B1 loop back mode:
				_: No
				_: AccessLoop
				"
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 11 }
		
-- 
-- info-ROU: GET db SET db
		msapIsdnPptpCtrlB2Service OBJECT-TYPE
			SYNTAX MsapIsdnB2ServiceType
			ACCESS read-write
			STATUS mandatory
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 12 }
		
-- 
-- info-ROU: GET db SET db
		msapIsdnPptpCtrlB2Loop OBJECT-TYPE
			SYNTAX MsapIsdnLoopType
			ACCESS read-write
			STATUS mandatory
			DESCRIPTION
				"Command parameter for command:
				msapIsdnPptpChangeData
				
				B2 loop back mode:
				_: No
				_: AccessLoop
				"
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 13 }
		
-- 
-- info-ROU: GET db SET db
		msapIsdnPptpCtrlDService OBJECT-TYPE
			SYNTAX MsapIsdnDServiceType
			ACCESS read-write
			STATUS mandatory
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 14 }
		
-- 
-- info-ROU: GET db SET db
		msapIsdnPptpCtrlDLoop OBJECT-TYPE
			SYNTAX MsapIsdnLoopType
			ACCESS read-write
			STATUS mandatory
			DESCRIPTION
				"Command parameter for command:
				msapIsdnPptpChangeData
				
				Internal D-channel loop back to user port:
				_: No
				_: AccessLoop
				"
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 15 }
		
-- 
-- info-ROU: GET db SET db
		msapIsdnPptpCtrlAutoact OBJECT-TYPE
			SYNTAX MsapIsdnOnOffType
			ACCESS read-write
			STATUS mandatory
			DESCRIPTION
				"Command parameter for command:
				msapIsdnPptpChangeData
				
				Steady layer 1 activation from the interface:
				_: off 
				_: on
				"
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 16 }
		
-- 
-- info-ROU: GET db SET db
		msapIsdnPptpCtrlEnablePfReset OBJECT-TYPE
			SYNTAX MsapIsdnYesNoType
			ACCESS read-write
			STATUS mandatory
			DESCRIPTION
				"Command parameter for command:
				msapIsdnPptpChangeData
				
				Enable parameter for power feed reset for NT's in L1 
				error cases:
				
				_: off 
				_: on
				"
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 17 }
		
-- 
-- info-ROU: GET db SET db
		msapIsdnPptpCtrlEocSend OBJECT-TYPE
			SYNTAX MsapIsdnEocSendType
			ACCESS read-write
			STATUS mandatory
			DESCRIPTION
				"Command parameter for command:
				msapIsdnPptpEocSend
				
				EOC send record"
--DEFAULT test-function-async     fsnIsdnPptpCtrlTest
--DEFAULT next-function-async     fsnIsdnPptpCtrlNext
--DEFAULT set-function-async      fsnIsdnPptpCtrlSet
--DEFAULT get-function-async      fsnIsdnPptpCtrlGet
			::= { msapIsdnPptpControlGroup 18 }
		
-- *************************************************************************
-- *************************************************************************
-- MSAP TLM Traps
-- *************************************************************************
-- *************************************************************************
-- 
		msapTlmTraps OBJECT IDENTIFIER ::= { msapTlm 5 }
		
		msapTlmTrapVars OBJECT IDENTIFIER ::= { msapTlmTraps 1 }
		
		msapTvPotsPptpIfIndex OBJECT-TYPE
			SYNTAX INTEGER
			ACCESS not-accessible
			STATUS mandatory
			DESCRIPTION
				"msapIfIndex of the msapIfTable[] (Entry pointed 
				by this index is to be changed)"
			::= { msapTlmTrapVars 1 }
		
		msapTvPotsPptpTimeAndDate OBJECT-TYPE
			SYNTAX INTEGER
			ACCESS not-accessible
			STATUS mandatory
			::= { msapTlmTrapVars 2 }
		
		msapTvPotsPptpPortData OBJECT-TYPE
			SYNTAX DisplayString
			ACCESS not-accessible
			STATUS mandatory
			DESCRIPTION
				"Port specific ASCII  identification
				
				Command parameter for command:
				msapPotsPptpChangeData"
			::= { msapTlmTrapVars 3 }
		
		msapTvPotsPptpChannelConnection OBJECT-TYPE
			SYNTAX MsapPptpConnectionType
			ACCESS not-accessible
			STATUS mandatory
			DESCRIPTION
				"Channel Connection:
				_: To wire
				_: No
				
				Command parameter for command:
				msapPotsPptpChangeData"
			::= { msapTlmTrapVars 4 }
		
		msapTvPotsPptpKindOfPort OBJECT-TYPE
			SYNTAX MsapPotsKindOfPortType
			ACCESS not-accessible
			STATUS mandatory
			DESCRIPTION
				"Kind Of Port:
				Special purpose of certain ports (according to PCF):
				- POTS interface
				- emergency equipment port to work with emergency 
				  telephone set (DTAG only) (on SU_POTS only)
				- Special measurement purpose of one port (TPP) 
				  (on SU_POTS only)
				"
			::= { msapTlmTrapVars 5 }
		
		msapTvPotsPptpInputLevelF2 OBJECT-TYPE
			SYNTAX MsapPotsInputLevelF2Type
			ACCESS not-accessible
			STATUS mandatory
			DESCRIPTION
				"Input Level F2 [dBr]:
				-20 ... +10; step: 0,5 "
			::= { msapTlmTrapVars 6 }
		
		msapTvPotsPptpOutputLevelF2 OBJECT-TYPE
			SYNTAX MsapPotsOutputLevelF2Type
			ACCESS not-accessible
			STATUS mandatory
			DESCRIPTION
				"Output Level F2 [dBr] (according to PCF):
				-20 ... +10; step: 0,5 
				"
			::= { msapTlmTrapVars 7 }
		
		msapTvPotsPptpImpedance OBJECT-TYPE
			SYNTAX MsapPotsImpedanceType
			ACCESS not-accessible
			STATUS mandatory
			DESCRIPTION
				"Impedance (according to PCF):
				_: 600 ohms
				_: 900 ohms
				_: complex   "
			::= { msapTlmTrapVars 8 }
		
		msapTvPotsPptpMeteringSignalType OBJECT-TYPE
			SYNTAX MsapPotsMeteringSignalTypeType
			ACCESS not-accessible
			STATUS mandatory
			DESCRIPTION
				"Metering Signal Type (according to PCF):
				_: No
				_: Depending on message
				_: Silent reversal only
				_: Frequency only                                        
				"
			::= { msapTlmTrapVars 9 }
		
		msapTvPotsPptpFeeding OBJECT-TYPE
			SYNTAX MsapPotsFeedingType
			ACCESS not-accessible
			STATUS mandatory
			DESCRIPTION
				"Feeding"
			::= { msapTlmTrapVars 10 }
		
		msapTvPotsPptpGroundKey OBJECT-TYPE
			SYNTAX MsapPotsGroundKeyType
			ACCESS not-accessible
			STATUS mandatory
			DESCRIPTION
				"Ground Key (according to PCF):
				_: disabled
				_: enabled  "
			::= { msapTlmTrapVars 11 }
		
		msapTvIsdnPptpIfIndex OBJECT-TYPE
			SYNTAX INTEGER
			ACCESS not-accessible
			STATUS mandatory
			::= { msapTlmTrapVars 12 }
		
		msapTvIsdnPptpTimeAndDate OBJECT-TYPE
			SYNTAX INTEGER
			ACCESS not-accessible
			STATUS mandatory
			::= { msapTlmTrapVars 13 }
		
		msapTvIsdnPptpPortData OBJECT-TYPE
			SYNTAX DisplayString
			ACCESS not-accessible
			STATUS mandatory
			DESCRIPTION
				"Port specific ASCII  identification."
			::= { msapTlmTrapVars 14 }
		
		msapTvIsdnPptpChannelConnection OBJECT-TYPE
			SYNTAX MsapPptpConnectionType
			ACCESS not-accessible
			STATUS mandatory
			DESCRIPTION
				"Command parameter for command:
				msapIsdnPptpChangeData
				
				Channel Connection: At isdnChannelConnection = No: 
				the alarm 'No connection to subscriber line' 
				(isdnNoConAlarm) is activated."
			::= { msapTlmTrapVars 15 }
		
		msapTvIsdnPptpFeeding OBJECT-TYPE
			SYNTAX MsapIsdnOnOffType
			ACCESS not-accessible
			STATUS mandatory
			DESCRIPTION
				"Feeding power supply for user port:
				_: on
				_: off
				"
			::= { msapTlmTrapVars 16 }
		
		msapTvIsdnPptp1Tr6Conversion OBJECT-TYPE
			SYNTAX MsapIsdnOnOffType
			ACCESS not-accessible
			STATUS mandatory
			DESCRIPTION
				"D channel protocol conversion between DSS1 on the 
				network and 1TR6 on the subscriber side:
				
				_: off
				_: on"
			::= { msapTlmTrapVars 17 }
		
		msapTvIsdnPptpB1Service OBJECT-TYPE
			SYNTAX MsapIsdnB1ServiceType
			ACCESS not-accessible
			STATUS mandatory
			::= { msapTlmTrapVars 18 }
		
		msapTvIsdnPptpB1Loop OBJECT-TYPE
			SYNTAX MsapIsdnLoopType
			ACCESS not-accessible
			STATUS mandatory
			DESCRIPTION
				"Command parameter for command:
				msapIsdnPptpChangeData
				
				B1 loop back mode:
				_: No
				_: AccessLoop
				"
			::= { msapTlmTrapVars 19 }
		
		msapTvIsdnPptpB2Service OBJECT-TYPE
			SYNTAX MsapIsdnB2ServiceType
			ACCESS not-accessible
			STATUS mandatory
			::= { msapTlmTrapVars 20 }
		
		msapTvIsdnPptpB2Loop OBJECT-TYPE
			SYNTAX MsapIsdnLoopType
			ACCESS not-accessible
			STATUS mandatory
			DESCRIPTION
				"B2 loop back mode:
				_: No
				_: AccessLoop
				"
			::= { msapTlmTrapVars 21 }
		
		msapTvIsdnPptpDService OBJECT-TYPE
			SYNTAX MsapIsdnDServiceType
			ACCESS not-accessible
			STATUS mandatory
			::= { msapTlmTrapVars 22 }
		
		msapTvIsdnPptpDLoop OBJECT-TYPE
			SYNTAX MsapIsdnLoopType
			ACCESS not-accessible
			STATUS mandatory
			DESCRIPTION
				"Internal D-channel loop back to user port:
				_: No
				_: AccessLoop
				
				"
			::= { msapTlmTrapVars 23 }
		
		msapTvIsdnPptpAutoact OBJECT-TYPE
			SYNTAX MsapIsdnOnOffType
			ACCESS not-accessible
			STATUS mandatory
			DESCRIPTION
				"Steady layer 1 activation from the interface:
				_: off 
				_: on"
			::= { msapTlmTrapVars 24 }
		
		msapTvIsdnPptpEnablePfReset OBJECT-TYPE
			SYNTAX MsapIsdnYesNoType
			ACCESS not-accessible
			STATUS mandatory
			DESCRIPTION
				"Enable parameter for power feed reset for NT's in L1 
				error cases:
				
				_: off 
				_: on"
			::= { msapTlmTrapVars 25 }
		
		msapTvIsdnPptpEocSend OBJECT-TYPE
			SYNTAX MsapIsdnEocSendType
			ACCESS not-accessible
			STATUS mandatory
			DESCRIPTION
				"EOC send request"
			::= { msapTlmTrapVars 26 }
		
	
--
-- Trap definitions
--
	
		msapTrAal1IfCreated TRAP-TYPE
			ENTERPRISE msap
			VARIABLES { msapAal1TvTimeAndDate, msapAal1TvIfIndex, msapAal1TvVccIndex, msapAal1TvOperState, msapAal1TvAdminState, 
				msapAal1TvHwUnitIndex, msapAal1TvAlarmState, msapAal1TvCbrClockMode, msapAal1TvCas, msapAal1TvPartialFill, 
				msapAal1TvBufMaxSize, msapAal1TvCdvRxT, msapAal1TvCellLossIntegrationPeriod, msapAal1TvConnType, msapAal1TvDbCes, 
				msapAal1TvDbCesIdlePattern, msapAal1TvSignalingMode }
			DESCRIPTION
				"This trap is send when an AAL1 Interface has been created."
			::=  1300
			
		msapTrAal1IfDeleted TRAP-TYPE
			ENTERPRISE msap
			VARIABLES { msapAal1TvTimeAndDate, msapAal1TvIfIndex }
			DESCRIPTION
				"This trap is send when an AAL1 Interface has been deleted."
			::=  1301
			
		msapTrAal1IfModified TRAP-TYPE
			ENTERPRISE msap
			VARIABLES { msapAal1TvTimeAndDate, msapAal1TvIfIndex, msapAal1TvBufMaxSize, msapAal1TvCdvRxT, msapAal1TvCellLossIntegrationPeriod, 
				msapAal1TvDbCesIdlePattern }
			DESCRIPTION
				"This trap is send when an AAL1 Interface has changed its state."
			::=  1302
			
		msapTrAal1IfAdminStateChanged TRAP-TYPE
			ENTERPRISE msap
			VARIABLES { msapAal1TvTimeAndDate, msapAal1TvIfIndex, msapAal1TvAdminState }
			DESCRIPTION
				"This trap is send when the AdminState of an AAL1 Interface has been changed."
			::=  1303
			
		msapTrAal1IfOperStateChanged TRAP-TYPE
			ENTERPRISE msap
			VARIABLES { msapAal1TvTimeAndDate, msapAal1TvIfIndex, msapAal1TvOperState }
			DESCRIPTION
				"This trap is send when the OperState of an AAL1 Interface has been changed."
			::=  1304
			
		msapTrUsCreated TRAP-TYPE
			ENTERPRISE msap
			VARIABLES { msapUsTvTimeAndDate, msapUsTvIndex, msapUsTvOperState, msapUsTvAdminState, msapUsTvType, 
				msapUsTvPptpIfIndex, msapUsTvAalxIfIndex, msapCesUsTvTimeSlotMap, msapCesUsTvServiceType, msapIsdnPstnUsTvPortNumber, 
				msapIsdnLlUsTvDChannelMode, msapIsdnPstnUsTvAalType }
			DESCRIPTION
				"This trap is send when an basic CES UPCC has been created."
			::=  1305
			
		msapTrUsDeleted TRAP-TYPE
			ENTERPRISE msap
			VARIABLES { msapUsTvTimeAndDate, msapUsTvIndex }
			DESCRIPTION
				"This trap is send when an UPCC has been deleted."
			::=  1306
			
		msapTrUsModified TRAP-TYPE
			ENTERPRISE msap
			VARIABLES { msapUsTvTimeAndDate, msapUsTvIndex, msapCesUsTvTimeSlotMap }
			DESCRIPTION
				"This trap is send when an UPCC has been changed its state."
			::=  1307
			
		msapTrUsAdminStateChanged TRAP-TYPE
			ENTERPRISE msap
			VARIABLES { msapUsTvTimeAndDate, msapUsTvIndex, msapUsTvAdminState }
			DESCRIPTION
				"This trap is send when the AdminState of an UP has been changed."
			::=  1308
			
		msapTrUsStateChanged TRAP-TYPE
			ENTERPRISE msap
			VARIABLES { msapUsTvTimeAndDate, msapUsTvIndex, msapUsTvAdminState, msapUsTvOperState }
			::=  1309
			
		msapLtmTrAutoMeasCreated TRAP-TYPE
			ENTERPRISE msap
			VARIABLES { msapLtmTvTimeAndDate, msapLtmTvIfIndex, msapLtmSltTvAutoMeasKind, msapLtmSltTvAutoMeasTimePeriod, msapLtmSltTvAutoMeasTimeWeekday, 
				msapLtmSltTvAutoMeasTimeHour, msapLtmSltTvAutoMeasThresIndex, msapLtmSltTvAutoMeasViaSplitter, msapLtmSltTvAutoMeasCheckPpa, msapLtmSltTvAutoMeasCheckRingerLoad
				 }
			::=  1310
			
		msapLtmTrAutoMeasDeleted TRAP-TYPE
			ENTERPRISE msap
			VARIABLES { msapLtmTvTimeAndDate, msapLtmTvIfIndex, msapLtmSltTvAutoMeasThresIndex }
			::=  1311
			
		msapLtmTrGetLineState TRAP-TYPE
			ENTERPRISE msap
			VARIABLES { msapLtmTvTimeAndDate, msapLtmTvIfIndex, msapLtmSltTvDmndLineType, msapLtmSltTvDmndLineState }
			::=  1312
			
		msapLtmTrPatEnabled TRAP-TYPE
			ENTERPRISE msap
			VARIABLES { msapLtmTvTimeAndDate, msapLtmTvIfIndex }
			::=  1316
			
		msapLtmTrPatDisabled TRAP-TYPE
			ENTERPRISE msap
			VARIABLES { msapLtmTvTimeAndDate, msapLtmTvIfIndex }
			::=  1317
			
		msapLtmTrMeasStart TRAP-TYPE
			ENTERPRISE msap
			VARIABLES { msapLtmTvTimeAndDate, msapLtmTvIfIndex, msapLtmSltTvDmndMeasRequest, msapLtmSltTvDmndMeasViaSplitter }
			::=  1320
			
		msapLtmTrMeasCompleted TRAP-TYPE
			ENTERPRISE msap
			VARIABLES { msapLtmTvTimeAndDate, msapLtmTvIfIndex, msapLtmSltTvDmndLineType, msapLtmSltTvDmndLineState, msapLtmSltTvDmndMeasResIndex, 
				msapLtmSltTvMeasResultStatus }
			::=  1321
			
		msapLtmTrAccessEnabled TRAP-TYPE
			ENTERPRISE msap
			VARIABLES { msapLtmTvTimeAndDate, msapLtmTvIfIndex, msapLtmSltTvAccessLineAccess, msapLtmSltTvAccessLineType, msapLtmSltTvAccessLineState
				 }
			::=  1322
			
		msapLtmTrAccessDisabled TRAP-TYPE
			ENTERPRISE msap
			VARIABLES { msapLtmTvTimeAndDate, msapLtmTvIfIndex, msapLtmSltTvAccessLineAccess, msapLtmSltTvAccessLineType, msapLtmSltTvAccessLineState
				 }
			::=  1323
			
		msapLtmTrDefaultThresLoaded TRAP-TYPE
			ENTERPRISE msap
			VARIABLES { msapLtmTvTimeAndDate, msapLtmSltTvMeasThresValIndex, msapLtmTvIfIndex }
			::=  1324
			
		msapLtmTrThresChanged TRAP-TYPE
			ENTERPRISE msap
			VARIABLES { msapLtmTvTimeAndDate, msapLtmTvIfIndex, msapLtmSltTvMeasThresValIndex }
			::=  1325
			
		msapLtmTrSendMeteringImpulsesStart TRAP-TYPE
			ENTERPRISE msap
			VARIABLES { msapLtmTvTimeAndDate, msapLtmTvIfIndex }
			::=  1326
			
		msapLtmTrSendMeteringImpulsesStop TRAP-TYPE
			ENTERPRISE msap
			VARIABLES { msapLtmTvTimeAndDate, msapLtmTvIfIndex }
			::=  1327
			
		msapLtmTrSendRingingImpulsesStart TRAP-TYPE
			ENTERPRISE msap
			VARIABLES { msapLtmTvTimeAndDate, msapLtmTvIfIndex }
			::=  1328
			
		msapLtmTrSendRingingImpulsesStop TRAP-TYPE
			ENTERPRISE msap
			VARIABLES { msapLtmTvTimeAndDate, msapLtmTvIfIndex }
			::=  1329
			
		msapLtmTrFeedNormalStart TRAP-TYPE
			ENTERPRISE msap
			VARIABLES { msapLtmTvTimeAndDate, msapLtmTvIfIndex }
			::=  1330
			
		msapLtmTrFeedNormalStop TRAP-TYPE
			ENTERPRISE msap
			VARIABLES { msapLtmTvTimeAndDate, msapLtmTvIfIndex }
			::=  1331
			
		msapLtmTrFeedReversedStart TRAP-TYPE
			ENTERPRISE msap
			VARIABLES { msapLtmTvTimeAndDate, msapLtmTvIfIndex }
			::=  1332
			
		msapLtmTrFeedReversedStop TRAP-TYPE
			ENTERPRISE msap
			VARIABLES { msapLtmTvTimeAndDate, msapLtmTvIfIndex }
			::=  1333
			
		msapLtmTrTerminalTestStart TRAP-TYPE
			ENTERPRISE msap
			VARIABLES { msapLtmTvTimeAndDate, msapLtmTvIfIndex }
			::=  1334
			
		msapLtmTrTerminalTestStop TRAP-TYPE
			ENTERPRISE msap
			VARIABLES { msapLtmTvTimeAndDate, msapLtmTvIfIndex }
			::=  1335
			
		msapLtmTrTerminalTestResults TRAP-TYPE
			ENTERPRISE msap
			VARIABLES { msapLtmTvTimeAndDate, msapLtmTvIfIndex, msapLtmMaintTvCpePotsTtLoopState, msapLtmMaintTvCpePotsTtLoopResistance, msapLtmMaintTvCpePotsTtNumberOfImpulses, 
				msapLtmMaintTvCpePotsTtImpulseDuration, msapLtmMaintTvCpePotsTtPauseDuration, msapLtmMaintTvCpePotsTtHookFlashDuration }
			::=  1336
			
		msapLtmTrTestToneOn TRAP-TYPE
			ENTERPRISE msap
			VARIABLES { msapLtmTvTimeAndDate, msapLtmTvIfIndex, msapLtmMaintTvCpeIsdnLineAccess }
			::=  1337
			
		msapLtmTrTestToneOff TRAP-TYPE
			ENTERPRISE msap
			VARIABLES { msapLtmTvTimeAndDate, msapLtmTvIfIndex }
			::=  1338
			
		msapLtmTrPortReseted TRAP-TYPE
			ENTERPRISE msap
			VARIABLES { msapLtmTvTimeAndDate, msapLtmTvIfIndex }
			::=  1339
			
		msapLtmTrInterfaceTestSignalOn TRAP-TYPE
			ENTERPRISE msap
			VARIABLES { msapLtmTvTimeAndDate, msapLtmTvIfIndex }
			::=  1340
			
		msapLtmTrInterfaceTestSignalOff TRAP-TYPE
			ENTERPRISE msap
			VARIABLES { msapLtmTvTimeAndDate, msapLtmTvIfIndex }
			::=  1341
			
		msapLtmTrLoopInterfaceOn TRAP-TYPE
			ENTERPRISE msap
			VARIABLES { msapLtmTvTimeAndDate, msapLtmTvIfIndex }
			::=  1342
			
		msapLtmTrLoopInterfaceOff TRAP-TYPE
			ENTERPRISE msap
			VARIABLES { msapLtmTvTimeAndDate, msapLtmTvIfIndex }
			::=  1343
			
		msapLtmTrLoopNtOn TRAP-TYPE
			ENTERPRISE msap
			VARIABLES { msapLtmTvTimeAndDate, msapLtmTvIfIndex, msapLtmMaintTvIsdnLoopNtMode }
			::=  1344
			
		msapLtmTrLoopNtOff TRAP-TYPE
			ENTERPRISE msap
			VARIABLES { msapLtmTvTimeAndDate, msapLtmTvIfIndex }
			::=  1345
			
		msapLtmTrForcedActivationOn TRAP-TYPE
			ENTERPRISE msap
			VARIABLES { msapLtmTvTimeAndDate, msapLtmTvIfIndex }
			::=  1346
			
		msapLtmTrForcedActivationOff TRAP-TYPE
			ENTERPRISE msap
			VARIABLES { msapLtmTvTimeAndDate, msapLtmTvIfIndex }
			::=  1347
			
		msapLtmTrBerTestOn TRAP-TYPE
			ENTERPRISE msap
			VARIABLES { msapLtmTvTimeAndDate, msapLtmTvIfIndex, msapLtmMaintTvIsdnBerStart }
			::=  1348
			
		msapLtmTrBerTestOff TRAP-TYPE
			ENTERPRISE msap
			VARIABLES { msapLtmTvTimeAndDate, msapLtmTvIfIndex }
			::=  1349
			
		msapLtmTrBerTestCompleted TRAP-TYPE
			ENTERPRISE msap
			VARIABLES { msapLtmTvTimeAndDate, msapLtmTvIfIndex, msapLtmMaintTvIsdnBerResultAvailable, msapLtmMaintTvIsdnBerResultDuration, msapLtmMaintTvIsdnBerResultErrors, 
				msapLtmMaintTvIsdnBerResultErrorRate }
			::=  1350
			
		msapLtmTrBerResult TRAP-TYPE
			ENTERPRISE msap
			VARIABLES { msapLtmTvTimeAndDate, msapLtmTvIfIndex, msapLtmMaintTvIsdnBerResultDuration, msapLtmMaintTvIsdnBerResultErrors, msapLtmMaintTvIsdnBerResultErrorRate
				 }
			::=  1351
			
		msapLtmTrDefaultGlobalsLoaded TRAP-TYPE
			ENTERPRISE msap
			VARIABLES { msapLtmTvTimeAndDate, msapLtmTvIfIndex }
			::=  1352
			
		msapTrPotsPptpChangeData TRAP-TYPE
			ENTERPRISE msap
			VARIABLES { msapTvPotsPptpIfIndex, msapTvPotsPptpTimeAndDate, msapTvPotsPptpPortData, msapTvPotsPptpChannelConnection, msapTvPotsPptpKindOfPort, 
				msapTvPotsPptpInputLevelF2, msapTvPotsPptpOutputLevelF2, msapTvPotsPptpImpedance, msapTvPotsPptpMeteringSignalType, msapTvPotsPptpFeeding, 
				msapTvPotsPptpGroundKey }
			DESCRIPTION
				"This trap is send when data of an an POTS PPTP object has been modified.
				
				The trap transmit the following attributes:
				msapTvPptpTimeAndDate, msapTvPptpPortData, 
				msapTvPptpChannelConnection, msapTvPotsPptpKindOfPort, 
				msapTvPotsPptpInputLevelF2, msapTvPotsPptpOutputLevelF2, 
				msapTvPotsPptpImpedance, msapTvPotsPptpMeteringSignalType, 
				msapTvPotsPptpFeeding, msapTvPotsPptpGroundKey, 
				msapTvPptpIfIndex"
			::=  1353
			
		msapTrIsdnPptpChangeData TRAP-TYPE
			ENTERPRISE msap
			VARIABLES { msapTvIsdnPptpIfIndex, msapTvIsdnPptpTimeAndDate, msapTvIsdnPptpPortData, msapTvIsdnPptpChannelConnection, msapTvIsdnPptpFeeding, 
				msapTvIsdnPptp1Tr6Conversion, msapTvIsdnPptpB1Service, msapTvIsdnPptpB1Loop, msapTvIsdnPptpB2Service, msapTvIsdnPptpB2Loop, 
				msapTvIsdnPptpDService, msapTvIsdnPptpDLoop, msapTvIsdnPptpAutoact, msapTvIsdnPptpEnablePfReset }
			DESCRIPTION
				"This trap is send when data of an an ISDN PPTP object has been modified.
				
				The trap transmit the following attributes:
				msapTvPptpTimeAndDate, msapTvPptpPortData, 
				msapTvPptpChannelConnection, msapTvIsdnPptpFeeding, 
				msapTvIsdnPptp1TR6Conversion, msapTvIsdnPptpB1Loop, 
				msapTvIsdnPptpB2Loop, msapTvIsdnPptpDLoop, 
				msapTvIsdnPptpAutoact, msapTvIsdnPptpEnablePFReset,  
				msapTvPptpIfIndex"
			::=  1354
			
		msapTrIsdnPptpEocSend TRAP-TYPE
			ENTERPRISE msap
			VARIABLES { msapTvIsdnPptpTimeAndDate, msapTvIsdnPptpEocSend, msapTvIsdnPptpIfIndex }
			DESCRIPTION
				"This trap is send when EOC data of an an ISDN PPTP object has been sent.
				
				The trap transmit the following attributes:
				msapTvPptpIfIndex, msapTvIsdnPptpTimeAndDate
				msapTvIsdnPptpEocSend"
			::=  1355
			
		msapTrIsdnPptpEocRecReset TRAP-TYPE
			ENTERPRISE msap
			VARIABLES { msapTvIsdnPptpTimeAndDate, msapTvIsdnPptpIfIndex }
			DESCRIPTION
				"This trap is send when EOCRec of an an ISDN PPTP object has been reset.
				
				The trap transmit the following attributes:
				msapTvPptpIfIndex, msapTvIsdnPptpTimeAndDate"
			::=  1356
			
	
	END

--
-- MSAP-MIB.my
--
