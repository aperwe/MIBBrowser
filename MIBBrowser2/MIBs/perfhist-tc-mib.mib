PerfHist-TC-MIB DEFINITIONS ::= BEGIN

IMPORTS
   MODULE-IDENTITY,
   Gauge32, experimental
       FROM SNMPv2-SMI
   TEXTUAL-CONVENTION
       FROM SNMPv2-TC
   mib-2
       FROM RFC1213-MIB;


perfHistTCMIB MODULE-IDENTITY
     LAST-UPDATED "9610241100Z"
     ORGANIZATION "IETF AToMMIB and TrunkMIB WGs"
     CONTACT-INFO
                  "Kaj Tesink
         Postal:  Bell Communications Research
                  331 Newman Springs Road
                  Red Bank, NJ 07701
                  USA
         Tel:     +1 908 758 5254
         Fax:     +1 908 758 4177
         E-mail:  kaj@cc.bellcore.com"
     DESCRIPTION
      "This MIB Module provides Textual Conventions
        to be used by systems supporting 15 minute
        based performance history counts."
     ::= { mib-2 5555 }

               -- ****************************************
               -- * Note to RFC editor                   *
               -- * Assign a number for xxx              *
               -- * from IANA when publishing this       *
               -- * MIB as RFC                           *
               -- ****************************************



-- The Textual Conventions defined below are organized
-- alphabetically

-- Use of these TCs assumes the following:

-- 0  The agent supports 15 minute based history
--    counters.
-- 0  The agent is capable of keeping a history of n
--    intervals of 15 minute performance data. The
--    value of n is defined by the media-specific MIB
--    module but shall be 0 < n =< 96.
-- 0  The agent may optionally support performance
--    data aggregating the history intervals.
-- 0  The agent will keep separate tables for the
--    current interval, the history intervals, and
--    the total aggregates.
-- 0  The agent will keep the following objects per
--    interface:
--
-- xyzTimeElapsed OBJECT-TYPE
--       SYNTAX  INTEGER (0..899)
--       MAX-ACCESS  read-only
--       STATUS  current
--       DESCRIPTION
--       "The number of seconds that have elapsed since
--       the beginning of the current error-measurement
--       period."
--       ::= { xxx }

-- xyzValidIntervals OBJECT-TYPE
--       SYNTAX  INTEGER (0..<n>)
--         1 =< n =< 96
--       MAX-ACCESS  read-only
--       STATUS  current
--       DESCRIPTION
--       "The number of previous near end intervals
--       for which valid data was collected.  The value
--       will be <n> unless the interface was brought
--       online within the last 24 hours, in which case
--       the value will be the number of complete 15
--       minute near end intervals since the interface
--       has been online.  In the case where the agent
--       is a proxy, it is possible that some intervals
--       are unavailable.  In this case, this
--       interval is the maximum interval number for
--       which valid data is available."
--       ::= { xxx }

-- xyzInvalidIntervals OBJECT-TYPE
--     SYNTAX  INTEGER (0..<n>)
--     MAX-ACCESS  read-only
--     STATUS  current
--     DESCRIPTION
--       "The number of intervals for which no valid
--       data is available."
--       ::= { xxx }

PerfCurrentCount ::= TEXTUAL-CONVENTION
      STATUS  current
      DESCRIPTION
         "A counter associated with interface
          performance measurements in a current 15
          minute measurement interval. The value
          of this counter start from zero and is
          increased when associated events occur,
          until the end of the 15 minute interval.
          At that time the value of the counter is
          stored in the first 15 minute history
          interval, and the CurrentCount is
          restarted at zero."
       SYNTAX  Gauge32

PerfIntervalCount ::= TEXTUAL-CONVENTION
      STATUS  current
      DESCRIPTION
         "A counter associated with interface
          performance measurements in a previous
          15 minute measurement interval. In the
          case where the agent has no valid data
          available for a particular interval the
          corresponding object instance is not
          available and upon a retrieval request
          a corresponding error message (noSuch*)
          shall be returned. In a system supporting
          a history of n intervals with
          IntervalCount(1) and IntervalCount(n) the
          most and least recent intervals
          respectively, the following applies at
          the end of a 15 minute interval:
          - discard the value of IntervalCount(n)
          - the value of IntervalCount(i) becomes that
            of IntervalCount(i-1) for n >= i > 1
          - the value of IntervalCount(1) becomes that
            of CurrentCount
          - the TotalCount, if supported, is adjusted."
       SYNTAX  Gauge32

PerfTotalCount ::= TEXTUAL-CONVENTION
      STATUS  current
      DESCRIPTION
         "A counter associated with interface
          performance measurements agggregating the
          previous valid 15 minute measurement
          intervals. Intervals for which no valid
          data was available are counted as 0."
       SYNTAX  Gauge32

END
