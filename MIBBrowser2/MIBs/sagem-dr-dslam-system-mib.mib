--
-- SAGEM-DR-DSLAM-SYSTEM.MIB
-- MIB generated by MG-SOFT Visual MIB Builder Version 2.1 Build 199
-- Friday, April 27, 2001 at 15:19:33
--

	SAGEM-DR-DSLAM-SYSTEM-MIB DEFINITIONS ::= BEGIN

		IMPORTS 
			dslam			
				FROM SAGEM-DR-DSLAM-MIB			
			SagemString100, SagemString, SagemTFTPFileNameString, SagemUnsigned16, SagemUnsigned8, 
			SagemInteger8, SagemBoolean			
				FROM SAGEM-DR-TC			
			IpAddress, OBJECT-TYPE, MODULE-IDENTITY, NOTIFICATION-TYPE			
				FROM SNMPv2-SMI			
			MacAddress, PhysAddress			
				FROM SNMPv2-TC;
	
	
		dslam-system MODULE-IDENTITY
			LAST-UPDATED "190009271126Z"
			ORGANIZATION
				"Sagem-DR"
			CONTACT-INFO
				"Sagem-DR"
			DESCRIPTION
				"This module handles miscellaneous parameters related to the equipment :
				- General parameters
				- Passwords
				- Synchronization
				- General commands
				- SNMP settings
				- Teleload"
			::= { dslam 1 }
		
	
	
	
--
-- Node definitions
--
	
		summary OBJECT IDENTIFIER ::= { dslam-system 1 }
		
		sumEquipmentName OBJECT-TYPE
			SYNTAX SagemString100
			MAX-ACCESS read-only
			STATUS current
			DESCRIPTION
				"Name of the equipment"
			::= { summary 1 }
		
		sumRAMSize OBJECT-TYPE
			SYNTAX SagemString100
			MAX-ACCESS read-only
			STATUS current
			DESCRIPTION
				"Size of the RAM"
			::= { summary 4 }
		
		sumFlashSize OBJECT-TYPE
			SYNTAX SagemString100
			MAX-ACCESS read-only
			STATUS current
			DESCRIPTION
				"Size of the flash memory"
			::= { summary 5 }
		
		general OBJECT IDENTIFIER ::= { dslam-system 2 }
		
		genSystemDescriptionProviderName OBJECT-TYPE
			SYNTAX SagemString100
			MAX-ACCESS read-only
			STATUS current
			DESCRIPTION
				"Description of the equipment (name given by the provider)"
			::= { general 1 }
		
		genSystemNameProviderName OBJECT-TYPE
			SYNTAX SagemString100
			MAX-ACCESS read-write
			STATUS current
			DESCRIPTION
				"Name of the equipment given by the user 
				company (name given by the provider)"
			::= { general 2 }
		
		genSystemLocationProviderName OBJECT-TYPE
			SYNTAX SagemString100
			MAX-ACCESS read-write
			STATUS current
			DESCRIPTION
				"Location of the equipment (name given
				by the provider)"
			::= { general 3 }
		
		genSystemContactProviderName OBJECT-TYPE
			SYNTAX SagemString100
			MAX-ACCESS read-write
			STATUS current
			DESCRIPTION
				"Contact for user company (name given
				by the provider)"
			::= { general 4 }
		
		genCurrentYear OBJECT-TYPE
			SYNTAX SagemUnsigned16
			MAX-ACCESS read-write
			STATUS current
			DESCRIPTION
				"Current date year"
			::= { general 5 }
		
		genCurrentMonth OBJECT-TYPE
			SYNTAX SagemUnsigned8
			MAX-ACCESS read-write
			STATUS current
			DESCRIPTION
				"Current date month"
			::= { general 6 }
		
		genCurrentDay OBJECT-TYPE
			SYNTAX SagemUnsigned8
			MAX-ACCESS read-write
			STATUS current
			DESCRIPTION
				"Current date day"
			::= { general 7 }
		
		genCurrentHour OBJECT-TYPE
			SYNTAX SagemUnsigned8
			MAX-ACCESS read-write
			STATUS current
			DESCRIPTION
				"Current date hour"
			::= { general 8 }
		
		genCurrentMinute OBJECT-TYPE
			SYNTAX SagemUnsigned8
			MAX-ACCESS read-write
			STATUS current
			DESCRIPTION
				"Current date minute"
			::= { general 9 }
		
		genCurrentSecond OBJECT-TYPE
			SYNTAX SagemUnsigned8
			MAX-ACCESS read-write
			STATUS current
			DESCRIPTION
				"Current date second"
			::= { general 10 }
		
		genNetworkNodeID OBJECT-TYPE
			SYNTAX IpAddress
			MAX-ACCESS read-write
			STATUS current
			DESCRIPTION
				"Network Node ID or router ID for unnumbered links"
			::= { general 11 }
		
		genSubNetMask OBJECT-TYPE
			SYNTAX IpAddress
			MAX-ACCESS read-write
			STATUS current
			DESCRIPTION
				"Sub Network Mask"
			::= { general 12 }
		
		genGatewayAdd OBJECT-TYPE
			SYNTAX IpAddress
			MAX-ACCESS read-write
			STATUS current
			DESCRIPTION
				"Gateway address"
			::= { general 13 }
		
		genMacAddress OBJECT-TYPE
			SYNTAX MacAddress
			MAX-ACCESS read-write
			STATUS current
			DESCRIPTION
				"MAC address"
			::= { general 14 }
		
		genAtmAddress OBJECT-TYPE
			SYNTAX PhysAddress
			MAX-ACCESS read-write
			STATUS current
			DESCRIPTION
				"ATM address"
			::= { general 15 }
		
		genAction OBJECT-TYPE
			SYNTAX INTEGER
				{
				create(0),
				modify(1),
				delete(2)
				}
			MAX-ACCESS read-write
			STATUS current
			DESCRIPTION
				"0 = Create
				1 = Modify
				2 = Delete"
			::= { general 16 }
		
		users OBJECT IDENTIFIER ::= { dslam-system 3 }
		
		profilesMax OBJECT-TYPE
			SYNTAX SagemUnsigned16
			MAX-ACCESS read-only
			STATUS current
			DESCRIPTION
				"The maximum number of profiles the equipment can support"
			::= { users 1 }
		
		profileTable OBJECT-TYPE
			SYNTAX SEQUENCE OF ProfileEntry
			MAX-ACCESS not-accessible
			STATUS current
			DESCRIPTION
				"A list of access profiles"
			::= { users 2 }
		
		profileEntry OBJECT-TYPE
			SYNTAX ProfileEntry
			MAX-ACCESS not-accessible
			STATUS current
			DESCRIPTION
				"A single entry in the profileTable"
			INDEX { profileIndex }
			::= { profileTable 1 }
		
		ProfileEntry ::=
			SEQUENCE { 
				profileIndex
					SagemUnsigned16,
				profileName
					SagemString,
				profilePassword
					SagemString,
				profileAllowedClients
					SagemInteger8,
				profileAction
					INTEGER
			 }

		profileIndex OBJECT-TYPE
			SYNTAX SagemUnsigned16
			MAX-ACCESS read-only
			STATUS current
			DESCRIPTION
				"Index for profileTable (FFFF means 'not valid')"
			::= { profileEntry 1 }
		
		profileName OBJECT-TYPE
			SYNTAX SagemString
			MAX-ACCESS read-write
			STATUS current
			DESCRIPTION
				"Profile name"
			::= { profileEntry 2 }
		
		profilePassword OBJECT-TYPE
			SYNTAX SagemString
			MAX-ACCESS read-write
			STATUS current
			DESCRIPTION
				"Password associated to profile"
			::= { profileEntry 3 }
		
		profileAllowedClients OBJECT-TYPE
			SYNTAX SagemInteger8
			MAX-ACCESS read-write
			STATUS current
			DESCRIPTION
				"Allowed clients"
			::= { profileEntry 4 }
		
		profileAction OBJECT-TYPE
			SYNTAX INTEGER
				{
				create(0),
				modify(1),
				delete(2)
				}
			MAX-ACCESS read-write
			STATUS current
			DESCRIPTION
				"0 = Create
				1 = Modify
				2 = Delete"
			::= { profileEntry 5 }
		
		commands OBJECT IDENTIFIER ::= { dslam-system 4 }
		
		sysLoadDefaultConfig OBJECT-TYPE
			SYNTAX SagemBoolean
			MAX-ACCESS read-write
			STATUS current
			DESCRIPTION
				"Set to load default configuration"
			::= { commands 1 }
		
		sysSaveToFlashFlag OBJECT-TYPE
			SYNTAX SagemBoolean
			MAX-ACCESS read-write
			STATUS current
			DESCRIPTION
				"Set to save to flash"
			::= { commands 2 }
		
		sysRunCmtSoftFlag OBJECT-TYPE
			SYNTAX SagemString
			MAX-ACCESS read-write
			STATUS current
			DESCRIPTION
				"Set to run new cmt version of software"
			::= { commands 3 }
		
		sysRunDslSoftFlag OBJECT-TYPE
			SYNTAX SagemString
			MAX-ACCESS read-write
			STATUS current
			DESCRIPTION
				"Set to run new dsl version of software"
			::= { commands 4 }
		
		sysRunFlashConfigFlag OBJECT-TYPE
			SYNTAX SagemBoolean
			MAX-ACCESS read-write
			STATUS current
			DESCRIPTION
				"Set to run flash config file"
			::= { commands 5 }
		
		sysSaveSerialFlashFlag OBJECT-TYPE
			SYNTAX SagemString
			MAX-ACCESS read-write
			STATUS current
			DESCRIPTION
				"Save config to serial flash"
			::= { commands 6 }
		
		sysLoadSerialFlashFlag OBJECT-TYPE
			SYNTAX SagemString
			MAX-ACCESS read-write
			STATUS current
			DESCRIPTION
				"Load config from serial flash"
			::= { commands 7 }
		
		sysRebootFlag OBJECT-TYPE
			SYNTAX SagemBoolean
			MAX-ACCESS read-write
			STATUS current
			DESCRIPTION
				"Set to reboot equipment"
			::= { commands 8 }
		
		sysUpdateSoftOptions OBJECT-TYPE
			SYNTAX SagemBoolean
			MAX-ACCESS read-write
			STATUS current
			DESCRIPTION
				"Set to update software options"
			::= { commands 9 }
		
		system-snmp OBJECT IDENTIFIER ::= { dslam-system 5 }
		
		snmpManagersMax OBJECT-TYPE
			SYNTAX SagemUnsigned16
			MAX-ACCESS read-only
			STATUS current
			DESCRIPTION
				"The maximum number of managers the equipment can support"
			::= { system-snmp 1 }
		
		snmpManagerTable OBJECT-TYPE
			SYNTAX SEQUENCE OF SnmpManagerEntry
			MAX-ACCESS not-accessible
			STATUS current
			DESCRIPTION
				"A list of SNMP managers "
			::= { system-snmp 2 }
		
		snmpManagerEntry OBJECT-TYPE
			SYNTAX SnmpManagerEntry
			MAX-ACCESS not-accessible
			STATUS current
			DESCRIPTION
				"A single entry in the table of the SNMP managers"
			INDEX { snmpManagerIndex }
			::= { snmpManagerTable 1 }
		
		SnmpManagerEntry ::=
			SEQUENCE { 
				snmpManagerIndex
					SagemUnsigned16,
				snmpManagerDslamAddress
					IpAddress,
				snmpManagerAction
					INTEGER
			 }

		snmpManagerIndex OBJECT-TYPE
			SYNTAX SagemUnsigned16
			MAX-ACCESS read-only
			STATUS current
			DESCRIPTION
				"Index for snmpManagerTable (FFFF means 'not valid')"
			::= { snmpManagerEntry 1 }
		
		snmpManagerDslamAddress OBJECT-TYPE
			SYNTAX IpAddress
			MAX-ACCESS read-write
			STATUS current
			DESCRIPTION
				"IP address of the manager"
			::= { snmpManagerEntry 2 }
		
		snmpManagerAction OBJECT-TYPE
			SYNTAX INTEGER
				{
				create(0),
				modify(1),
				delete(2)
				}
			MAX-ACCESS read-write
			STATUS current
			DESCRIPTION
				"0 = Create
				1 = Modify
				2 = Delete"
			::= { snmpManagerEntry 3 }
		
		snmpMngrTrapsMax OBJECT-TYPE
			SYNTAX SagemUnsigned16
			MAX-ACCESS read-only
			STATUS current
			DESCRIPTION
				"The maximum number of traps the equipment can support"
			::= { system-snmp 3 }
		
		snmpMngrTrapTable OBJECT-TYPE
			SYNTAX SEQUENCE OF SnmpMngrTrapEntry
			MAX-ACCESS not-accessible
			STATUS current
			DESCRIPTION
				"A list of SNMP manager traps"
			::= { system-snmp 4 }
		
		snmpMngrTrapEntry OBJECT-TYPE
			SYNTAX SnmpMngrTrapEntry
			MAX-ACCESS not-accessible
			STATUS current
			DESCRIPTION
				"A single entry in the table of the traps"
			INDEX { snmpMngrTrapIndex }
			::= { snmpMngrTrapTable 1 }
		
		SnmpMngrTrapEntry ::=
			SEQUENCE { 
				snmpMngrTrapIndex
					SagemUnsigned16,
				snmpMngrTrapDslamAddress
					IpAddress,
				snmpMngrTrapSendFlag
					INTEGER,
				snmpMngrTrapSnmpVersion
					INTEGER,
				snmpMngrTrapCommunity
					SagemString,
				snmpMngrTrapAction
					INTEGER
			 }

		snmpMngrTrapIndex OBJECT-TYPE
			SYNTAX SagemUnsigned16
			MAX-ACCESS read-only
			STATUS current
			DESCRIPTION
				"Index for snmpMngrTrapTable (FFFF means 'not valid')"
			::= { snmpMngrTrapEntry 1 }
		
		snmpMngrTrapDslamAddress OBJECT-TYPE
			SYNTAX IpAddress
			MAX-ACCESS read-write
			STATUS current
			DESCRIPTION
				"IP address of the host which receives the trap"
			::= { snmpMngrTrapEntry 2 }
		
		snmpMngrTrapSendFlag OBJECT-TYPE
			SYNTAX INTEGER
				{
				no(0),
				yes(1)
				}
			MAX-ACCESS read-write
			STATUS current
			DESCRIPTION
				"Enables, disables traps"
			::= { snmpMngrTrapEntry 3 }
		
		snmpMngrTrapSnmpVersion OBJECT-TYPE
			SYNTAX INTEGER
				{
				snmpv1(0),
				snmpv2(1)
				}
			MAX-ACCESS read-write
			STATUS current
			DESCRIPTION
				"SNMP version used"
			::= { snmpMngrTrapEntry 4 }
		
		snmpMngrTrapCommunity OBJECT-TYPE
			SYNTAX SagemString
			MAX-ACCESS read-write
			STATUS current
			DESCRIPTION
				"Traps community"
			::= { snmpMngrTrapEntry 5 }
		
		snmpMngrTrapAction OBJECT-TYPE
			SYNTAX INTEGER
				{
				create(0),
				modify(1),
				delete(2)
				}
			MAX-ACCESS read-write
			STATUS current
			DESCRIPTION
				"0 = Create
				1 = Modify
				2 = Delete"
			::= { snmpMngrTrapEntry 6 }
		
		snmpSendTestTrap OBJECT-TYPE
			SYNTAX SagemBoolean
			MAX-ACCESS read-write
			STATUS current
			DESCRIPTION
				"Set to generate a Test Trap"
			::= { system-snmp 5 }
		
		teleload OBJECT IDENTIFIER ::= { dslam-system 6 }
		
		configurationfile OBJECT IDENTIFIER ::= { teleload 1 }
		
		cfgDownloadTFTPServer OBJECT-TYPE
			SYNTAX IpAddress
			MAX-ACCESS read-write
			STATUS current
			DESCRIPTION
				"TFTP Server IP address for configuration file downloading"
			::= { configurationfile 1 }
		
		cfgDownloadFile OBJECT-TYPE
			SYNTAX SagemTFTPFileNameString
			MAX-ACCESS read-write
			STATUS current
			DESCRIPTION
				"Name of the file to download"
			::= { configurationfile 2 }
		
		cfgDownloadStartFlag OBJECT-TYPE
			SYNTAX SagemBoolean
			MAX-ACCESS read-write
			STATUS current
			DESCRIPTION
				"Set to download the configuration file into the equipment"
			::= { configurationfile 3 }
		
		cfgUploadStartFlag OBJECT-TYPE
			SYNTAX SagemBoolean
			MAX-ACCESS read-write
			STATUS current
			DESCRIPTION
				"Set to upload the configuration file from the equipment"
			::= { configurationfile 4 }
		
		softwarefile OBJECT IDENTIFIER ::= { teleload 2 }
		
		sftDowloadTFTPServer OBJECT-TYPE
			SYNTAX IpAddress
			MAX-ACCESS read-write
			STATUS current
			DESCRIPTION
				"TFTP Server IP address for software file downloading"
			::= { softwarefile 1 }
		
		sftDownloadCmtFile OBJECT-TYPE
			SYNTAX SagemTFTPFileNameString
			MAX-ACCESS read-write
			STATUS current
			DESCRIPTION
				"Name of the CMT software file to download"
			::= { softwarefile 2 }
		
		sftDownloadCmtStartFlag OBJECT-TYPE
			SYNTAX SagemBoolean
			MAX-ACCESS read-write
			STATUS current
			DESCRIPTION
				"Set to download the CMT software file into the equipment"
			::= { softwarefile 3 }
		
		sftDownloadAdslFile OBJECT-TYPE
			SYNTAX SagemTFTPFileNameString
			MAX-ACCESS read-write
			STATUS current
			DESCRIPTION
				"Name of the ADSL software file to download"
			::= { softwarefile 4 }
		
		sftDownloadAdslStartFlag OBJECT-TYPE
			SYNTAX SagemBoolean
			MAX-ACCESS read-write
			STATUS current
			DESCRIPTION
				"Set to download the ADSL software file into the equipment"
			::= { softwarefile 5 }
		
		traps OBJECT IDENTIFIER ::= { dslam-system 7 }
		
		trapTestTrap NOTIFICATION-TYPE
			OBJECTS { sumEquipmentName }
			STATUS current
			DESCRIPTION
				"Test Trap (Set snmpSendTestTrap to generate it)"
			::= { traps 1 }
		
		trapLogTrap NOTIFICATION-TYPE
			OBJECTS { trapLogDate, trapLogObject, trapLogEvent, trapLogSeverity, trapLogName
				 }
			STATUS current
			DESCRIPTION
				"Log Trap"
			::= { traps 3 }
		
		trapLogIndex OBJECT-TYPE
			SYNTAX INTEGER
			MAX-ACCESS read-only
			STATUS current
			DESCRIPTION
				"A unique value which identify a particular log entry.
				The index value cannot exced logCapacity and then returns to zero
				when the number of events exceds the capacity of equipement log table.
				Its value is :
				logIndex = <total number of event>%logCapacity.
				It is mandatory for the equipment to respond to get-next in
				anti-chronological order (youngest first) no matter to the index value.
				Get-next(LogEntry.logEntry) is logEntry.logIndex[logLastEvent]"
			::= { traps 4 }
		
		trapLogDate OBJECT-TYPE
			SYNTAX SagemString
			MAX-ACCESS read-only
			STATUS current
			DESCRIPTION
				"When the event had happened."
			::= { traps 5 }
		
		trapLogObject OBJECT-TYPE
			SYNTAX SagemString
			MAX-ACCESS read-only
			STATUS current
			DESCRIPTION
				"A reference to the function/interface who produced the event"
			::= { traps 6 }
		
		trapLogEvent OBJECT-TYPE
			SYNTAX INTEGER
				{
				alarmOn(1),
				alarmOff(2),
				event(3)
				}
			MAX-ACCESS read-only
			STATUS current
			DESCRIPTION
				"indicates the type of event which had occured."
			::= { traps 7 }
		
		trapLogSeverity OBJECT-TYPE
			SYNTAX INTEGER
				{
				major(1),
				minor(2),
				none(3)
				}
			MAX-ACCESS read-only
			STATUS current
			DESCRIPTION
				"Alarm severity"
			::= { traps 8 }
		
		trapLogName OBJECT-TYPE
			SYNTAX OCTET STRING
			MAX-ACCESS read-only
			STATUS current
			DESCRIPTION
				"A text string which identifies the particular entry among the log entries."
			::= { traps 9 }
		
	
	END

--
-- SAGEM-DR-DSLAM-SYSTEM.MIB
--
