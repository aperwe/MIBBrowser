---------------------------------------------------------
-- SAGEM-DR-TC.mib
-- MIB generated by MG-SOFT Visual MIB Builder Version 1.5 Build 103
-- Thursday, August 24, 2000 at 17:11:00
---------------------------------------------------------

	SAGEM-DR-TC DEFINITIONS ::= BEGIN

		IMPORTS 
			DisplayString, TEXTUAL-CONVENTION			
				FROM SNMPv2-TC;
	
	
--
-- Type definitions
--
	
		SagemBoolean ::= INTEGER
			{
			true(1),
			false(2)
			}
		
		SagemInteger8 ::= INTEGER (-128..127)
		
		SagemInteger16 ::= INTEGER (-32768..32767)
		
		SagemUnsigned8 ::= INTEGER (0..255)
		
		SagemUnsigned16 ::= INTEGER (0..65535)
		
	
--
-- Textual conventions
--

-- NF
	SagemBoolean ::= TEXTUAL-CONVENTION
    		STATUS       current
    	DESCRIPTION
            "Represents a boolean value."
        SYNTAX       INTEGER { true(1), false(2) }


	SagemUnsigned16 ::= TEXTUAL-CONVENTION
                STATUS current
                DESCRIPTION
                  "Textual convention for a 16 bit integer value. "
                SYNTAX INTEGER (0..65535)	

	SagemUnsigned8 ::= TEXTUAL-CONVENTION
                STATUS current
                DESCRIPTION
                  "Textual convention for a 8 bit integer value. "
                SYNTAX INTEGER (0..255)	

	SagemInteger16 ::= TEXTUAL-CONVENTION
                STATUS current
                DESCRIPTION
                  "Textual convention for a 16 bit integer value. "
                SYNTAX INTEGER (-32768..32767)	

	SagemInteger8 ::= TEXTUAL-CONVENTION
                STATUS current
                DESCRIPTION
                  "Textual convention for a 8 bit integer value. "
                SYNTAX INTEGER (-128..127)	


		SagemString ::= TEXTUAL-CONVENTION
			DISPLAY-HINT
				"20a"
			STATUS current
			DESCRIPTION
				"String defined for Sagem's use (20 characters)"
			SYNTAX DisplayString (SIZE (0..19))
			
		SagemString100 ::= TEXTUAL-CONVENTION
			DISPLAY-HINT
				"100a"
			STATUS current
			DESCRIPTION
				"String defined for Sagem's use (100 characters)"
			SYNTAX DisplayString (SIZE (0..99))
			
		SagemTFTPFileNameString ::= TEXTUAL-CONVENTION
			DISPLAY-HINT
				"100a"
			STATUS current
			DESCRIPTION
				"String defined for Sagem's use (100 characters)"
			SYNTAX DisplayString (SIZE (0..99))
			
	
	END

-----------------------------------------------
-- SAGEM-DR-TC.mib
-----------------------------------------------
