ISAR-MIB DEFINITIONS ::= BEGIN


-- 
-- ORGANIZATION : SIEMENS AG
-- 
-- PRODUCT : IAD4700 V2.0
-- 
-- LAST-UPDATED : Tue Nov  7 09:55:01 MET 2000

-- 
-- IAD4700 V1.0 : system definitions
--                interfaces
--                ds1, ds0bundle, ds0channel
--                LAN port
--                HSSI port
--                HDLC logical port
--                ethernet like interface
--                bridge
--                speech processor
--                ATM
--                tracing
--                IMA
--                OAM
--                services
--                interworking functions
--                CES / THDLCS / FRS / LANIS / SIGNALLINGS
--                alarm handling
--                inband IP
--                power on self test
--                TFTP
-- 
-- IAD4700 V1.1 : STM1
-- 
--
-- IAD4700 V2.0 : S0
--                CCC
--                VCS
-- 
--                VoDsl (step 1a)
-- 
-- 




-- This file contains all the MIB definitions (except the one
-- from RFC 1213) for IAD4700.
-- The MIB defined in RFC 1213 is not included in this file because
-- it is already present in the SNMP agent.


IMPORTS
	mib-2, DisplayString, ifIndex, ifEntry, ifAdminStatus,
	transmission
		FROM RFC1213-MIB
				
	Counter, Gauge, TimeTicks, private, IpAddress
		FROM RFC1155-SMI;


enterprises      OBJECT IDENTIFIER ::= { private  1 }
sni              OBJECT IDENTIFIER ::= { enterprises  231 }
siemensUnits     OBJECT IDENTIFIER ::= { sni  7 }
oenProductMibs   OBJECT IDENTIFIER ::= { siemensUnits  1 }
bn               OBJECT IDENTIFIER ::= { oenProductMibs  5 }
atmAccess        OBJECT IDENTIFIER ::= { bn  2 }
isar             OBJECT IDENTIFIER ::= { atmAccess  1 }

isarIsystemMIBObjects            OBJECT IDENTIFIER ::= { isar  1 }
isarIifMIBObjects                OBJECT IDENTIFIER ::= { isar  2 }
isarIsnmpMIBObjects              OBJECT IDENTIFIER ::= { isar  3 }
isarIds0ChannelMIBObjects        OBJECT IDENTIFIER ::= { isar  4 }
isarIds0BundleMIBObjects         OBJECT IDENTIFIER ::= { isar  5 }
isarIds1MIBObjects               OBJECT IDENTIFIER ::= { isar  6 }
isarIlanPortMIBObjects           OBJECT IDENTIFIER ::= { isar  7 }
isarIhssiPortMIBObjects          OBJECT IDENTIFIER ::= { isar  8 }
isarIfrnetservMIBObjects         OBJECT IDENTIFIER ::= { isar  9 }
isarIatmfCESMIBObjects           OBJECT IDENTIFIER ::= { isar  10 }
isarIatmfImaMIBObjects           OBJECT IDENTIFIER ::= { isar  11 }
isarIoamMIBObjects               OBJECT IDENTIFIER ::= { isar  12 }
isarIatmMIBObjects               OBJECT IDENTIFIER ::= { isar  13 }
isarIdot1dBridgeMIBObjects       OBJECT IDENTIFIER ::= { isar  14 }
isarIserviceMIBObjects           OBJECT IDENTIFIER ::= { isar  15 }
isarIlanisMIBObjects             OBJECT IDENTIFIER ::= { isar  16 }
isarIthdlcsMIBObjects            OBJECT IDENTIFIER ::= { isar  17 }
isarItraceHandlerMIBObjects      OBJECT IDENTIFIER ::= { isar  18 }
isarIalarmLogMIBObjects          OBJECT IDENTIFIER ::= { isar  19 }
isarIspeechProcessorMIBObjects   OBJECT IDENTIFIER ::= { isar  20 }
isarIhdlcLogPortMIBObjects       OBJECT IDENTIFIER ::= { isar  21 }
isarIvcsMIBObjects               OBJECT IDENTIFIER ::= { isar  22 }
isarIfrAtmIwfMIBObjects          OBJECT IDENTIFIER ::= { isar  23 }
isarIiwfMIBObjects               OBJECT IDENTIFIER ::= { isar  24 }
isarIpowerOnSTMIBObjects         OBJECT IDENTIFIER ::= { isar  25 }
isarIhdlcStatisticsMIBObjects    OBJECT IDENTIFIER ::= { isar  26 }
isarItftpMIBObjects              OBJECT IDENTIFIER ::= { isar  27 }
isarIinbandIpMIBObjects          OBJECT IDENTIFIER ::= { isar  28 }
isarIsignallingMIBObjects        OBJECT IDENTIFIER ::= { isar  29 }
isarIdebugMIBObjects             OBJECT IDENTIFIER ::= { isar  30 }
isarItimeMIBObjects              OBJECT IDENTIFIER ::= { isar  31 }
isarIsonetMIBObjects             OBJECT IDENTIFIER ::= { isar  32 }
isarIs0MIBObjects                OBJECT IDENTIFIER ::= { isar  33 }
isarIcccMIBObjects               OBJECT IDENTIFIER ::= { isar  34 }
-- reserved for merge with RAPM-branch
-- isarIrapmMIBObjects              OBJECT IDENTIFIER ::= { isar  35 }
isarIsdslMIBObjects              OBJECT IDENTIFIER ::= { isar  36 }
-- reserved for RAPM
-- isarIaltAlarmLogMIBObjects       OBJECT IDENTIFIER ::= { isar  37 }

isarInullObjectIdentifier        OBJECT IDENTIFIER ::= { 0 0 }

-- !!!!!!!!!!!!!!!!!!!!!!!!!!!!!!!!!!!!!!!!!!!!!!!!!!!!!!!!!!!!!!!
-- overwrite of ifType defined in rfc1213 by IANAifType found in
-- http://ftp.isi.edu/mib/ianaiftype.mib
-- based on : LAST-UPDATED 9910081430Z   October 8, 1999
-- !!!!!!!!!!!!!!!!!!!!!!!!!!!!!!!!!!!!!!!!!!!!!!!!!!!!!!!!!!!!!!!
--
--   IANAifType ::= TEXTUAL-CONVENTION
--       STATUS       current
--       DESCRIPTION
--              "This data type is used as the syntax of the ifType
--               object in the (updated) definition of MIB-II's
--               ifTable.
--
--               The definition of this textual convention with the
--               addition of newly assigned values is published
--               periodically by the IANA, in either the Assigned
--               Numbers RFC, or some derivative of it specific to
--               Internet Network Management number assignments.  (The
--               latest arrangements can be obtained by contacting the
--               IANA.)
--
--               Requests for new values should be made to IANA via
--               email (iana@iana.org).
--
--               The relationship between the assignment of ifType
--               values and of OIDs to particular media-specific MIBs
--               is solely the purview of IANA and is subject to change
--               without notice.  Quite often, a media-specific MIB's
--               OID-subtree assignment within MIB-II's 'transmission'
--               subtree will be the same as its ifType value.
--               However, in some circumstances this will not be the
--               case, and implementors must not pre-assume any
--               specific relationship between ifType values and
--               transmission subtree OIDs."


ifType OBJECT-TYPE
    SYNTAX  INTEGER {
                other(1),          -- none of the following
                regular1822(2),
                hdh1822(3),
                ddnX25(4),
                rfc877x25(5),
                ethernetCsmacd(6),
                iso88023Csmacd(7),
                iso88024TokenBus(8),
                iso88025TokenRing(9),
                iso88026Man(10),
                starLan(11),
                proteon10Mbit(12),
                proteon80Mbit(13),
                hyperchannel(14),
                fddi(15),
                lapb(16),
                sdlc(17),
                ds1(18),            -- DS1-MIB
                e1(19),             -- Obsolete see DS1-MIB
                basicISDN(20),
                primaryISDN(21),
                propPointToPointSerial(22), -- proprietary serial
                ppp(23),
                softwareLoopback(24),
                eon(25),            -- CLNP over IP 
                ethernet3Mbit(26),
                nsip(27),           -- XNS over IP
                slip(28),           -- generic SLIP
                ultra(29),          -- ULTRA technologies
                ds3(30),            -- DS3-MIB
                sip(31),            -- SMDS, coffee
                frameRelay(32),     -- DTE only. 
                rs232(33),
                para(34),           -- parallel-port
                arcnet(35),         -- arcnet
                arcnetPlus(36),     -- arcnet plus
                atm(37),            -- ATM cells
                miox25(38),
                sonet(39),          -- SONET or SDH 
                x25ple(40),
                iso88022llc(41),
                localTalk(42),
                smdsDxi(43),
                frameRelayService(44),  -- FRNETSERV-MIB
                v35(45),
                hssi(46),
                hippi(47),
                modem(48),          -- Generic modem
                aal5(49),           -- AAL5 over ATM
                sonetPath(50),
                sonetVT(51),
                smdsIcip(52),       -- SMDS InterCarrier Interface
                propVirtual(53),    -- proprietary virtual/internal
                propMultiplexor(54),-- proprietary multiplexing
                ieee80212(55),      -- 100BaseVG
                fibreChannel(56),   -- Fibre Channel
                hippiInterface(57), -- HIPPI interfaces     
                frameRelayInterconnect(58), -- Obsolete use either
                                    -- frameRelay(32) or 
                                    -- frameRelayService(44).
                aflane8023(59),     -- ATM Emulated LAN for 802.3
                aflane8025(60),     -- ATM Emulated LAN for 802.5
                cctEmul(61),        -- ATM Emulated circuit          
                fastEther(62),      -- Fast Ethernet (100BaseT)
                isdn(63),           -- ISDN and X.25           
                v11(64),            -- CCITT V.11/X.21             
                v36(65),            -- CCITT V.36                  
                g703at64k(66),      -- CCITT G703 at 64Kbps
                g703at2mb(67),      -- Obsolete see DS1-MIB
                qllc(68),           -- SNA QLLC                 
                fastEtherFX(69),    -- Fast Ethernet (100BaseFX)   
                channel(70),        -- channel                  
                ieee80211(71),      -- radio spread spectrum       
                ibm370parChan(72),  -- IBM System 360/370 OEMI Channel
                escon(73),          -- IBM Enterprise Systems Connection
                dlsw(74),           -- Data Link Switching
                isdns(75),          -- ISDN S/T interface
                isdnu(76),          -- ISDN U interface
                lapd(77),           -- Link Access Protocol D
                ipSwitch(78),       -- IP Switching Objects
                rsrb(79),           -- Remote Source Route Bridging
                atmLogical(80),     -- ATM Logical Port
                ds0(81),            -- Digital Signal Level 0
                ds0Bundle(82),      -- group of ds0s on the same ds1
                bsc(83),            -- Bisynchronous Protocol
                async(84),          -- Asynchronous Protocol
                cnr(85),            -- Combat Net Radio
                iso88025Dtr(86),    -- ISO 802.5r DTR
                eplrs(87),          -- Ext Pos Loc Report Sys
                arap(88),           -- Appletalk Remote Access Protocol
                propCnls(89),       -- Proprietary Connectionless Protocol
                hostPad(90),        -- CCITT-ITU X.29 PAD Protocol
                termPad(91),        -- CCITT-ITU X.3 PAD Facility
                frameRelayMPI(92),  -- Multiproto Interconnect over FR
                x213(93),           -- CCITT-ITU X213
                adsl(94),           -- Asymmetric Digital Subscriber Loop
                radsl(95),          -- Rate-Adapt. Digital Subscriber Loop
                sdsl(96),           -- Symmetric Digital Subscriber Loop
                vdsl(97),           -- Very H-Speed Digital Subscrib. Loop
                iso88025CRFPInt(98), -- ISO 802.5 CRFP
                myrinet(99),        -- Myricom Myrinet
                voiceEM(100),       -- voice recEive and transMit
                voiceFXO(101),      -- voice Foreign Exchange Office
                voiceFXS(102),      -- voice Foreign Exchange Station
                voiceEncap(103),    -- voice encapsulation
                voiceOverIp(104),   -- voice over IP encapsulation
                atmDxi(105),        -- ATM DXI
                atmFuni(106),       -- ATM FUNI
                atmIma (107),       -- ATM IMA                
                pppMultilinkBundle(108), -- PPP Multilink Bundle
                ipOverCdlc (109),   -- IBM ipOverCdlc
                ipOverClaw (110),   -- IBM Common Link Access to Workstn
                stackToStack (111), -- IBM stackToStack
                virtualIpAddress (112), -- IBM VIPA
                mpc (113),          -- IBM multi-protocol channel support
                ipOverAtm (114),    -- IBM ipOverAtm
                iso88025Fiber (115), -- ISO 802.5j Fiber Token Ring
                tdlc (116),	       -- IBM twinaxial data link control
                gigabitEthernet (117), -- Gigabit Ethernet
                hdlc (118),         -- HDLC
                lapf (119),	       -- LAP F
                v37 (120),	       -- V.37
                x25mlp (121),       -- Multi-Link Protocol
                x25huntGroup (122), -- X25 Hunt Group
                trasnpHdlc (123),   -- Transp HDLC
                interleave (124),   -- Interleave channel
                fast (125),         -- Fast channel
                ip (126),	       -- IP (for APPN HPR in IP networks)
                docsCableMaclayer (127),  -- CATV Mac Layer
                docsCableDownstream (128), -- CATV Downstream interface
                docsCableUpstream (129),  -- CATV Upstream interface
                a12MppSwitch (130), -- Avalon Parallel Processor
                tunnel (131),       -- Encapsulation interface
                coffee (132),       -- coffee pot
                ces (133),          -- Circuit Emulation Service
                atmSubInterface (134), -- ATM Sub Interface
                l2vlan (135),       -- Layer 2 Virtual LAN using 802.1Q
                l3ipvlan (136),     -- Layer 3 Virtual LAN using IP
                l3ipxvlan (137),    -- Layer 3 Virtual LAN using IPX
                digitalPowerline (138), -- IP over Power Lines	
                mediaMailOverIp (139), -- Multimedia Mail over IP
                dtm (140),        -- Dynamic syncronous Transfer Mode
                dcn (141),    -- Data Communications Network
                ipForward (142),    -- IP Forwarding Interface
                msdsl (143),       -- Multi-rate Symmetric DSL
                ieee1394 (144), -- IEEE1394 High Performance Serial Bus
                if-gsn (145),       --   HIPPI-6400 
                dvbRccMacLayer (146), -- DVB-RCC MAC Layer
                dvbRccDownstream (147),  -- DVB-RCC Downstream Channel
                dvbRccUpstream (148),  -- DVB-RCC Upstream Channel
                atmVirtual (149),   -- ATM Virtual Interface
                mplsTunnel (150),   -- MPLS Tunnel Virtual Interface
                srp (151),	-- Spatial Reuse Protocol	
                voiceOverAtm (152),  -- Voice Over ATM
                voiceOverFrameRelay (153),   -- Voice Over Frame Relay 
                idsl (154),		-- Digital Subscriber Loop over ISDN
                compositeLink (155),  -- Avici Composite Link Interface
                ss7SigLink (156),     -- SS7 Signaling Link 
                propWirelessP2P (157),  --  Prop. P2P wireless interface
                frForward (158),    -- Frame Forward Interface
                rfc1483 (159),	-- Multiprotocol over ATM AAL5
                usb (160),		-- USB Interface
                ieee8023adLag(161)  -- IEEE 802.3ad Link Aggregate
            }
    ACCESS  read-only
    STATUS  mandatory
    DESCRIPTION
           "The type of interface, distinguished according to
            the physical/link protocol(s) immediately `below'
            the network layer in the protocol stack."
    ::= { ifEntry 3 }

-- !!!!!!!!!!!!!!!!!!!!!!!!!!!!!!!!!!!!!!!!!!!!!!!!!!!!!!!!!!!!!!!
-- overwrite of ifType defined in rfc1213 by IANAifType found in
-- http://ftp.isi.edu/mib/ianaiftype.mib
-- !!!!!!!!!!!!!!!!!!!!!!!!!!!!!!!!!!!!!!!!!!!!!!!!!!!!!!!!!!!!!!!



-- This file cannot be used to create SNMP agent.
-- The file isarOneFile.my has to be used to create the agent.


-- isarIsystemMIBObjects      OBJECT IDENTIFIER ::= { isar  1 }


--
-- ISAR systemMIBObjects : begin
--
-- enterprise MIB for ISAR
-- The MIB is written for SNMPv1.

--
-- ISAR system 
--



-- isarIallowConfiguration OBJECT-TYPE
--    SYNTAX  INTEGER { 
--                      true(1), 
--                      false(2) 
--            }
--    ACCESS  read-write
--    STATUS  mandatory
--    DESCRIPTION
--           "When true(1), the IAD4700 may be reconfigured.  Only when 
--            true(1), the configuration file is allowed to be generated."
--    ::= { isarIsystemMIBObjects  1 }

isarIsaveNow OBJECT-TYPE
    SYNTAX  INTEGER { 
                      true(1), 
                      false(2) 
            }
    ACCESS  read-write
    STATUS  mandatory
    DESCRIPTION
           "When true(1), the IAD4700 will automatically regenerate the
            configuration file.  The 'configuration update log' will
            be 'recreated' (deleted and created)."
    ::= { isarIsystemMIBObjects  2 }


isarIperformanceStatistics OBJECT-TYPE
    SYNTAX  INTEGER { 
                      disabled(1),
                      enabled(2)
            }
    ACCESS  read-write
    STATUS  mandatory
    DESCRIPTION
           "Indicates whether the collection of performance parameters
            is enabled or not and this for the complete IAD4700. This field
            can be used to align the intervals throughout the network.
            15 minutes after the enable is sent to the agent, the 
            statistics for the first (next) interval are collected. The
            previous intervals are discarded."
    DEFVAL { disabled }
    ::= { isarIsystemMIBObjects  3 }

isarIrestoreFactoryDefault OBJECT-TYPE
    SYNTAX  INTEGER { 
                      true(1),
                      false(2)
            }
    ACCESS  read-write
    STATUS  optional
    DESCRIPTION
           "The persistent store is cleared when this object is set to 
            'true'. It has to be set back to 'false' after clearing the 
            persistent store."
    DEFVAL { false }
    ::= { isarIsystemMIBObjects  7 }



-- version information

isarIacsmVersionObjects  OBJECT IDENTIFIER ::= 
                                   { isarIsystemMIBObjects  4 }

isarIacsmVersion OBJECT-TYPE
    SYNTAX  OCTET STRING
    ACCESS  read-only
    STATUS  mandatory
    DESCRIPTION
           "Version of the flex file loaded by the ACSM at 
            initialisation."
    ::= { isarIacsmVersionObjects  1 }

isarIvoiceProcessorVersionObjects  OBJECT IDENTIFIER ::= 
                                   { isarIsystemMIBObjects  9 }

isarIvoiceProcessorVersion OBJECT-TYPE
    SYNTAX  OCTET STRING
    ACCESS  read-only
    STATUS  obsolete
    DESCRIPTION
           "Version of the flex file loaded by the voice processor at 
            initialisation."
    ::= { isarIvoiceProcessorVersionObjects  1 }

isarIiwe8VersionObjects  OBJECT IDENTIFIER ::= 
                                   { isarIsystemMIBObjects  13 }

isarIiwe8Version OBJECT-TYPE
    SYNTAX  OCTET STRING
    ACCESS  read-only
    STATUS  mandatory
    DESCRIPTION
           "Version of the IWE8."
    ::= { isarIiwe8VersionObjects  1 }

isarIbootstrapVersionObjects  OBJECT IDENTIFIER ::= 
                                   { isarIsystemMIBObjects  16 }

isarIbootstrapVersion OBJECT-TYPE
    SYNTAX  OCTET STRING
    ACCESS  read-only
    STATUS  obsolete
    DESCRIPTION
           "incorparated in slot table."
    ::= { isarIbootstrapVersionObjects  1 }

isarIstm1VersionObjects  OBJECT IDENTIFIER ::= 
                                   { isarIsystemMIBObjects  26 }

isarIstm1Version OBJECT-TYPE
    SYNTAX  OCTET STRING
    ACCESS  read-only
    STATUS  mandatory
    DESCRIPTION
           "Version of the stm1."
    ::= { isarIstm1VersionObjects  1 }


isarIsdslVersionObjects  OBJECT IDENTIFIER ::= 
                                   { isarIsystemMIBObjects  28 }

isarIsdslVersion OBJECT-TYPE
    SYNTAX  OCTET STRING
    ACCESS  read-only
    STATUS  mandatory
    DESCRIPTION
           "Version of the SDSL Interface."
    ::= { isarIsdslVersionObjects  1 }


isarIappletVersionObjects  OBJECT IDENTIFIER ::= 
                                   { isarIsystemMIBObjects  29 }


isarIappletVersion OBJECT-TYPE
    SYNTAX  OCTET STRING
    ACCESS  read-only
    STATUS  mandatory
    DESCRIPTION
           "Version of the applet file required to manage this IAD 4700."
    ::= { isarIappletVersionObjects 1 }




-- RefClock : provides parameters for clock synchronisation and 
--            distribution. For CES structured data transfer the system 
--            has to be configured in the synchronous mode.

isarIsystemRefClockObjects  OBJECT IDENTIFIER ::= 
                                   { isarIsystemMIBObjects  5 }

isarIrefClockOperMode OBJECT-TYPE
    SYNTAX  INTEGER {
                      synchronous(1),
                      asynchronous(2)
            }
    ACCESS  read-only
    STATUS  mandatory
    DESCRIPTION
           "Indicates whether the system runs in synchronous or 
            asynchronous mode (also called FALC mode).
            The value is determined via ini-file.
            Not to be shown to operator."
    ::= { isarIsystemRefClockObjects  1 }

isarIrefClockClockMode OBJECT-TYPE
    SYNTAX  INTEGER {
                      normal(1),
                      holdover(2),
                      freeRunning(3)
            }
    ACCESS  read-write
    STATUS  obsolete
    DESCRIPTION
           "."
    DEFVAL { normal }
    ::= { isarIsystemRefClockObjects  2 }

isarIrefClockSyncMode OBJECT-TYPE
    SYNTAX  INTEGER {
                      mamoE1Drop(1),
                      mamoE1Aggr(2),
                      pm1(3),
                      pm2(4),
                      pm3(5)
            }
    ACCESS  read-write
    STATUS  obsolete
    DESCRIPTION
           "."
    ::= { isarIsystemRefClockObjects  3 }

isarIrefClockSetting OBJECT-TYPE
    SYNTAX  INTEGER {
                      defaultSetting(1),
                      master(2),
                      slaveOnMamoE1Drop(3),
                      slaveOnMamoE1Aggr(4),
                      slaveOnPm1(5),
                      slaveOnPm2(6),
                      slaveOnPm3(7)
            }
    ACCESS  read-write
    STATUS  mandatory
    DESCRIPTION
           "Common MAMO clock setting.
            Changing the clock setting will cause a regeneration of the 
            persistent store followed by a reboot of the system.
            The operator must confirm the result of his action before a SET
            is sent to the IAD4700.
            defaultSetting = the IAD4700 will slave on the active aggregate
            side interface which means 'slaveOnMamoE1Aggr' in case of MAMO 
            only or 'slaveOnPm3' if an APM is plugged in."
    DEFVAL { defaultSetting }
    ::= { isarIsystemRefClockObjects  4 }



-- AAL sporadic counters

isarIaalSporadicCounterObjects  OBJECT IDENTIFIER ::= 
                                   { isarIsystemMIBObjects  6 }

isarIiwe8UtopiaTrmBusParityError OBJECT-TYPE
    SYNTAX  Counter
    ACCESS  read-only
    STATUS  mandatory
    DESCRIPTION
           "Counter."
    ::= { isarIaalSporadicCounterObjects  1 }

isarIiwe8ExternalRamParityError OBJECT-TYPE
    SYNTAX  Counter
    ACCESS  read-only
    STATUS  mandatory
    DESCRIPTION
           "Counter."
    ::= { isarIaalSporadicCounterObjects  2 }

isarIiwe8InternalParityError OBJECT-TYPE
    SYNTAX  Counter
    ACCESS  read-only
    STATUS  mandatory
    DESCRIPTION
           "Counter."
    ::= { isarIaalSporadicCounterObjects  3 }

isarIacsmUtopia0ParityError OBJECT-TYPE
    SYNTAX  Counter
    ACCESS  read-only
    STATUS  mandatory
    DESCRIPTION
           "Counter."
    ::= { isarIaalSporadicCounterObjects  4 }

isarIacsmUtopia1ParityError OBJECT-TYPE
    SYNTAX  Counter
    ACCESS  read-only
    STATUS  mandatory
    DESCRIPTION
           "Counter."
    ::= { isarIaalSporadicCounterObjects  5 }

isarIacsmUtopia2ParityError OBJECT-TYPE
    SYNTAX  Counter
    ACCESS  read-only
    STATUS  mandatory
    DESCRIPTION
           "Counter."
    ::= { isarIaalSporadicCounterObjects  6 }

isarIacsmUtopiaBParityError OBJECT-TYPE
    SYNTAX  Counter
    ACCESS  read-only
    STATUS  mandatory
    DESCRIPTION
           "Counter."
    ::= { isarIaalSporadicCounterObjects  7 }

isarIsarParityError OBJECT-TYPE
    SYNTAX  Counter
    ACCESS  read-only
    STATUS  mandatory
    DESCRIPTION
           "Counter."
    ::= { isarIaalSporadicCounterObjects  8 }



-- SNTP information

isarIsystemSntpObjects  OBJECT IDENTIFIER ::= 
                                   { isarIsystemMIBObjects  8 }

isarIsntpAllowed OBJECT-TYPE
    SYNTAX  INTEGER {
                      true(1),
                      false(2)
            }
    ACCESS  read-write
    STATUS  mandatory
    DESCRIPTION
           "The local time will be synchronized using SNTP when this 
            object is set to true."
    ::= { isarIsystemSntpObjects  1 }

isarIsntpPeriod OBJECT-TYPE
    SYNTAX  INTEGER
    ACCESS  read-write
    STATUS  mandatory
    DESCRIPTION
           "Unit = minutes.  Synchronization period."
    ::= { isarIsystemSntpObjects  2 }

isarIsntpTimeDifference OBJECT-TYPE
    SYNTAX  INTEGER 
    ACCESS  read-only
    STATUS  mandatory
    DESCRIPTION
           "Unit = seconds.  Allows to view the last difference
            between the local time and the SNTP time."
    ::= { isarIsystemSntpObjects  3 }

isarIsntpFailures OBJECT-TYPE
    SYNTAX  Counter
    ACCESS  read-only
    STATUS  mandatory
    DESCRIPTION
           "Counts the number of times that the synchronization has 
            failed.  The counter is reset to zero after a successful
            synchronization.  In combination with the synchronization
            period one can determine the last successful 
            synchronization."
    ::= { isarIsystemSntpObjects  4 }

isarIsntpServerAddr OBJECT-TYPE
    SYNTAX  IpAddress
    ACCESS  read-write
    STATUS  mandatory
    DESCRIPTION
           "IP Address of SNTP server."
    ::= { isarIsystemSntpObjects  5 }

isarIsntpReset OBJECT-TYPE
    SYNTAX  INTEGER {
                      true(1),
                      false(2)
            }
    ACCESS  read-write
    STATUS  mandatory
    DESCRIPTION
           "set to true : forced synchronization.
            Only valid when isarIsntpAllowed = true.
            Set automatically back to false."
    ::= { isarIsystemSntpObjects  6 }




-- ISAR slot table


isarIslotTable OBJECT-TYPE
    SYNTAX  SEQUENCE OF IsarIslotEntry
    ACCESS  not-accessible
    STATUS  mandatory
    DESCRIPTION
           "."
    ::= { isarIsystemMIBObjects  10 }

isarIslotEntry OBJECT-TYPE
    SYNTAX  IsarIslotEntry
    ACCESS  not-accessible
    STATUS  mandatory
    DESCRIPTION
           "One row in the isarIslotTable."
    INDEX   { isarIphysSlotId }
    ::= { isarIslotTable  1 }


IsarIslotEntry ::=
    SEQUENCE { 
      isarIphysSlotId
        INTEGER,

      isarIphysStackNo
        INTEGER,
       
      isarIpmSerialNo
        OCTET STRING,
        
      isarIhwVersion
        OCTET STRING,
        
      isarIslotType
        INTEGER,
        
      isarIisArmed
        INTEGER,
        
      isarIswCompatibility
        INTEGER,

      isarIminRel
        OCTET STRING,

      isarIthisLoad
        INTEGER,

      isarInewLoad
        INTEGER,

      isarIpromoteLoad
        INTEGER,

      isarIutilization
        INTEGER,

      isarIKterm
        INTEGER,

      isarIbootNow
        INTEGER,

      isarIslotBootstrapVersion
        OCTET STRING,

      isarIslotVoiceProcessorVersion
        OCTET STRING

    }
    
isarIphysSlotId OBJECT-TYPE
    SYNTAX  INTEGER (0..3)
    ACCESS  read-only
    STATUS  mandatory
    DESCRIPTION
           "Slot Id as defined by hardware
               0    : MAMO
               1..3 : PM."
    ::= { isarIslotEntry  1 }

isarIphysStackNo OBJECT-TYPE
    SYNTAX  INTEGER (0..63)
    ACCESS  read-only
    STATUS  optional
    DESCRIPTION
           "Number of the IAD4700 in the stack."
    ::= { isarIslotEntry  2 }

isarIpmSerialNo OBJECT-TYPE
    SYNTAX  OCTET STRING
    ACCESS  read-only
    STATUS  mandatory
    DESCRIPTION
           "Serial number of this PM."
    ::= { isarIslotEntry  3 }

isarIhwVersion OBJECT-TYPE
    SYNTAX  OCTET STRING
    ACCESS  read-only
    STATUS  mandatory
    DESCRIPTION
           "Hardware version of this PM."
    ::= { isarIslotEntry  4 }

isarIslotType OBJECT-TYPE
    SYNTAX  INTEGER {
                      unknown(1),
                      empty(2),
                      invalid(3),
                      mamoE1Atm(4),
                      mamoT1Atm(5), -- not used in IAD4700 v1 / v2.0
                      imaE1(6),
                      imaT1(7),     -- not used in IAD4700 v1 / v2.0
                      stm1ShortReach(8),
                      vcmE1(9),
                      vcmT1(10),     -- not used in IAD4700 v1 / v2.0
                      -- ces(11)
                      -- hssi(12)
                      stm1IntermediateReach(13),
                      stm1LongReach(14),
                      stm1VeryLongReach(15),
                      bri4nt(16),
                      bri8nt(17),
                      -- tcMac(18)   reserved
                      sdsl2B1Q(19),
                      sdslPAM16(20),
                      bri4te(21),
                      bri8te(22),
                      sdsl(23)      -- 2B1Q and PAM16 possible
                      -- ces4E1(24)
                      -- ces8E1(25)
                      -- ces4T1(26)
                      -- ces8T1(27)
                       
            }
    ACCESS  read-only
    STATUS  optional
    DESCRIPTION
           "The PM type detected via the hardware detection mechanism."
    ::= { isarIslotEntry  5 }

isarIisArmed OBJECT-TYPE
    SYNTAX  INTEGER { 
                      true(1), 
                      false(2) 
            } 
    ACCESS  read-only
    STATUS  optional
    DESCRIPTION
           "Indicates whether the mentioned PM type is plugged in."
    ::= { isarIslotEntry  6 }

isarIswCompatibility OBJECT-TYPE
    SYNTAX  INTEGER { 
                      compatible(1), 
                      notCompatible(2), 
                      notApplicable(3)
            }  
    ACCESS  read-only
    STATUS  optional
    DESCRIPTION
           "Indicates whether the PM is compatible.
            notApplicable is used for passive PM"
    ::= { isarIslotEntry  7 }

isarIminRel OBJECT-TYPE
    SYNTAX  OCTET STRING
    ACCESS  read-only
    STATUS  mandatory
    DESCRIPTION
           "Indicates the minor software release of the current load."
    ::= { isarIslotEntry  8 }

isarIthisLoad OBJECT-TYPE
    SYNTAX  INTEGER { 
                      primary(1), 
                      secondary(2) 
            }  
    ACCESS  read-only
    STATUS  optional
    DESCRIPTION
           "This load is the load that the PM is currently executing."
    ::= { isarIslotEntry  9 }

isarInewLoad OBJECT-TYPE
    SYNTAX  INTEGER { 
                      primary(1), 
                      secondary(2) 
            }  
    ACCESS  read-write
    STATUS  optional
    DESCRIPTION
           "New load is the load the PM should start from when forced
            booted."
    ::= { isarIslotEntry  10 }

isarIpromoteLoad OBJECT-TYPE
    SYNTAX  INTEGER { 
                      true(1), 
                      false(2) 
            }  
    ACCESS  read-write
    STATUS  optional
    DESCRIPTION
           "Promote the secondary load to primary load.  The field is set
            to 'false' after the promote."
    DEFVAL { false }
    ::= { isarIslotEntry  11 }


isarIutilization OBJECT-TYPE
    SYNTAX  INTEGER
    ACCESS  read-only
    STATUS  optional
    DESCRIPTION
           "Processor utilization in percent."
    ::= { isarIslotEntry  12 }

isarIKterm OBJECT-TYPE
    SYNTAX  INTEGER
    ACCESS  read-only
    STATUS  optional
    DESCRIPTION
           "K is used to enable tuning of the scheduling system in case
            the low level virtual processors are starting to suffer from
            starvation.
            When K reaches a predefined threshold, the system is 
            concidered as stalled and is rebooted (cold boot).
            A trap is sent when K crosses a certain threshold (before
            the reboot threshold is reached)."
    ::= { isarIslotEntry  13 }

isarIbootNow OBJECT-TYPE
    SYNTAX  INTEGER { 
                      true(1), 
                      false(2) 
            } 
    ACCESS  read-write
    STATUS  optional
    DESCRIPTION
           "Forces a boot.
               MAMO : warm boot
               PM : forced boot."
    ::= { isarIslotEntry  14 }

isarIslotBootstrapVersion OBJECT-TYPE
    SYNTAX  OCTET STRING 
    ACCESS  read-only
    STATUS  optional
    DESCRIPTION
           "Version of the bootstrap at initialization.
            This is valid for all active modules."
    ::= { isarIslotEntry  15 }

isarIslotVoiceProcessorVersion OBJECT-TYPE
    SYNTAX  OCTET STRING 
    ACCESS  read-only
    STATUS  optional
    DESCRIPTION
           "Version of the voice processor flex file loaded
            at initialization.
            This is only valid for isarIslotType=vcmE1 or vcmT1."
    ::= { isarIslotEntry  16 }



-- ISAR physical port table


isarIphysPortTable OBJECT-TYPE
    SYNTAX  SEQUENCE OF IsarIphysPortEntry
    ACCESS  not-accessible
    STATUS  mandatory
    DESCRIPTION
           "."
    ::= { isarIsystemMIBObjects  14 }

isarIphysPortEntry OBJECT-TYPE
    SYNTAX  IsarIphysPortEntry
    ACCESS  not-accessible
    STATUS  mandatory
    DESCRIPTION
           "Description of the physical ports per module present in the
            IAD4700 and a mapping to their ifIndex."
    INDEX   { isarIphysStackNo, isarIphysSlotId, isarIphysPortId }
    ::= { isarIphysPortTable  1 }


IsarIphysPortEntry ::=
    SEQUENCE { 
      isarIphysPortId
        INTEGER,
        
      isarIphysPortIfIndex
        INTEGER

    }
    
isarIphysPortId OBJECT-TYPE
    SYNTAX  INTEGER (0..2147483647)
    ACCESS  read-only
    STATUS  mandatory
    DESCRIPTION
           "Port number that is unique per module."
    ::= { isarIphysPortEntry  1 }

isarIphysPortIfIndex OBJECT-TYPE
    SYNTAX  INTEGER (1..2147483647)
    ACCESS  read-only
    STATUS  mandatory
    DESCRIPTION
           "IfIndex belonging to this port."
    ::= { isarIphysPortEntry  2 }




-- ISAR temperature sensor table


isarItempSensorTable OBJECT-TYPE
    SYNTAX  SEQUENCE OF IsarItempSensorEntry
    ACCESS  not-accessible
    STATUS  mandatory
    DESCRIPTION
           "."
    ::= { isarIsystemMIBObjects  11 }

isarItempSensorEntry OBJECT-TYPE
    SYNTAX  IsarItempSensorEntry
    ACCESS  not-accessible
    STATUS  mandatory
    DESCRIPTION
           "One row in the isarItempSensorTable."
    INDEX   { isarItempSensorId }
    ::= { isarItempSensorTable  1 }


IsarItempSensorEntry ::=
    SEQUENCE { 
      isarItempSensorId
        INTEGER,
        
      isarItempSensorName
        OCTET STRING,
        
      isarItempSensorThreshold
        INTEGER,
        
      isarItempSensorCurrentTemp
        INTEGER,
        
      isarItempSensorSecondThreshold
        INTEGER

    }
    
isarItempSensorId OBJECT-TYPE
    SYNTAX  INTEGER
    ACCESS  read-only
    STATUS  mandatory
    DESCRIPTION
           "Identification of temperature sensor."
    ::= { isarItempSensorEntry  1 }

isarItempSensorName OBJECT-TYPE
    SYNTAX  OCTET STRING
    ACCESS  read-only
    STATUS  mandatory
    DESCRIPTION
           "Name of temperature sensor."
    ::= { isarItempSensorEntry  2 }

isarItempSensorThreshold OBJECT-TYPE
    SYNTAX  INTEGER
    ACCESS  read-only
    STATUS  mandatory
    DESCRIPTION
           "Threshold above which an alarm will be generated."
    ::= { isarItempSensorEntry  3 }

isarItempSensorCurrentTemp OBJECT-TYPE
    SYNTAX  INTEGER
    ACCESS  read-only
    STATUS  mandatory
    DESCRIPTION
           "Current temperature."
    ::= { isarItempSensorEntry  4 }

isarItempSensorSecondThreshold OBJECT-TYPE
    SYNTAX  INTEGER
    ACCESS  read-only
    STATUS  mandatory
    DESCRIPTION
           "For STM1 : the threshold above which the LASER will be 
                       switched off
            For the rest : not used (value = 0)."
    ::= { isarItempSensorEntry  5 }



-- power supply table

isarIpowerSupplyTable OBJECT-TYPE
    SYNTAX  SEQUENCE OF IsarIpowerSupplyEntry
    ACCESS  not-accessible
    STATUS  mandatory
    DESCRIPTION
           "."
    ::= { isarIsystemMIBObjects  12 }

isarIpowerSupplyEntry OBJECT-TYPE
    SYNTAX  IsarIpowerSupplyEntry
    ACCESS  not-accessible
    STATUS  mandatory
    DESCRIPTION
           "One row in the isarIpowerSupplyTable."
    INDEX   { isarIpowerSupplyId }
    ::= { isarIpowerSupplyTable  1 }


IsarIpowerSupplyEntry ::=
    SEQUENCE { 
      isarIpowerSupplyId
        INTEGER,
                
      isarIpowerSupplyStatus
        INTEGER,
                
      isarIpowerSupplyName
        OCTET STRING
    }

isarIpowerSupplyId OBJECT-TYPE
    SYNTAX  INTEGER (0..3)
    ACCESS  read-only
    STATUS  mandatory
    DESCRIPTION
           "Identification of the power supply."
    ::= { isarIpowerSupplyEntry  1 }

isarIpowerSupplyStatus OBJECT-TYPE
    SYNTAX  INTEGER {
                      up(1),
                      down(2)
            }
    ACCESS  read-only
    STATUS  mandatory
    DESCRIPTION
           "Status of the power supply."
    DEFVAL { down }
    ::= { isarIpowerSupplyEntry  2 }

isarIpowerSupplyName OBJECT-TYPE
    SYNTAX  OCTET STRING
    ACCESS  read-only
    STATUS  mandatory
    DESCRIPTION
           "Name of the power supply."
    ::= { isarIpowerSupplyEntry  3 }



-- MAC addresses

isarIlanPortMACAddressObjects  OBJECT IDENTIFIER ::= 
                                   { isarIsystemMIBObjects  17 }
isarIlanPortMACAddress OBJECT-TYPE
    SYNTAX  OCTET STRING (SIZE (6))
    ACCESS  read-only
    STATUS  mandatory
    DESCRIPTION
           "The MAC address of the user 100 BaseT port of 
            the MAMO."
    ::= { isarIlanPortMACAddressObjects 1 }

    
isarImaintPortMACAddressObjects  OBJECT IDENTIFIER ::= 
                                   { isarIsystemMIBObjects  18 }
                                   
isarImaintPortMACAddress OBJECT-TYPE
    SYNTAX  OCTET STRING (SIZE (6))
    ACCESS  read-only
    STATUS  mandatory
    DESCRIPTION
           "The MAC address of the maintenance 10 BaseT port of 
            the MAMO."
    ::= { isarImaintPortMACAddressObjects 1 }




-- trap community strings table

isarItrapComTable OBJECT-TYPE
    SYNTAX  SEQUENCE OF IsarItrapComEntry
    ACCESS  not-accessible
    STATUS  mandatory
    DESCRIPTION
           "."
    ::= { isarIsystemMIBObjects  19 }

isarItrapComEntry OBJECT-TYPE
    SYNTAX  IsarItrapComEntry
    ACCESS  not-accessible
    STATUS  mandatory
    DESCRIPTION
           "One row in the isarItrapComTable."
    INDEX   { isarItrapIpAddr }
    ::= { isarItrapComTable  1 }


IsarItrapComEntry ::=
    SEQUENCE { 
      isarItrapIpAddr
        IpAddress,
                
      isarItrapComName
        OCTET STRING,
                
      isarItrapComStatus
        INTEGER,
                
      isarItrapComPort
        INTEGER
    }

isarItrapIpAddr OBJECT-TYPE
    SYNTAX  IpAddress
    ACCESS  read-only
    STATUS  mandatory
    DESCRIPTION
           "IpAddress to which traps are sent."
    ::= { isarItrapComEntry  1 }

isarItrapComName OBJECT-TYPE
    SYNTAX  OCTET STRING (SIZE (1..64))
    ACCESS  read-write
    STATUS  mandatory
    DESCRIPTION
           "Community string."
    ::= { isarItrapComEntry  2 }

isarItrapComStatus OBJECT-TYPE
    SYNTAX  INTEGER {
                      true(1),
                      false(2)
            }
    ACCESS  read-write
    STATUS  mandatory
    DESCRIPTION
           "true = create or exist
            false = destroy."
    ::= { isarItrapComEntry  3 }

isarItrapComPort OBJECT-TYPE
    SYNTAX  INTEGER (0..65535)
    ACCESS  read-write
    STATUS  mandatory
    DESCRIPTION
           "The port to which the traps will be sent."
    DEFVAL  { 162 }
    ::= { isarItrapComEntry  4 }



-- TRAP

isarIsystemTraps OBJECT IDENTIFIER ::= { isarIsystemMIBObjects  15 }

isarIpowerSupplyDown TRAP-TYPE
    ENTERPRISE  isarIsystemTraps
    VARIABLES   { isarIpowerSupplyId }
    DESCRIPTION
           "Power supply status changed from up to down."
    ::= 1

isarIpowerSupplyUp TRAP-TYPE
    ENTERPRISE  isarIsystemTraps
    VARIABLES   { isarIpowerSupplyId }
    DESCRIPTION
           "Power supply status changed from down to up."
    ::= 2

isarIpowerSupplyDownAtStartUp TRAP-TYPE
    ENTERPRISE  isarIsystemTraps
    VARIABLES   { isarIpowerSupplyId }
    DESCRIPTION
           "Power supply status is down. at moment of start up."
    ::= 23



isarItempExceeded TRAP-TYPE
    ENTERPRISE  isarIsystemTraps
    VARIABLES   { isarItempSensorId }
    DESCRIPTION
           "Sensor temperature has exceeded the threshold."
    ::= 3

isarItempNormal TRAP-TYPE
    ENTERPRISE  isarIsystemTraps
    VARIABLES   { isarItempSensorId }
    DESCRIPTION
           "Sensor temperature has dropped x degrees below the 
            threshold."
    ::= 4

isarIinterfaceStatusChange TRAP-TYPE
    ENTERPRISE  isarIsystemTraps
    VARIABLES   { ifIndex,
                  ifAdminStatus,
                  ifAdminStatus,
                  isarIifOperStatusExt,
                  isarIifOperStatusExt
                }
    DESCRIPTION
           "An indication that the operation or administrative status of this  
            interface has changed.
            A status change is given when :
            1. ifAdminStatus is 'up' and 
               isarIifOperStatusExt is going 'down' (set alarm)
            2. when isarIifOperStatusExt is leaving the 'down' 
               state. (clear alarm)
            3. ifAdminStatus is set to 'up' and isarIifOperStatusExt is not
               changed to 'up' (set alarm)
            4. ifAdminStatus is set to 'down' and isarIifOperStatusExt is not
               'up' (clear alarm)
            The first isarIifOperStatusExt is the previous state,
            the second isarIifOperStatusExt is the new state.
            The first ifAdminStatus is the previous state,
            the second ifAdminStatus is the new state.
            The use of this trap is preferred over the use of linkUp
            and linkDown trap."
    ::= 5

isarIWatchdogWarning TRAP-TYPE
    ENTERPRISE  isarIsystemTraps
    VARIABLES   { isarIKterm }
    DESCRIPTION
           "An indication that the 'K-term', used for tuning of the
            scheduling system, has reached a threshold value.
            The software determines the threshold."
    ::= 6

isarIWatchdogWarningEnd TRAP-TYPE
    ENTERPRISE  isarIsystemTraps
    VARIABLES   { isarIKterm }
    DESCRIPTION
           "An indication that the 'K-term', used for tuning of the
            scheduling system, is back under a threshold value.
            The software determines the threshold."
    ::= 7

isarIiwe8HWFault TRAP-TYPE
    ENTERPRISE  isarIsystemTraps
    DESCRIPTION
           "IWE8 hardware fault."
    ::= 8

isarIiwe8HWFaultEnd TRAP-TYPE
    ENTERPRISE  isarIsystemTraps
    DESCRIPTION
           "End of IWE8 hardware fault."
    ::= 9

isarIiwe8LOCD TRAP-TYPE
    ENTERPRISE  isarIsystemTraps
    VARIABLES   { isarIatmfCESCbrIndex }
    DESCRIPTION
           "IWE8 loss of cell delineation."
    ::= 10

isarIiwe8LOCDEnd TRAP-TYPE
    ENTERPRISE  isarIsystemTraps
    VARIABLES   { isarIatmfCESCbrIndex }
    DESCRIPTION
           "End of IWE8 loss of cell delineation."
    ::= 11

isarIloadPromoted TRAP-TYPE
    ENTERPRISE  isarIsystemTraps
    VARIABLES   { isarIphysSlotId }
    DESCRIPTION
           "Secondary load promotion successful."
    ::= 14

isarIloadPromotionFailed TRAP-TYPE
    ENTERPRISE  isarIsystemTraps
    VARIABLES   { isarIphysSlotId }
    DESCRIPTION
           "Secondary load promotion failed."
    ::= 15

isarIsntpTraps OBJECT IDENTIFIER ::= { isarIsystemSntpObjects  7 }

isarIsntpStopped TRAP-TYPE
    ENTERPRISE  isarIsntpTraps
    DESCRIPTION
           "SNTP has stopped working."
    ::= 1

isarIsntpRestarted TRAP-TYPE
    ENTERPRISE  isarIsntpTraps
    DESCRIPTION
           "SNTP restarted."
    ::= 2

isarIsntpServerProblems TRAP-TYPE
    ENTERPRISE  isarIsntpTraps
    DESCRIPTION
           "The SNTP server doesn't respond anymore."
    ::= 3

isarIsntpServerProblemsSolved TRAP-TYPE
    ENTERPRISE  isarIsntpTraps
    DESCRIPTION
           "The SNTP server responds again."
    ::= 4



-- interfaces

isarIsystemNextMIBObjects  OBJECT IDENTIFIER 
  ::= { isarIsystemMIBObjects  20 }


isarIipInterfaceNextIndex OBJECT-TYPE
    SYNTAX  INTEGER (2..2147483647)
    ACCESS  read-only
    STATUS  mandatory
    DESCRIPTION
           "This object is used to assist the manager in
            selecting a value for isarIipInterfaceId.  
            The manager has to GET this index before creating a row in 
            isarIipInterfaceTable."
    ::= { isarIsystemNextMIBObjects  1 }

isarIsystemRouteNextMIBObjects  OBJECT IDENTIFIER 
  ::= { isarIsystemMIBObjects  22 }

isarIipInterfaceRouteNextIndex OBJECT-TYPE
    SYNTAX  INTEGER (2..2147483647)
    ACCESS  read-only
    STATUS  mandatory
    DESCRIPTION
           "This object is used to assist the manager in
            selecting a value for isarIipInterfaceRouteId.  
            The manager has to GET this index before creating a row in 
            isarIipInterfaceRouteTable."
    ::= { isarIsystemRouteNextMIBObjects  1 }


-- ISAR IP interface table


isarIipInterfaceTable OBJECT-TYPE
    SYNTAX  SEQUENCE OF IsarIipInterfaceEntry
    ACCESS  not-accessible
    STATUS  mandatory
    DESCRIPTION
           "This table contains the IP interfaces present in the system.
            IP interfaces can be used for inband management connections.
            It must be possible to dynamically add and delete entries.
            An entry that is assigned to a protocol handler cannot be
            deleted.
            An entry that has IP interface routes assigned to it cannot be
	    deleted."
    ::= { isarIsystemMIBObjects  21 }

isarIipInterfaceEntry OBJECT-TYPE
    SYNTAX  IsarIipInterfaceEntry
    ACCESS  not-accessible
    STATUS  mandatory
    DESCRIPTION
           "Description of the IP interfaces present in the IAD4700."
    INDEX   { isarIipInterfaceId }
    ::= { isarIipInterfaceTable  1 }


IsarIipInterfaceEntry ::=
    SEQUENCE {
      isarIipInterfaceId
        INTEGER,

      isarIipInterfaceExternalIpNumber
        IpAddress,

      isarIipInterfaceRowStatus
        INTEGER,

      isarIipInterfaceProtocolHandlerIndex
        INTEGER,

      isarIipInterfaceNumberOfRoutes
        INTEGER
    }

isarIipInterfaceId OBJECT-TYPE
    SYNTAX  INTEGER (0..2147483647)
    ACCESS  read-only
    STATUS  mandatory
    DESCRIPTION
           "Interface number, unique in the system, determined by the
            manager via isarIipInterfaceNextIndex."
    ::= { isarIipInterfaceEntry 1 }

isarIipInterfaceExternalIpNumber OBJECT-TYPE
    SYNTAX  IpAddress
    ACCESS  read-write
    STATUS  mandatory
    DESCRIPTION
           "Optional external IP number for the IP interface.
            When no IP number is provided by the operator, the IP number
            is equal to the IP number of the 10BaseT management interface.
            Modify is not allowed.
            The SNMPv2 MAX-ACCESS is read(-only)-create."
    ::= { isarIipInterfaceEntry 2 }

isarIipInterfaceRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIipInterfaceEntry 3 }

isarIipInterfaceProtocolHandlerIndex OBJECT-TYPE
    SYNTAX  INTEGER
    ACCESS  read-only
    STATUS  mandatory
    DESCRIPTION
           "The index of the inband IP protocol handler where the channel
            is assigned to. For unassigned IP interfaces the value is 0.
            The index is the same as isarIprotocolHandlerIndex
            in the IsarIprotocolHandlerEntry.
            The value of this object is initialized by the system
            after the associated entry in the isarIprotocolHandlerTable
            has been created."
    ::= { isarIipInterfaceEntry 4 }

isarIipInterfaceNumberOfRoutes OBJECT-TYPE
    SYNTAX  INTEGER
    ACCESS  read-only
    STATUS  mandatory
    DESCRIPTION
           "The number of routes that have been defined for this IP
            interface.
	    The value is of this object is set by the system each time a
	    route for this IP interface is added or removed."
    ::= { isarIipInterfaceEntry 5 }


-- ISAR IP interface route table


isarIipInterfaceRouteTable OBJECT-TYPE
    SYNTAX  SEQUENCE OF IsarIipInterfaceRouteEntry
    ACCESS  not-accessible
    STATUS  mandatory
    DESCRIPTION
           "This table contains routing entries for the IP interfaces
            present in the system. A route describes the relation between
            an IP interface and an IP host address or network address of
	    (a) management station(s) that access the system via 
	    inband management.
            It must be possible to dynamically add and delete entries."
    ::= { isarIsystemMIBObjects  23 }

isarIipInterfaceRouteEntry OBJECT-TYPE
    SYNTAX  IsarIipInterfaceRouteEntry
    ACCESS  not-accessible
    STATUS  mandatory
    DESCRIPTION
           "Description of the IP interface routes present in the system."
    INDEX   { isarIipInterfaceRouteId }
    ::= { isarIipInterfaceRouteTable  1 }


IsarIipInterfaceRouteEntry ::=
    SEQUENCE {
      isarIipInterfaceRouteId
        INTEGER,

      isarIipInterfaceRouteIpNumber
        IpAddress,

      isarIipInterfaceRouteIpInterfaceId
        INTEGER,

      isarIipInterfaceRouteRowStatus
        INTEGER
    }

isarIipInterfaceRouteId OBJECT-TYPE
    SYNTAX  INTEGER (0..2147483647)
    ACCESS  read-only
    STATUS  mandatory
    DESCRIPTION
           "Route number, unique in the system, determined by the
            manager via isarIipInterfaceRouteNextIndex."
    ::= { isarIipInterfaceRouteEntry 1 }

isarIipInterfaceRouteIpNumber OBJECT-TYPE
    SYNTAX  IpAddress
    ACCESS  read-write
    STATUS  mandatory
    DESCRIPTION
           "IP host address or network address of the system(s) 
	    linked with the IP interface.
            Modify is not allowed.
            The SNMPv2 MAX-ACCESS is read(-only)-create."
    ::= { isarIipInterfaceRouteEntry 2 }

isarIipInterfaceRouteIpInterfaceId OBJECT-TYPE
    SYNTAX  INTEGER
    ACCESS  read-write
    STATUS  mandatory
    DESCRIPTION
           "The index of the IP interface.
            The index is the same as isarIipInterfaceId in the
	    isarIipInterfaceTable.
            The SNMPv2 MAX-ACCESS is read(-only)-create."
    ::= { isarIipInterfaceRouteEntry 3 }

isarIipInterfaceRouteRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIipInterfaceRouteEntry 4 }




-- FALC : excessive bit error and alignment error threshold objects
-- the thresholds are used by the FALC to generate alarms

isarIFALCMIBObjects  OBJECT IDENTIFIER 
  ::= { isarIsystemMIBObjects  24 }

-- thresholds table for net/user FALC and for QFALC (IMA)
-- the exact FALC is determined via the ifIndex

isarIFALCThresholdsTable OBJECT-TYPE
    SYNTAX  SEQUENCE OF IsarIFALCThresholdsEntry
    ACCESS  not-accessible
    STATUS  mandatory
    DESCRIPTION
           "This table contains thresholds for Alignment Errors and
            Excessive Bit Error Rate alarms generated by net/user FALC or 
            QFALC.
            Entries in this table are created by IAD4700 at startup of the
            system (one entry for net FALC, one entry for user FALC,
            one entry per port on the IMA module)."
    ::= { isarIFALCMIBObjects  9 }

isarIFALCThresholdsEntry OBJECT-TYPE
    SYNTAX  IsarIFALCThresholdsEntry
    ACCESS  not-accessible
    STATUS  mandatory
    DESCRIPTION
           "Thresholds for one port."
    INDEX   { ifIndex }
    ::= { isarIFALCThresholdsTable  1 }


IsarIFALCThresholdsEntry ::=
    SEQUENCE {
      isarIFALCThresholdsAlignSamplePeriod
        INTEGER,

      isarIFALCThresholdsAlignErr
        INTEGER,

      isarIFALCThresholdsExcBERLower
        INTEGER,

      isarIFALCThresholdsExcBERUpper
        INTEGER

    }

isarIFALCThresholdsAlignSamplePeriod OBJECT-TYPE
    SYNTAX  INTEGER (0..65535)
    ACCESS  read-write
    STATUS  mandatory
    DESCRIPTION
           "Alignment Sample Period for specified (Q)FALC.
            A write action with value 0 is not allowed (0 = read-only).
            Value 0 indicates that the firmware was not able
            to set the new period.  Threshold checking is stopped."
    DEFVAL { 5 }
    ::= { isarIFALCThresholdsEntry  1 }


isarIFALCThresholdsAlignErr OBJECT-TYPE
    SYNTAX  INTEGER (0..65535)
    ACCESS  read-write
    STATUS  mandatory
    DESCRIPTION
           "Alignment Error Threshold for specified (Q)FALC.
            A write action with value 0 is not allowed (0 = read-only).
            Value 0 indicates that the firmware was not able
            to set the new threshold.  Threshold checking is stopped."
    DEFVAL { 990 }
    ::= { isarIFALCThresholdsEntry  2 }

isarIFALCThresholdsExcBERLower OBJECT-TYPE
    SYNTAX  INTEGER (0..65535)
    ACCESS  read-write
    STATUS  mandatory
    DESCRIPTION
           "Lower Excessive Bit Error Rate Threshold for specified (Q)FALC.
            A write action with value 0 is not allowed (0 = read-only).
            Value 0 indicates that the firmware was not able
            to set the new threshold.  Threshold checking is stopped."
    DEFVAL { 22 }
    ::= { isarIFALCThresholdsEntry  3 }


isarIFALCThresholdsExcBERUpper OBJECT-TYPE
    SYNTAX  INTEGER (0..65535)
    ACCESS  read-write
    STATUS  mandatory
    DESCRIPTION
           "Upper Excessive Bit Error Rate Threshold for specified (Q)FALC.
            A write action with value 0 is not allowed (0 = read-only).
            Value 0 indicates that the firmware was not able
            to set the new threshold.  Threshold checking is stopped."
    DEFVAL { 25 }
    ::= { isarIFALCThresholdsEntry  4 }




-- memory pool
    
isarImemPoolObjects  OBJECT IDENTIFIER ::= 
                                   { isarIsystemMIBObjects  25 }
                                   
isarImemPoolNo OBJECT-TYPE
    SYNTAX  INTEGER (0..32)
    ACCESS  read-only
    STATUS  mandatory
    DESCRIPTION
           "The number of the memory pool that is empty.
            For internal use only.  Not to be displayed."
    ::= { isarImemPoolObjects 1 }


isarImemPoolEmpty TRAP-TYPE
    ENTERPRISE  isarIsystemTraps
    VARIABLES   { isarImemPoolNo }
    DESCRIPTION
           "Memory pool with number isarImemPoolNo is empty.
            From this moment on, creates are refused by the
            agent."
    ::= 12

isarImemPoolBackAvailable TRAP-TYPE
    ENTERPRISE  isarIsystemTraps
    VARIABLES   { isarImemPoolNo }
    DESCRIPTION
           "Memory pool with number isarImemPoolNo is no
            longer empty.
            From this moment on, creates are again accepted
            by the agent."
    ::= 13


-- IMA

isarIimaGroupTxClockMismatch TRAP-TYPE
    ENTERPRISE  isarIsystemTraps
    DESCRIPTION
           "IMA group: transmit clock modes of far end and near
            end don't match."
    ::= 16

isarIimaGroupTxNoClockMismatch TRAP-TYPE
    ENTERPRISE  isarIsystemTraps
    DESCRIPTION
           "IMA group: transmit clock modes of far end and near
            end match."
    ::= 17


-- persistent store 

isarIrestoreFailed TRAP-TYPE
    ENTERPRISE  isarIsystemTraps
    DESCRIPTION
           "Restore after boot failed (not everything is restored)."
    ::= 18


-- clock settings 

isarIinvalidSettingForCurrentHw TRAP-TYPE
    ENTERPRISE  isarIsystemTraps
    DESCRIPTION
           "The clock setting is invalid for the current
            configuration of the Hw."
    ::= 19

isarIinvalidSettingChangedToDefault TRAP-TYPE
    ENTERPRISE  isarIsystemTraps
    DESCRIPTION
           "The clock setting is invalid for the current
            configuration of the Hw. Clock setting has changed to
            DefaultSetting."
    ::= 20


-- E1 and STM1 error conditions 

isarIe1t1ErrorCondition TRAP-TYPE
    ENTERPRISE  isarIsystemTraps
    VARIABLES { ifIndex,
                ifAdminStatus,
                isarIifOperStatusExt,
                isarIdsx1LineStatus
              }
    DESCRIPTION
           "An indication that an AIS or RDI defect is detected on the 
            E1/T1 port (set alarm).
            OR
            An indication that no AIS and no RDI defect are detected 
            anymore on the E1/T1 port (clear alarm)."
    ::= 21

isarIstm1ErrorCondition TRAP-TYPE
    ENTERPRISE  isarIsystemTraps
    VARIABLES { ifIndex,
                ifAdminStatus,
                isarIifOperStatusExt,
                isarIsonetSectionCurrentStatus,
                isarIsonetLineCurrentStatus,
                isarIsonetPathCurrentStatus,
                isarIsonetAtmCurrentStatus
              }
    DESCRIPTION 
           "An indication that a line AIS, line RDI, path AIS or path 
            RDI defect is detected on the STM1 port (set alarm).
            OR            
            An indication that no line AIS, no line RDI, no path AIS and
            no path RDI defect are detected anymore on the STM1 port 
            (clear alarm)."
    ::= 22


-- bit rate overbooking factors
    
isarIoverbookingObjects  OBJECT IDENTIFIER ::= 
                                   { isarIsystemMIBObjects  27 }
                                   
isarInrtVbrOverbookingsFactor OBJECT-TYPE
    SYNTAX  INTEGER (1000..2000)
    ACCESS  read-write
    STATUS  mandatory
    DESCRIPTION
           "Overbookingsfactor for bandwidth for nrt-VBR traffic.
            The factor is internally devided by 1000.
            A value of 1100 gives a factor of 1.1.  This means that the 
            VCLs that use this traffic type may reserve a bandwidth that 
            is equal to (1.1 * maximum bandwidth).
            Default value = 1000 (= factor 1)."
    ::= { isarIoverbookingObjects 1 }

isarIabrOverbookingsFactor OBJECT-TYPE
    SYNTAX  INTEGER (1000..2000)
    ACCESS  read-write
    STATUS  mandatory
    DESCRIPTION
           "Overbookingsfactor for bandwidth for ABR traffic.
            The factor is internally devided by 1000.
            A value of 1100 gives a factor of 1.1.  This means that the 
            VCLs that use this traffic type may reserve a bandwidth that 
            is equal to (1.1 * maximum bandwidth).
            Default value = 1000 (= factor 1)."
    ::= { isarIoverbookingObjects 2 }

isarIubrPlusOverbookingsFactor OBJECT-TYPE
    SYNTAX  INTEGER (1000..2000)
    ACCESS  read-write
    STATUS  mandatory
    DESCRIPTION
           "Overbookingsfactor for bandwidth for UBR+ traffic.
            The factor is internally devided by 1000.
            A value of 1100 gives a factor of 1.1.  This means that the 
            VCLs that use this traffic type may reserve a bandwidth that 
            is equal to (1.1 * maximum bandwidth).
            Default value = 1000 (= factor 1)."
    ::= { isarIoverbookingObjects 3 }


--
-- ISAR systemMIBObjects : end
--


-- This file cannot be used to create SNMP agent.
-- The file isarOneFile.my has to be used to create the agent.

-- isarIifMIBObjects          OBJECT IDENTIFIER ::= { isar  2 }
  
--
-- ISAR ifMIBobjects : begin
--
-- This MIB is based on one of the MIBs described in IETF RFC 2233
-- The MIB is written for SNMPv1.
-- The textual conventions have been replaced by their base types
-- (because the 45020 does not know these textual conventions).
--

 
isarIifTableLastChange OBJECT-TYPE
    SYNTAX  TimeTicks
    ACCESS  read-only
    STATUS  mandatory
    DESCRIPTION
           "The value of sysUpTime at the time of the last
            creation or deletion of an entry in the ifTable.  If
            the number of entries has been unchanged since the
            last re-initialization of the local network management
            subsystem, then this object contains a zero value."
    ::= { isarIifMIBObjects  5 }


--  ifTable removed because the one of rfc1213 will be used and
--  not an enterprise version
--

--   Extension to the interface table
--

isarIifXTable OBJECT-TYPE
    SYNTAX  SEQUENCE OF IsarIifXEntry
    ACCESS  not-accessible
    STATUS  mandatory
    DESCRIPTION
           "A list of interface entries.  The number of entries
            is given by the value of ifNumber.  This table
            contains additional objects for the interface table."
    ::= { isarIifMIBObjects  1 }

isarIifXEntry OBJECT-TYPE
    SYNTAX  IsarIifXEntry
    ACCESS  not-accessible
    STATUS  mandatory
    DESCRIPTION
           "An entry containing additional management information
            applicable to a particular interface."
    INDEX   { ifIndex }
-- AUGMENTS { ifEntry } 
    ::= { isarIifXTable  1 }

IsarIifXEntry ::=
    SEQUENCE {
      isarIifName
        DisplayString,

      isarIifInMulticastPkts
        Counter,

      isarIifInBroadcastPkts
        Counter,

      isarIifOutMulticastPkts
        Counter,

      isarIifOutBroadcastPkts
        Counter,

      isarIifHCInOctets
        Counter,

      isarIifHCInUcastPkts
        Counter,

      isarIifHCInMulticastPkts
        Counter,

      isarIifHCInBroadcastPkts
        Counter,

      isarIifHCOutOctets
        Counter,

      isarIifHCOutUcastPkts
        Counter,

      isarIifHCOutMulticastPkts
        Counter,

      isarIifHCOutBroadcastPkts
        Counter,

      isarIifLinkUpDownTrapEnable
        INTEGER,

      isarIifHighSpeed
        Gauge,

      isarIifPromiscuousMode
        INTEGER,

      isarIifConnectorPresent
        INTEGER,

      isarIifAlias
        DisplayString,

      isarIifCounterDiscontinuityTime
        TimeTicks,

      isarIifOperStatusExt
        INTEGER,

      isarIifStackNumber
        INTEGER,

      isarIifSlotNumber
        INTEGER,

      isarIifphysPortId
        INTEGER,

      isarIifConnectionIdentifier
        INTEGER

    }

isarIifName OBJECT-TYPE
    SYNTAX  DisplayString
    ACCESS  read-only
    STATUS  mandatory
    DESCRIPTION
           "The textual name of the interface.  The value of this
            object should be the name of the interface as assigned
            by the local device and should be suitable for use in
            commands entered at the device's `console'.  This
            might be a text name, such as `le0' or a simple port
            number, such as `1', depending on the interface naming
            syntax of the device.  If several entries in the
            ifTable together represent a single interface as named
            by the device, then each will have the same value of
            ifName.  Note that for an agent which responds to SNMP
            queries concerning an interface on some other
            (proxied) device, then the value of ifName for such an
            interface is the proxied device's local name for it.

            If there is no local name, or this object is otherwise
            not applicable, then this object contains a zero-
            length string."
    ::= { isarIifXEntry  1 }

isarIifInMulticastPkts OBJECT-TYPE
    SYNTAX  Counter
    ACCESS  read-only
    STATUS  mandatory
    DESCRIPTION
           "The number of packets, delivered by this sub-layer to
            a higher (sub-)layer, which were addressed to a
            multicast address at this sub-layer.  For a MAC layer
            protocol, this includes both Group and Functional
            addresses.

            Discontinuities in the value of this counter can occur
            at re-initialization of the management system, and at
            other times as indicated by the value of
            isarIifCounterDiscontinuityTime."
    ::= { isarIifXEntry  2 }

isarIifInBroadcastPkts OBJECT-TYPE
    SYNTAX  Counter
    ACCESS  read-only
    STATUS  mandatory
    DESCRIPTION
           "The number of packets, delivered by this sub-layer to
            a higher (sub-)layer, which were addressed to a
            broadcast address at this sub-layer.

            Discontinuities in the value of this counter can occur
            at re-initialization of the management system, and at
            other times as indicated by the value of
            isarIifCounterDiscontinuityTime."
    ::= { isarIifXEntry  3 }

isarIifOutMulticastPkts OBJECT-TYPE
    SYNTAX  Counter
    ACCESS  read-only
    STATUS  mandatory
    DESCRIPTION
           "The total number of packets that higher-level
            protocols requested be transmitted, and which were
            addressed to a multicast address at this sub-layer,
            including those that were discarded or not sent.  For
            a MAC layer protocol, this includes both Group and
            Functional addresses.

            Discontinuities in the value of this counter can occur
            at re-initialization of the management system, and at
            other times as indicated by the value of
            isarIifCounterDiscontinuityTime."
    ::= { isarIifXEntry  4 }

isarIifOutBroadcastPkts OBJECT-TYPE
    SYNTAX  Counter
    ACCESS  read-only
    STATUS  mandatory
    DESCRIPTION
           "The total number of packets that higher-level
            protocols requested be transmitted, and which were
            addressed to a broadcast address at this sub-layer,
            including those that were discarded or not sent.

            Discontinuities in the value of this counter can occur
            at re-initialization of the management system, and at
            other times as indicated by the value of
            isarIifCounterDiscontinuityTime."
    ::= { isarIifXEntry  5 }


--
-- High Capacity Counter objects.  These objects are all
-- 64 bit versions of the "basic" ifTable counters.  These
-- objects all have the same basic semantics as their 32-bit
-- counterparts, however for SMIv2, their syntax has been extended
-- to 64 bits.
-- Since SMIv1 doesn't know Counter64, these counters are split
-- into a High and a Low part is.  
-- For the Low part, the entries in the ifTable will be used because 
-- they still have to contain the 32-bit part of 64-bit counters.
-- E.g. ifInOctets reports the least significant 32 bits, while 
-- isarIifHCInOctets reports the most significant 32 bits.
-- Both counters have to be combined to form the 64-bit counter.
-- Some counters have their low and high part in isarIifXTable.
--

isarIifHCInOctets OBJECT-TYPE
    SYNTAX  Counter
    ACCESS  read-only
    STATUS  mandatory
    DESCRIPTION
           "The total number of octets received on the interface,
            including framing characters.  This object is the high 
            part of a 64-bit version of ifInOctets.  The low
            part can be found in ifInOctets of the ifTable.

            Discontinuities in the value of this counter can occur
            at re-initialization of the management system, and at
            other times as indicated by the value of
            isarIifCounterDiscontinuityTime."
    ::= { isarIifXEntry  6 }


isarIifHCInUcastPkts OBJECT-TYPE
    SYNTAX  Counter
    ACCESS  read-only
    STATUS  mandatory
    DESCRIPTION
           "The number of packets, delivered by this sub-layer to
            a higher (sub-)layer, which were not addressed to a
            multicast or broadcast address at this sub-layer.
            This object is the high part of a 64-bit version of 
            ifInUcastPkts.  The low part can be found in
            ifInUcastPkts of the ifTable.

            Discontinuities in the value of this counter can occur
            at re-initialization of the management system, and at
            other times as indicated by the value of
            isarIifCounterDiscontinuityTime."
    ::= { isarIifXEntry  7 }

isarIifHCInMulticastPkts OBJECT-TYPE
    SYNTAX  Counter
    ACCESS  read-only
    STATUS  mandatory
    DESCRIPTION
           "The number of packets, delivered by this sub-layer to
            a higher (sub-)layer, which were addressed to a
            multicast address at this sub-layer.  For a MAC layer
            protocol, this includes both Group and Functional
            addresses.  This object is the high part of a 64-bit 
            version of isarIifInMulticastPkts.  The low part can  
            be found in isarIifInMulticastPkts.

            Discontinuities in the value of this counter can occur
            at re-initialization of the management system, and at
            other times as indicated by the value of
            isarIifCounterDiscontinuityTime."
    ::= { isarIifXEntry  8 }

isarIifHCInBroadcastPkts OBJECT-TYPE
    SYNTAX  Counter
    ACCESS  read-only
    STATUS  mandatory
    DESCRIPTION
           "The number of packets, delivered by this sub-layer to
            a higher (sub-)layer, which were addressed to a
            broadcast address at this sub-layer.  This object is the
            high part of a 64-bit version of isarIifInBroadcastPkts.   
            The low part can be found in isarIifInBroadcastPkts.

            Discontinuities in the value of this counter can occur
            at re-initialization of the management system, and at
            other times as indicated by the value of
            isarIifCounterDiscontinuityTime."
    ::= { isarIifXEntry  9 }

isarIifHCOutOctets OBJECT-TYPE
    SYNTAX  Counter
    ACCESS  read-only
    STATUS  mandatory
    DESCRIPTION
           "The total number of octets transmitted out of the
            interface, including framing characters.  This object
            is the high part of a 64-bit version of ifOutOctets.  
            The low part can be found in ifOutOctets of the ifTable.

            Discontinuities in the value of this counter can occur
            at re-initialization of the management system, and at
            other times as indicated by the value of
            isarIifCounterDiscontinuityTime."
    ::= { isarIifXEntry  10 }

isarIifHCOutUcastPkts OBJECT-TYPE
    SYNTAX  Counter
    ACCESS  read-only
    STATUS  mandatory
    DESCRIPTION
           "The total number of packets that higher-level
            protocols requested be transmitted, and which were not
            addressed to a multicast or broadcast address at this
            sub-layer, including those that were discarded or not
            sent.  This object is the high part of a 64-bit version 
            of ifOutUcastPkts.  The low part can be found in 
            ifOutUcastPkts of the ifTable.

            Discontinuities in the value of this counter can occur
            at re-initialization of the management system, and at
            other times as indicated by the value of
            isarIifCounterDiscontinuityTime."
    ::= { isarIifXEntry  11 }

isarIifHCOutMulticastPkts OBJECT-TYPE
    SYNTAX  Counter
    ACCESS  read-only
    STATUS  mandatory
    DESCRIPTION
           "The total number of packets that higher-level
            protocols requested be transmitted, and which were
            addressed to a multicast address at this sub-layer,
            including those that were discarded or not sent.  For
            a MAC layer protocol, this includes both Group and
            Functional addresses.  This object is the high part of 
            a 64-bit version of isarIifOutMulticastPkts.  The low part
            can be found in isarIifOutMulticastPkts.

            Discontinuities in the value of this counter can occur
            at re-initialization of the management system, and at
            other times as indicated by the value of
            isarIifCounterDiscontinuityTime."
    ::= { isarIifXEntry  12 }

isarIifHCOutBroadcastPkts OBJECT-TYPE
    SYNTAX  Counter
    ACCESS  read-only
    STATUS  mandatory
    DESCRIPTION
           "The total number of packets that higher-level
            protocols requested be transmitted, and which were
            addressed to a broadcast address at this sub-layer,
            including those that were discarded or not sent.  This
            object is the high part of a 64-bit version of 
            isarIifOutBroadcastPkts.  The low part can be found in
            isarIifOutBroadcastPkts.

            Discontinuities in the value of this counter can occur
            at re-initialization of the management system, and at
            other times as indicated by the value of
            isarIifCounterDiscontinuityTime."
    ::= { isarIifXEntry  13 }

isarIifLinkUpDownTrapEnable OBJECT-TYPE
    SYNTAX  INTEGER {
                      enabled(1),
                      disabled(2)
            }
    ACCESS  read-write
    STATUS  mandatory
    DESCRIPTION
           "Indicates whether linkUp/linkDown traps should be
            generated for this interface.

            By default, this object should have the value
            enabled(1) for interfaces which do not operate on
            'top' of any other interface (as defined in the
            ifStackTable), and disabled(2) otherwise."
    ::= { isarIifXEntry  14 }

isarIifHighSpeed OBJECT-TYPE
    SYNTAX  Gauge
    ACCESS  read-only
    STATUS  mandatory
    DESCRIPTION
           "An estimate of the interface's current bandwidth in
            units of 1,000,000 bits per second.  If this object
            reports a value of `n' then the speed of the interface
            is somewhere in the range of `n-500,000' to
            `n+499,999'.  For interfaces which do not vary in
            bandwidth or for those where no accurate estimation
            can be made, this object should contain the nominal
            bandwidth.  For a sub-layer which has no concept of
            bandwidth, this object should be zero."
    ::= { isarIifXEntry  15 }

isarIifPromiscuousMode OBJECT-TYPE
    SYNTAX  INTEGER { 
                      true(1), 
                      false(2) 
            }
    ACCESS  read-only
    STATUS  mandatory
    DESCRIPTION
           "This object has a value of false(2) if this interface
            only accepts packets/frames that are addressed to this
            station.  This object has a value of true(1) when the
            station accepts all packets/frames transmitted on the
            media.  The value true(1) is only legal on certain
            types of media.  If legal, setting this object to a
            value of true(1) may require the interface to be reset
            before becoming effective.

            The value of isarIifPromiscuousMode does not affect the
            reception of broadcast and multicast packets/frames by
            the interface.
            ACCESS changed from read-write to read-only."
    ::= { isarIifXEntry  16 }

isarIifConnectorPresent OBJECT-TYPE
    SYNTAX  INTEGER { 
                      true(1), 
                      false(2) 
            }
    ACCESS  read-only
    STATUS  mandatory
    DESCRIPTION
           "This object has the value 'true(1)' if the interface
            sublayer has a physical connector and the value
            'false(2)' otherwise."
    ::= { isarIifXEntry  17 }

isarIifAlias OBJECT-TYPE
    SYNTAX  DisplayString (SIZE(0..64))
    ACCESS  read-write
    STATUS  mandatory
    DESCRIPTION
           "This object is an 'alias' name for the interface as
            specified by a network manager, and provides a non-
            volatile 'handle' for the interface.

            On the first instantiation of an interface, the value
            of ifAlias associated with that interface is the
            zero-length string.  As and when a value is written
            into an instance of isarIifAlias through a network
            management set operation, then the agent must retain
            the supplied value in the isarIifAlias instance 
            associated with the same interface for as long as that 
            interface remains instantiated, including across all 
            re-initializations/reboots of the network management
            system, including those which result in a change of
            the interface's ifIndex value.

            An example of the value which a network manager might
            store in this object for a WAN interface is the
            (Telco's) circuit number/identifier of the interface.

            Some agents may support write-access only for
            interfaces having particular values of ifType.  An
            agent which supports write access to this object is
            required to keep the value in non-volatile storage,
            but it may limit the length of new values depending on
            how much storage is already occupied by the current
            values for other interfaces."
    ::= { isarIifXEntry  18 }

isarIifCounterDiscontinuityTime OBJECT-TYPE
    SYNTAX  TimeTicks
    ACCESS  read-only
    STATUS  mandatory
    DESCRIPTION
           "The value of sysUpTime on the most recent occasion at
            which any one or more of this interface's counters
            suffered a discontinuity.  The relevant counters are
            the specific instances associated with this interface
            of any Counter or Counter object contained in the
            ifTable or isarIifXTable.  If no such discontinuities 
            have occurred since the last re-initialization of the 
            local management subsystem, then this object contains a 
            zero value."
    ::= { isarIifXEntry  19 }

isarIifOperStatusExt OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "Replaces ifOperStatus of ifTable so that SNMPv2 values can 
            be used. (rfc 2233)
            The current operational state of the interface.  The
            testing(3) state indicates that no operational packets
            can be passed.  If ifAdminStatus is down(2) then
            isarIifOperStatusExt should be down(2).  If ifAdminStatus is
            changed to up(1) then isarIifOperStatusExt should change to
            up(1) if the interface is ready to transmit and
            receive network traffic; it should change to
            dormant(5) if the interface is waiting for external
            actions (such as a serial line waiting for an incoming
            connection); it should remain in the down(2) state if
            and only if there is a fault that prevents it from
            going to the up(1) state; it should remain in the
            notPresent(6) state if the interface has missing
            (typically, hardware) components."
    ::= { isarIifXEntry  20 }

isarIifStackNumber OBJECT-TYPE
    SYNTAX  INTEGER (0..63)
    ACCESS  read-only
    STATUS  mandatory
    DESCRIPTION
           "This object combined with isarIifSlotNumber determines the 
            physical location of the interface and represents the number
            of the IAD4700 in the stack of IAD4700s.
            Stack number is zero when there is no stacking."
    ::= { isarIifXEntry  21 }

isarIifSlotNumber OBJECT-TYPE
    SYNTAX  INTEGER (0..3)
    ACCESS  read-only
    STATUS  mandatory
    DESCRIPTION
           "This object combined with isarIifStackNumber determines the
            physical location of the interface and represents the number
            of the slot in the IAD4700.
            It corresponds to isarIphysSlotId of isarIslotTable."
    ::= { isarIifXEntry  22 }

isarIifphysPortId OBJECT-TYPE
    SYNTAX  INTEGER
    ACCESS  read-only
    STATUS  mandatory
    DESCRIPTION
           "This object corresponds to isarIphysPortId of 
            isarIphysPortTable.
            It is only filled in when the ifIndex belongs to a physical
            port.  If not, the value '-1' must be filled in."
    ::= { isarIifXEntry  23 }

isarIifConnectionIdentifier OBJECT-TYPE
    SYNTAX  INTEGER (0..2147483647)
    ACCESS  read-only
    STATUS  mandatory
    DESCRIPTION
           "The identification of the connection is filled in when an 
            entry in a connection is created.
            A value different from zero indicates that the interface
            is in use by a higher layer interface or by a service (IWF).
            The value itself has no meaning for the operator.
            For IAD4700 intern the value 0-1024 indicates the number of
            connection.  A value > 1024 is one specific connection."
    ::= { isarIifXEntry  24 }


--           The Interface Stack Group
--
-- Implementation of this group is mandatory for all systems
--


isarIifStackTable OBJECT-TYPE
    SYNTAX  SEQUENCE OF IsarIifStackEntry
    ACCESS  not-accessible
    STATUS  mandatory
    DESCRIPTION
           "The table containing information on the relationships
            between the multiple sub-layers of network interfaces.
            In particular, it contains information on which sub-
            layers run 'on top of' which other sub-layers, where
            each sub-layer corresponds to a conceptual row in the
            ifTable.  For example, when the sub-layer with ifIndex
            value x runs over the sub-layer with ifIndex value y,
            then this table contains:

              isarIifStackStatus.x.y=active

            For each ifIndex value, I, which identifies an active
            interface, there are always at least two instantiated
            rows in this table associated with I.  For one of
            these rows, I is the value of isarIifStackHigherLayer; 
            for the other, I is the value of isarIifStackLowerLayer.  
            (If I is not involved in multiplexing, then these are 
            the only two rows associated with I.)

            For example, two rows exist even for an interface
            which has no others stacked on top or below it:

              isarIifStackStatus.0.x=active
              isarIifStackStatus.x.0=active "
    ::= { isarIifMIBObjects  2 }

isarIifStackEntry OBJECT-TYPE
    SYNTAX  IsarIifStackEntry
    ACCESS  not-accessible
    STATUS  mandatory
    DESCRIPTION
           "Information on a particular relationship between two
            sub-layers, specifying that one sub-layer runs on
            'top' of the other sub-layer.  Each sub-layer
            corresponds to a conceptual row in the ifTable."
    INDEX   { isarIifStackHigherLayer,  isarIifStackLowerLayer }
    ::= { isarIifStackTable  1 }

IsarIifStackEntry ::=
    SEQUENCE {
      isarIifStackHigherLayer
        INTEGER,

      isarIifStackLowerLayer
        INTEGER
    }

isarIifStackHigherLayer OBJECT-TYPE
    SYNTAX  INTEGER
    ACCESS  read-only
    STATUS  mandatory
    DESCRIPTION
           "The value of ifIndex corresponding to the higher
            sub-layer of the relationship, i.e., the sub-layer
            which runs on 'top' of the sub-layer identified by the
            corresponding instance of isarIifStackLowerLayer.  If 
            there is no higher sub-layer (below the internetwork 
            layer), then this object has the value 0."
    ::= { isarIifStackEntry  1 }

isarIifStackLowerLayer OBJECT-TYPE
    SYNTAX  INTEGER
    ACCESS  read-only
    STATUS  mandatory
    DESCRIPTION
           "The value of ifIndex corresponding to the lower sub-
            layer of the relationship, i.e., the sub-layer which
            runs 'below' the sub-layer identified by the
            corresponding instance of isarIifStackHigherLayer.  If
            there is no lower sub-layer, then this object has the
            value 0."
    ::= { isarIifStackEntry  2 }

-- isarIifStackStatus  ::= { isarIifStackEntry  3 } : REMOVED


isarIifStackLastChange OBJECT-TYPE
    SYNTAX  TimeTicks
    ACCESS  read-only
    STATUS  mandatory
    DESCRIPTION
           "The value of sysUpTime at the time of the last change
            of the (whole) interface stack.  A change of the
            interface stack is defined to be any creation,
            deletion, or change in value of any instance of
            isarIifStackStatus.  If the interface stack has been
            unchanged since the last re-initialization of the
            local network management subsystem, then this object
            contains a zero value."
    ::= { isarIifMIBObjects  6 }





-- traps are moved to isarIsnmpMIB


--
-- ISAR ifMIBobjects : end
--  



-- This file cannot be used to create SNMP agent.
-- The file isarOneFile.my has to be used to create the agent.


-- isarIsnmpMIBObjects        OBJECT IDENTIFIER ::= { isar  3 }


--
-- ISAR snmpMIBobjects : begin
--
-- This MIB is based on one of the MIBs described in IETF RFC 1907
-- The MIB is written for SNMPv1.
-- The textual conventions have been replaced by their base types
-- (because the 45020 does not know these textual conventions).
-- system, sysORTable removed because explicit for SNMPv2, snmp removed
-- information copied out of rfc1215 (linkUp and linkDown are different
-- in rfc2233)

isarIsnmpTraps OBJECT IDENTIFIER ::= { isarIsnmpMIBObjects  5 }

isarIcoldStart TRAP-TYPE
    ENTERPRISE  isarIsnmpTraps
    DESCRIPTION
           "A coldStart trap signifies that the sending
            protocol entity is reinitializing itself such
            that the agent's configuration or the protocol
            entity implementation may be altered."
    ::= 0

isarIwarmStart TRAP-TYPE
    ENTERPRISE  isarIsnmpTraps
    DESCRIPTION
           "A warmStart trap signifies that the sending
            protocol entity is reinitializing itself such
            that neither the agent configuration nor the
            protocol entity implementation is altered."
    ::= 1

isarIlinkDown TRAP-TYPE
    ENTERPRISE  isarIsnmpTraps
    VARIABLES   { ifIndex }
    DESCRIPTION
           "A linkDown trap signifies that the sending protocol entity
            recognizes a failure in one of the communication links
            represented in the agent's configuration."
    ::= 2

isarIlinkUp TRAP-TYPE
    ENTERPRISE  isarIsnmpTraps
    VARIABLES   { ifIndex }
    DESCRIPTION
           "A linkUp trap signifies that the sending protocol entity
            recognizes that one of the communication links
            represented in the agent's configuration has come up."
    ::= 3

isarIauthenticationFailure TRAP-TYPE
    ENTERPRISE  isarIsnmpTraps
    DESCRIPTION
           "An authenticationFailure trap signifies that
            the sending protocol entity is the addressee
            of a protocol message that is not properly
            authenticated.  While implementations of the
            SNMP must be capable of generating this trap,
            they must also be capable of suppressing the
            emission of such traps via an implementation-
            specific mechanism."
    ::= 4


--
-- ISAR snmpMIBobjects : end
--  




-- This file cannot be used to create SNMP agent.
-- The file isarOneFile.my has to be used to create the agent.


-- isarIds0ChannelMIBObjects  OBJECT IDENTIFIER ::= { isar  4 }


--
-- ISAR ds0ChannelMIBObjects : begin
--  
-- This MIB is based on one of the MIBs described in IETF draft
-- draft-ietf-trunkmib-ds0-mib-08.
-- The MIB is written for SNMPv1.
-- The textual conventions have been replaced by their base types
-- (because the 45020 does not know these textual conventions).


--  This is the MIB module for the DS0channel Interface objects.          
 


-- Replaced textual conventions

-- imported textual conventions

-- TruthValue : Represents a boolean value.
--              More information : see RFC1903
-- is replaced by INTEGER {...}
-- originally used in : dsx0RobbedBitSignalling dsx0TransmitCodesEnable

-- InterfaceIndex : A unique value, greater than zero, for each interface
--                  or interface sub-layer in the managed system.  It is
--                  recommended that values are assigned contiguously
--                  starting from 1.  The value for each interface sub-
--                  layer must remain constant at least from one re-
--                  initialization of the entity's network management
--                 system to the next re-initialization.  See RFC2233.
-- is replaced by INTEGER  (1..2147483647)
-- originally used in : dsx0ChanMappedIfIndex

-- InterfaceIndexOrZero : This textual convention is an extension of the
--                        InterfaceIndex convention.  The latter defines
--                        a greater than zero value used to identify an 
--                        interface or interface sub-layer in the 
--                        managed system.  This extension permits the 
--                        additional value of zero.  The value zero is 
--                        object-specific and must therefore be defined 
--                        as part of the description of any object which
--                        uses this syntax.  See RFC2233.
-- is replaced by INTEGER  (1..2147483647)
-- originally used in : dsx0Ds0BundleMappedIfIndex





          
          
-- The DS0 Config Group

-- Implementation of this group is mandatory for all
-- systems that use a DS0 Interface.

-- The DS0 Config Group consists of two tables:
--    DS0 Configuration Table
--    DS0 Channel Mapping Table

-- The DS0 Configuration Table


isarIdsx0ConfigTable OBJECT-TYPE
    SYNTAX  SEQUENCE OF IsarIdsx0ConfigEntry
    ACCESS  not-accessible
    STATUS  mandatory
    DESCRIPTION
           "The DS0 Configuration table."
    ::= { isarIds0ChannelMIBObjects  1 }

isarIdsx0ConfigEntry OBJECT-TYPE
    SYNTAX  IsarIdsx0ConfigEntry
    ACCESS  not-accessible
    STATUS  mandatory
    DESCRIPTION
           "An entry in the DS0 Configuration table.  There
            is an entry in this table for each DS0 interface."
    INDEX   { ifIndex }
    ::= { isarIdsx0ConfigTable  1 }

IsarIdsx0ConfigEntry ::=
    SEQUENCE {
      isarIdsx0Ds0ChannelNumber
        INTEGER,

      isarIdsx0RobbedBitSignalling
        INTEGER,

      isarIdsx0CircuitIdentifier
        DisplayString,

      isarIdsx0IdleCode
        INTEGER,

      isarIdsx0SeizedCode
        INTEGER,

      isarIdsx0ReceivedCode
        INTEGER,

      isarIdsx0TransmitCodesEnable
        INTEGER,

      isarIdsx0Ds0BundleMappedIfIndex
        INTEGER
    }

isarIdsx0Ds0ChannelNumber OBJECT-TYPE
    SYNTAX  INTEGER (0..31)
    ACCESS  read-only
    STATUS  mandatory
    DESCRIPTION
           "This object indicates the channel number of the
            ds0 on its DS1/E1."
    ::= { isarIdsx0ConfigEntry  1 }

isarIdsx0RobbedBitSignalling OBJECT-TYPE
    SYNTAX  INTEGER { true(1), false(2) }
    ACCESS  read-write
    STATUS  mandatory
    DESCRIPTION
           "This object indicates if Robbed Bit Signalling is
            turned on or off for a given ds0.  This only
            applies to DS0s on a DS1 link.  For E1 links the
            value is always off (false)."
    ::= { isarIdsx0ConfigEntry  2 }

isarIdsx0CircuitIdentifier OBJECT-TYPE
    SYNTAX  DisplayString (SIZE (0..255))
    ACCESS  read-write
    STATUS  mandatory
    DESCRIPTION
           "This object contains the transmission vendor's
            circuit identifier, for the purpose of
            facilitating troubleshooting."
    ::= { isarIdsx0ConfigEntry  3 }

isarIdsx0IdleCode OBJECT-TYPE
    SYNTAX  INTEGER (0..15)
    ACCESS  read-write
    STATUS  mandatory
    DESCRIPTION
           "This object contains the code transmitted in the
            ABCD bits when the ds0 is not connected and
            isarIdsx0TransmitCodesEnable is enabled.  The object
            is a bitmap and the various bit positions are:
                    1     D bit
                    2     C bit
                    4     B bit
                    8     A bit"
    ::= { isarIdsx0ConfigEntry  4 }

isarIdsx0SeizedCode OBJECT-TYPE
    SYNTAX  INTEGER (0..15)
    ACCESS  read-write
    STATUS  mandatory
    DESCRIPTION
           "This object contains the code transmitted in the
            ABCD bits when the ds0 is connected and
            isarIdsx0TransmitCodesEnable is enabled.  The object
            is a bitmap and the various bit positions are:
                    1     D bit
                    2     C bit
                    4     B bit
                    8     A bit"
    ::= { isarIdsx0ConfigEntry  5 }

isarIdsx0ReceivedCode OBJECT-TYPE
    SYNTAX  INTEGER (0..15)
    ACCESS  read-only
    STATUS  mandatory
    DESCRIPTION
           "This object contains the code being received in
            the ABCD bits.  The object is a bitmap and the
            various bit positions are:
                 1     D bit
                 2     C bit
                 4     B bit
                 8     A bit"
    ::= { isarIdsx0ConfigEntry  6 }

isarIdsx0TransmitCodesEnable OBJECT-TYPE
    SYNTAX  INTEGER { true(1), false(2) }
    ACCESS  read-write
    STATUS  mandatory
    DESCRIPTION
           "This object determines if the idle and seized
            codes are transmitted. If the value of this object
            is true then the codes are transmitted."
    ::= { isarIdsx0ConfigEntry  7 }

isarIdsx0Ds0BundleMappedIfIndex OBJECT-TYPE
    SYNTAX  INTEGER (0..2147483647)
    ACCESS  read-only
    STATUS  mandatory
    DESCRIPTION
           "This object indicates the ifIndex value assigned
            by the agent for the ds0Bundle(82) ifEntry to
            which the given ds0(81) ifEntry may belong.

            If the given ds0(81) ifEntry does not belong to
            any ds0Bundle(82) ifEntry, then this object has a
            value of zero.

            While this object provides information that can
            also be found in the isarIifStackTable, it provides
            this same information with a single table lookup,
            rather than by walking the isarIifStackTable to find
            the possibly non-existent ds0Bundle(82) ifEntry
            that may be stacked above the given ds0(81)
            ifTable entry."
    ::= { isarIdsx0ConfigEntry  8 }


-- The DS0 Channel Mapping Table

isarIdsx0ChanMappingTable OBJECT-TYPE
    SYNTAX  SEQUENCE OF IsarIdsx0ChanMappingEntry
    ACCESS  not-accessible
    STATUS  mandatory
    DESCRIPTION
           "The DS0 Channel Mapping table.  This table maps a
            DS0 channel number on a particular DS1/E1 into an
            ifIndex."
    ::= { isarIds0ChannelMIBObjects  3 }

isarIdsx0ChanMappingEntry OBJECT-TYPE
    SYNTAX  IsarIdsx0ChanMappingEntry
    ACCESS  not-accessible
    STATUS  mandatory
    DESCRIPTION
           "An entry in the DS0 Channel Mapping table.  There
            is an entry in this table corresponding to each
            ds0 ifEntry within any interface that is
            channelized to the individual ds0 ifEntry level.

            This table is intended to facilitate mapping from
            channelized interface / channel number to DS0
            ifEntry.  (e.g. mapping (DS1 ifIndex, DS0 Channel
            Number) -> ifIndex)

            While this table provides information that can
            also be found in the isarIifStackTable and
            dsx0ConfigTable, it provides this same information
            with a single table lookup, rather than by walking
            the isarIifStackTable to find the various constituent
            ds0 ifTable entries, and testing various
            isarIdsx0ConfigTable entries to check for the entry
            with the applicable DS0 channel number."
    INDEX   { ifIndex,  isarIdsx0Ds0ChannelNumber }
    ::= { isarIdsx0ChanMappingTable  1 }

IsarIdsx0ChanMappingEntry ::=
    SEQUENCE {
      isarIdsx0ChanMappedIfIndex
        INTEGER
    }

isarIdsx0ChanMappedIfIndex OBJECT-TYPE
    SYNTAX  INTEGER (1..2147483647)
    ACCESS  read-only
    STATUS  mandatory
    DESCRIPTION
           "This object indicates the ifIndex value assigned
            by the agent for the individual ds0 ifEntry that
            corresponds to the given DS0 channel number
            (specified by the INDEX element
            isarIdsx0Ds0ChannelNumber) of the given channelized
            interface (specified by INDEX element ifIndex)."
    ::= { isarIdsx0ChanMappingEntry  1 }



--
-- ISAR ds0ChannelMIBObjects : end
--  



-- This file cannot be used to create SNMP agent.
-- The file isarOneFile.my has to be used to create the agent.


-- isarIds0BundleMIBObjects   OBJECT IDENTIFIER ::= { isar  5 }



--
-- ISAR ds0BundleMIBObjects : begin
--  
-- This MIB is based on one of the MIBs described in IETF draft
-- draft-ietf-trunkmib-ds0-mib-08.
-- The MIB is written for SNMPv1.
-- The textual conventions have been replaced by their base types
-- (because the 45020 does not know these textual conventions).

--  This is the MIB module for the DS0Bundle Interface objects.          
 


-- Replaced textual conventions

-- imported textual conventions

-- TestAndIncr : Represents integer-valued information used for atomic
--               operations.  More information : see RFC1903
-- is replaced by INTEGER (0..2147483647)
-- originally used in : dsx0BundleNextIndex

-- InterfaceIndex : A unique value, greater than zero, for each interface
--                  or interface sub-layer in the managed system.  It is
--                  recommended that values are assigned contiguously
--                  starting from 1.  The value for each interface sub-
--                  layer must remain constant at least from one re-
--                  initialization of the entity's network management
--                 system to the next re-initialization.  See RFC2233.
-- is replaced by INTEGER  (1..2147483647)
-- originally used in : dsx0BundleIfIndex 

-- RowStatus : The RowStatus textual convention is used to manage the
--             creation and deletion of conceptual rows. See RFC1903.
-- is replaced by INTEGER {...}
-- originally used in : dsx0BundleRowStatus dsx0BondRowStatus



 
 
          
--
-- The DS0 Bundle Config Group
--
-- Implementation of this group is mandatory for all
-- systems that use a DS0Bundle Interface.
--
-- The DS0 Bundle Config Group consists of one table:
--    DS0 Bundle Table

--  The DS0 Bundle Table

isarIdsx0BundleNextIndex OBJECT-TYPE
    SYNTAX  INTEGER (0..2147483647)
    ACCESS  read-only
    STATUS  mandatory
    DESCRIPTION
           "This object is used to assist the manager in
            selecting a value for isarIdsx0BundleIndex.  
            The manager has to GET this index before creating a row in 
            isarIdsx0BundleTable."
    ::= { isarIds0BundleMIBObjects 2 }

isarIdsx0BundleTable OBJECT-TYPE
    SYNTAX  SEQUENCE OF IsarIdsx0BundleEntry
    ACCESS  not-accessible
    STATUS  mandatory
    DESCRIPTION
           "There is a row in this table for each ds0Bundle
            in the system.  This table can be used to
            (indirectly) create rows in the ifTable with
            ifType = 'ds0Bundle(82)'.
            
            The operator is not allowed to delete ds0bundles with an ifName
            that starts with Internal_."
    ::= { isarIds0BundleMIBObjects  3 }

isarIdsx0BundleEntry OBJECT-TYPE
    SYNTAX  IsarIdsx0BundleEntry
    ACCESS  not-accessible
    STATUS  mandatory
    DESCRIPTION
           "There is a row in entry in this table for each
            ds0Bundle interface."
    INDEX   { isarIdsx0BundleIndex }
    ::= { isarIdsx0BundleTable  1 }

IsarIdsx0BundleEntry ::=
    SEQUENCE {
      isarIdsx0BundleIndex
        INTEGER,

      isarIdsx0BundleIfIndex
        INTEGER,

      isarIdsx0BundleCircuitIdentifier
        DisplayString,

      isarIdsx0BundleRowStatus
        INTEGER,

      isarIdsx0BundleMap
        INTEGER,

      isarIdsx0BundleLowerLayerIfIndex
        INTEGER,

      isarIdsx0BundleMapString
        OCTET STRING

    }

isarIdsx0BundleIndex OBJECT-TYPE
    SYNTAX  INTEGER (1..2147483647)
    ACCESS  read-only
    STATUS  mandatory
    DESCRIPTION
           "A unique identifier for a ds0Bundle.  This is not
            the same value as ifIndex.  This table is not
            indexed by ifIndex because the manager has to
            choose the index in a createable row and the agent
            must be allowed to select ifIndex values."
    ::= { isarIdsx0BundleEntry  1 }

isarIdsx0BundleIfIndex OBJECT-TYPE
    SYNTAX  INTEGER (1..2147483647)
    ACCESS  read-only
    STATUS  mandatory
    DESCRIPTION
           "The ifIndex value the agent selected for the
            (new) ds0Bundle interface."
    ::= { isarIdsx0BundleEntry  2 }

isarIdsx0BundleCircuitIdentifier OBJECT-TYPE
    SYNTAX  DisplayString (SIZE (0..255))
    ACCESS  read-write
    STATUS  mandatory
    DESCRIPTION
           "This variable contains the transmission vendor's
            circuit identifier, for the purpose of
            facilitating troubleshooting.
            The SNMPv2 MAX-ACCESS is read-create."
    ::= { isarIdsx0BundleEntry  3 }

isarIdsx0BundleRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIdsx0BundleEntry  4 }


isarIdsx0BundleMap OBJECT-TYPE
    SYNTAX  INTEGER
    ACCESS  read-write
    STATUS  mandatory
    DESCRIPTION
           "This is a bitmap that indicates which ds0 channels belong to
            this bundle.  The field is defined as the sum of (2 to the 
            power of isarIdsx0Ds0ChannelNumber-X) where 
            isarIdsx0Ds0ChannelNumber-X (0..31) represents the channels
            belonging to the bundle.
            REMARK : the bundle cannot be changed (only deleted) once it
            is used in a connection (active or not).
            
            REMARK : isarIdsx0BundleMap is not to be used by the 45020
            The agent will refuse a SET that contains a value for both
            isarIdsx0BundleMap and isarIdsx0BundleMapString.
            
            The SNMPv2 MAX-ACCESS is read-create."
    ::= { isarIdsx0BundleEntry  5 }
    
isarIdsx0BundleLowerLayerIfIndex OBJECT-TYPE
    SYNTAX  INTEGER (1..2147483647)
    ACCESS  read-write
    STATUS  mandatory
    DESCRIPTION
           "The ifIndex value of the E1 or S0 port on which the bundle is 
            defined.  The value is determined by the SNMP manager.
            The operator is not allowed to change this value.
            The SNMPv2 MAX-ACCESS is read-create."
    ::= { isarIdsx0BundleEntry  6 }

isarIdsx0BundleMapString OBJECT-TYPE
    SYNTAX  OCTET STRING (SIZE (4))
    ACCESS  read-write
    STATUS  mandatory
    DESCRIPTION
           "This OCTET STRING is for 45020 use only ! (However, the agent
            cannot prevent other management stations to use this object.)
            It contains the same information as isarIdsx0BundleMap.
            
            - isarIdsx0BundleMapString will be converted by the agent into
              isarIdsx0BundleMap at time of SET (of the string).
            - isarIdsx0BundleMap will be converted by the agent into
              isarIdsx0BundleMapString at time of GET (of the string).
              
            The agent will refuse a SET that contains a value for both
            isarIdsx0BundleMap and isarIdsx0BundleMapString.
            
            The SNMPv2 MAX-ACCESS is read-create."
    ::= { isarIdsx0BundleEntry  7 }
    



-- ds0 bundle ifIndex mapping table


isarIdsx0BundleMappingTable OBJECT-TYPE
    SYNTAX  SEQUENCE OF IsarIdsx0BundleMappingEntry
    ACCESS  not-accessible
    STATUS  mandatory
    DESCRIPTION
           "Mapping of ifIndex into isarIdsx0BundleIndex."
    ::= { isarIds0BundleMIBObjects  4 }

isarIdsx0BundleMappingEntry OBJECT-TYPE
    SYNTAX  IsarIdsx0BundleMappingEntry
    ACCESS  not-accessible
    STATUS  mandatory
    DESCRIPTION
           "One row in the isarIdsx0BundleMappingTable."
    INDEX   { ifIndex }
    ::= { isarIdsx0BundleMappingTable  1 }


IsarIdsx0BundleMappingEntry ::=
    SEQUENCE { 
      isarIdsx0BundleMappedIndex
        INTEGER
    }
    
isarIdsx0BundleMappedIndex OBJECT-TYPE
    SYNTAX  INTEGER (1..2147483647)
    ACCESS  read-only
    STATUS  mandatory
    DESCRIPTION
           "The index of the ds0 bundle in
            isarIdsx0BundleTable."
    ::= { isarIdsx0BundleMappingEntry  1 }




--
-- ISAR ds0BundleMIBObjects : end
--  




-- This file cannot be used to create SNMP agent.
-- The file isarOneFile.my has to be used to create the agent.


-- isarIds1MIBObjects         OBJECT IDENTIFIER ::= { isar  6 }



--
-- ISAR ds1MIBObjects : begin
--  
-- This MIB is based on one of the MIBs described in IETF draft
-- draft-ietf-trunkmib-ds1-mib-09.
-- The MIB is written for SNMPv1.
-- The textual conventions have been replaced by their base types
-- (because the 45020 does not know these textual conventions).

-- The MIB module to describe DS1, E1, DS2, and E2 interfaces objects.

-- The DS1 Near End Group

-- The DS1 Near End Group consists of four tables:
--    DS1 Configuration
--    DS1 Current
--    DS1 Interval
--    DS1 Total

-- The DS1 Configuration Table

isarIdsx1ConfigTable OBJECT-TYPE
    SYNTAX  SEQUENCE OF IsarIdsx1ConfigEntry
    ACCESS  not-accessible
    STATUS  mandatory
    DESCRIPTION
           "The DS1 Configuration table."
    ::= { isarIds1MIBObjects  6 }

isarIdsx1ConfigEntry OBJECT-TYPE
    SYNTAX  IsarIdsx1ConfigEntry
    ACCESS  not-accessible
    STATUS  mandatory
    DESCRIPTION
           "An entry in the DS1 Configuration table."
    INDEX   { isarIdsx1LineIndex }
    ::= { isarIdsx1ConfigTable  1 }

IsarIdsx1ConfigEntry ::=
    SEQUENCE {
      isarIdsx1LineIndex
        INTEGER,

      isarIdsx1IfIndex
        INTEGER,

      isarIdsx1TimeElapsed
        INTEGER,

      isarIdsx1ValidIntervals
        INTEGER,

      isarIdsx1LineType
        INTEGER,

      isarIdsx1LineCoding
        INTEGER,

      isarIdsx1SendCode
        INTEGER,

      isarIdsx1CircuitIdentifier
        DisplayString,

      isarIdsx1LoopbackConfig
        INTEGER,

      isarIdsx1LineStatus
        INTEGER,

      isarIdsx1SignalMode
        INTEGER,

      isarIdsx1TransmitClockSource
        INTEGER,

      isarIdsx1Fdl
        INTEGER,

      isarIdsx1InvalidIntervals
        INTEGER,

      isarIdsx1LineLength
        INTEGER,

      isarIdsx1LineStatusLastChange
        TimeTicks,

      isarIdsx1LineStatusChangeTrapEnable
        INTEGER,

      isarIdsx1LoopbackStatus
        INTEGER,

      isarIdsx1Ds1ChannelNumber
        INTEGER,

      isarIdsx1Channelization
        INTEGER,

      isarIdsx1Ebit
        INTEGER,

      isarIdsx1EbitPolarity
        INTEGER,

      isarIdsx1NationalBits
        INTEGER,

      isarIdsx1AccessMode
        INTEGER,

      isarIdsx1RecSensitivity
        INTEGER,

      isarIdsx1LineAttenuation
        INTEGER,

      isarIdsx1LineEqualisation
        INTEGER,

      isarIdsx1DataLink
        INTEGER,
        
      isarIdsx1RaiFormat
        INTEGER,

      isarIdsx1InfoLock
        INTEGER,

      isarIdsx1RefClock
        INTEGER,

      isarIdsx1LoopTimeslot
        INTEGER
    }

isarIdsx1LineIndex OBJECT-TYPE
    SYNTAX  INTEGER (1..2147483647)
    ACCESS  read-only
    STATUS  mandatory
    DESCRIPTION
           "This object should be made equal to ifIndex.  The
            next paragraph describes its previous usage.
            Making the object equal to ifIndex allows proper
            use of isarIifStackTable and ds0/ds0bundle mibs.

            Previously, this object is the identifier of a DS1
            Interface on a managed device.  If there is an
            ifEntry that is directly associated with this and
            only this DS1 interface, it should have the same
            value as ifIndex.  Otherwise, number the
            isarIdsx1LineIndices with an unique identifier
            following the rules of choosing a number that is
            greater than ifNumber and numbering the inside
            interfaces (e.g., equipment side) with even
            numbers and outside interfaces (e.g, network side)
            with odd numbers."
    ::= { isarIdsx1ConfigEntry  1 }

isarIdsx1IfIndex OBJECT-TYPE
    SYNTAX  INTEGER (1..2147483647)
    ACCESS  read-only
    STATUS  deprecated
    DESCRIPTION
           "This value for this object is equal to the value
            of ifIndex from the Interfaces table of MIB II
            (RFC 1213)."
    ::= { isarIdsx1ConfigEntry  2 }

isarIdsx1TimeElapsed OBJECT-TYPE
    SYNTAX  INTEGER (0..899)
    ACCESS  read-only
    STATUS  mandatory
    DESCRIPTION
           "The number of seconds that have elapsed since the
            beginning of the near end current error-
            measurement period."
    ::= { isarIdsx1ConfigEntry  3 }

isarIdsx1ValidIntervals OBJECT-TYPE
    SYNTAX  INTEGER (0..96)
    ACCESS  read-only
    STATUS  mandatory
    DESCRIPTION
           "The number of previous near end intervals for
            which valid data was collected.  The value will be
            96 unless the interface was brought online within
            the last 24 hours, in which case the value will be
            the number of complete 15 minute near end
            intervals since the interface has been online.  In
            the case where the agent is a proxy, it is
            possible that some intervals are unavailable.  In
            this case, this interval is the maximum interval
            number for which valid data is available."
    ::= { isarIdsx1ConfigEntry  4 }

isarIdsx1LineType OBJECT-TYPE
    SYNTAX  INTEGER {
                 other(1),
                 dsx1ESF(2),
                 dsx1D4(3),
                 dsx1E1(4),
                 dsx1E1CRC(5),
                 dsx1E1MF(6),
                 dsx1E1CRCMF(7),
                 dsx1Unframed(8),
                 dsx1E1Unframed(9),
                 dsx1DS2M12(10),
                 dsx2E2(11)
               }
    ACCESS  read-write
    STATUS  mandatory
    DESCRIPTION
           "This variable indicates  the  variety  of  DS1
             Line  implementing  this  circuit.  The type of
            circuit affects the number of bits  per  second
            that  the circuit can reasonably carry, as well
            as the interpretation of the  usage  and  error
            statistics.  The values, in sequence, describe:

            TITLE:         SPECIFICATION:
            dsx1ESF         Extended SuperFrame DS1 (T1.107)
            dsx1D4          AT&T D4 format DS1 (T1.107)
            dsx1E1          ITU-T Recommendation G.704
                             (Table 4a)
            dsx1E1-CRC      ITU-T Recommendation G.704
                             (Table 4b)
            dsxE1-MF        G.704 (Table 4a) with TS16
                             multiframing enabled
            dsx1E1-CRC-MF   G.704 (Table 4b) with TS16
                             multiframing enabled
            dsx1Unframed    DS1 with No Framing
            dsx1E1Unframed  E1 with No Framing (G.703)
            dsx1DS2M12      DS2 frame format (T1.107)
            dsx1E2          E2 frame format (G.704)

            For clarification, the capacity for each E1 type
            is as listed below:
            dsx1E1Unframed - E1, no framing = 32 x 64k = 2048k
            dsx1E1 or dsx1E1CRC - E1, with framing,
               no signalling = 31 x 64k = 1984k
            dsx1E1MF or dsx1E1CRCMF - E1, with framing,
               signalling = 30 x 64k = 1920k

            For further information See ITU-T Recomm G.704"
    ::= { isarIdsx1ConfigEntry  5 }

isarIdsx1LineCoding OBJECT-TYPE
    SYNTAX  INTEGER {
                 dsx1JBZS(1),
                 dsx1B8ZS(2),
                 dsx1HDB3(3),
                 dsx1ZBTSI(4),
                 dsx1AMI(5),
                 other(6),
                 dsx1B6ZS(7)
               }
    ACCESS  read-write
    STATUS  mandatory
    DESCRIPTION
           "This variable describes the variety of Zero Code
            Suppression used on this interface, which in turn
            affects a number of its characteristics.

            dsx1JBZS refers the Jammed Bit Zero Suppression,
            in which the AT&T specification of at least one
            pulse every 8 bit periods is literally implemented
            by forcing a pulse in bit 8 of each channel.
            Thus, only seven bits per channel, or 1.344 Mbps,
            is available for data.

            dsx1B8ZS refers to the use of a specified pattern
            of normal bits and bipolar violations which are
            used to replace a sequence of eight zero bits.

            ANSI Clear Channels may use dsx1ZBTSI, or Zero
            Byte Time Slot Interchange.

            E1 links, with or without CRC, use dsx1HDB3 or
            dsx1AMI.

            dsx1AMI refers to a mode wherein no zero code
            suppression is present and the line encoding does
            not solve the problem directly.  In this
            application, the higher layer must provide data
            which meets or exceeds the pulse density
            requirements, such as inverting HDLC data.

            dsx1B6ZS refers to the user of a specifed pattern
            of normal bits and bipolar violations which are
            used to replace a sequence of six zero bits.  Used
            for DS2."
    ::= { isarIdsx1ConfigEntry  6 }

isarIdsx1SendCode OBJECT-TYPE
    SYNTAX  INTEGER {
                 dsx1SendNoCode(1),
                 dsx1SendLineCode(2),
                 dsx1SendPayloadCode(3),
                 dsx1SendResetCode(4),
                 dsx1SendQRS(5),
                 dsx1Send511Pattern(6),
                 dsx1Send3in24Pattern(7),
                 dsx1SendOtherTestPattern(8)
               }
    ACCESS  read-write
    STATUS  mandatory
    DESCRIPTION
           "This variable indicates what type of code is
            being sent across the DS1 interface by the device.
            Setting this variable causes the interface to send
            the code requested.  The values mean:
            
            dsx1SendNoCode
                sending looped or normal data

            dsx1SendLineCode
                sending a request for a line loopback

            dsx1SendPayloadCode
                sending a request for a payload loopback

            dsx1SendResetCode
                sending a loopback termination request

            dsx1SendQRS
                sending a Quasi-Random Signal  (QRS)  test
                     pattern

            dsx1Send511Pattern
                sending a 511 bit fixed test pattern

            dsx1Send3in24Pattern
                sending a fixed test pattern of 3 bits set
                in 24

            dsx1SendOtherTestPattern
                sending a test pattern  other  than  those
                described by this object"
    ::= { isarIdsx1ConfigEntry  7 }

isarIdsx1CircuitIdentifier OBJECT-TYPE
    SYNTAX  DisplayString (SIZE (0..255))
    ACCESS  read-write
    STATUS  mandatory
    DESCRIPTION
           "This variable contains the transmission vendor's
            circuit identifier, for the purpose of
            facilitating troubleshooting."
    ::= { isarIdsx1ConfigEntry  8 }

isarIdsx1LoopbackConfig OBJECT-TYPE
    SYNTAX  INTEGER {
                 dsx1NoLoop(1),
                 dsx1PayloadLoop(2),
                 dsx1LineLoop(3),
                 dsx1OtherLoop(4),
                 dsx1InwardLoop(5),
                 dsx1DualLoop(6)
               }
    ACCESS  read-write
    STATUS  mandatory
    DESCRIPTION
           "This variable represents the desired loopback
            configuration of the DS1 interface.  Agents
            supporting read/write access should return
            inconsistentValue in response to a requested
            loopback state that the interface does not
            support.  The values mean:

            dsx1NoLoop
             Not in the loopback state.  A device that is not
            capable of performing a loopback on the interface
            shall always return this as its value.

            dsx1PayloadLoop
             The received signal at this interface is looped
            through the device.  Typically the received signal
            is looped back for retransmission after it has
            passed through the device's framing function.

            dsx1LineLoop
             The received signal at this interface does not go
            through the device (minimum penetration) but is
            looped back out.

            dsx1OtherLoop
             IAD4700: TimeslotLoop.

            dsx1InwardLoop
             The transmitted signal at this interface is
            looped back and received by the same interface.
            What is transmitted onto the line is product
            dependent.

            dsx1DualLoop
             Both dsx1LineLoop and dsx1InwardLoop will be
            active simultaneously."
    ::= { isarIdsx1ConfigEntry  9 }

isarIdsx1LineStatus OBJECT-TYPE
    SYNTAX  INTEGER (1..8388607)
    ACCESS  read-only
    STATUS  mandatory
    DESCRIPTION
           "This variable indicates the Line Status of the
            interface.  It contains loopback, failure,
            received 'alarm' and transmitted 'alarms
            information.

            The isarIdsx1LineStatus is a bit map represented as a
            sum, therefore, it can represent multiple failures
            (alarms) and a LoopbackState simultaneously.

            dsx1NoAlarm must be set if and only if no other
            flag is set.

            If the isarIdsx1loopbackState bit is set, the loopback
            in effect can be determined from the
            isarIdsx1loopbackConfig object.
            The various bit positions are:
           1    dsx1NoAlarm           No alarm present
           2    dsx1RcvFarEndLOF      Far end LOF (a.k.a., Yellow Alarm)
           4    dsx1XmtFarEndLOF      Near end sending LOF Indication
           8    dsx1RcvAIS            Far end sending AIS
          16    dsx1XmtAIS            Near end sending AIS
          32    dsx1LossOfFrame       Near end LOF (a.k.a., Red Alarm)
          64    dsx1LossOfSignal      Near end Loss Of Signal
         128    dsx1LoopbackState     Near end is looped
         256    dsx1T16AIS            E1 TS16 AIS
         512    dsx1RcvFarEndLOMF     Far End Sending TS16 LOMF
        1024    dsx1XmtFarEndLOMF     Near End Sending TS16 LOMF
        2048    dsx1RcvTestCode       Near End detects a test code
        4096    dsx1OtherFailure      any line status not defined here
        8192    dsx1UnavailSigState   Near End in Unavailable Signal
                                      State
       16384    dsx1NetEquipOOS       Carrier Equipment Out of Service
       32768    dsx1RcvPayloadAIS     DS2 Payload AIS
       65536    dsx1Ds2PerfThreshold  DS2 Performance Threshold
                                      Exceeded
      131072    dsx1ExcBer            excessive bit error rate
      262144    dsx1RdiRai            remote defect indication / remote 
                                      alarm indication
      524288    dsx1Timeout           E1T1Port HW timeout
     1048576    dsx1Shorted           E1T1Port HW in shortcut
     2097152    dsx1Intwk             CRC4 interworking (de)activated
     4194304    dsx1Align             far-end & no CRC4 alignment 
                                      (de)activated
                                      "
    ::= { isarIdsx1ConfigEntry  10 }

isarIdsx1SignalMode OBJECT-TYPE
    SYNTAX  INTEGER {
                 none(1),
                 robbedBit(2),
                 bitOriented(3),
                 messageOriented(4),
                 other(5)
               }
    ACCESS  read-write
    STATUS  mandatory
    DESCRIPTION
           "'none' indicates that no bits are reserved for
             signaling on this channel.

            'robbedBit' indicates that DS1 Robbed Bit  Signaling 
             is in use.

            'bitOriented' indicates that E1 Channel  Associated 
             Signaling is in use.

            'messageOriented' indicates that Common  Channel
             Signaling is in use either on channel 16 of
             an E1 link or channel 24 of a DS1."
    ::= { isarIdsx1ConfigEntry  11 }

isarIdsx1TransmitClockSource OBJECT-TYPE
    SYNTAX  INTEGER {
                 loopTiming(1),
                 localTiming(2),
                 throughTiming(3)
               }
    ACCESS  read-write
    STATUS  mandatory
    DESCRIPTION
           "The source of Transmit Clock.
            'loopTiming' indicates that the recovered receive 
             clock is used as the transmit clock.

            'localTiming' (also called system timed) indicates that a local
             clock source is used or when an external clock is attached
             to the box containing the interface.

            'throughTiming' indicates that recovered receive
             clock from another interface is used as the
             transmit clock.
             
             This object is not applicable to the E1-IMA ports.  The
             configuration is done via isarIimaLinkTransmitClockSource."
    ::= { isarIdsx1ConfigEntry  12 }

isarIdsx1Fdl OBJECT-TYPE
    SYNTAX  INTEGER (1..15)
    ACCESS  read-write
    STATUS  mandatory
    DESCRIPTION
           "This bitmap describes the use of  the  facilities 
            data link, and is the sum of the capabilities.  
            Set any bits that are appropriate:

                 other(1),
                 dsx1AnsiT1403(2),
                 dsx1Att54016(4),
                 dsx1FdlNone(8)

            'other' indicates that a protocol  other  than
             one following is used.

            'dsx1AnsiT1403' refers to the  FDL  exchange
             recommended by ANSI.

             'dsx1Att54016' refers to ESF FDL exchanges.

             'dsx1FdlNone' indicates that the device does
              not use the FDL."
    ::= { isarIdsx1ConfigEntry  13 }

isarIdsx1InvalidIntervals OBJECT-TYPE
    SYNTAX  INTEGER (0..96)
    ACCESS  read-only
    STATUS  mandatory
    DESCRIPTION
           "The number of intervals for which no valid data
            is available."
    ::= { isarIdsx1ConfigEntry  14 }

isarIdsx1LineLength OBJECT-TYPE
    SYNTAX  INTEGER (0..64000)	
 -- UNITS meters

    ACCESS  read-write
    STATUS  mandatory
    DESCRIPTION
           "The length of the ds1 line in meters. This
            objects provides information for line build out
            circuitry.  This object is only useful if the
            interface has configurable line build out
            circuitry."
    ::= { isarIdsx1ConfigEntry  15 }

isarIdsx1LineStatusLastChange OBJECT-TYPE
    SYNTAX  TimeTicks
    ACCESS  read-only
    STATUS  optional
    DESCRIPTION
           "The value of MIB II's sysUpTime object at the
            time this DS1 entered its current line status
            state.  If the current state was entered prior to
            the last re-initialization of the proxy-agent,
            then this object contains a zero value."
    ::= { isarIdsx1ConfigEntry  16 }

isarIdsx1LineStatusChangeTrapEnable OBJECT-TYPE
    SYNTAX  INTEGER {
                 enabled(1),
                 disabled(2)
               }
    ACCESS  read-write
    STATUS  optional
    DESCRIPTION
           "Indicates whether isarIdsx1LineStatusChange traps
            should be generated for this interface."
    DEFVAL  { disabled }
    ::= { isarIdsx1ConfigEntry  17 }

isarIdsx1LoopbackStatus OBJECT-TYPE
    SYNTAX  INTEGER (1..127)
    ACCESS  read-only
    STATUS  mandatory
    DESCRIPTION
           "This variable represents the current state of the
            loopback on the DS1 interface.  It contains
            information about loopbacks established by a
            manager and remotely from the far end.

            The isarIdsx1LoopbackStatus is a bit map represented as
            a sum, therefore is can represent multiple
            loopbacks simultaneously.

            The various bit positions are:
             1  dsx1NoLoopback
             2  dsx1NearEndPayloadLoopback
             4  dsx1NearEndLineLoopback
             8  dsx1NearEndOtherLoopback
            16  dsx1NearEndInwardLoopback
            32  dsx1FarEndPayloadLoopback
            64  dsx1FarEndLineLoopback"
    ::= { isarIdsx1ConfigEntry  18 }

isarIdsx1Ds1ChannelNumber OBJECT-TYPE
    SYNTAX  INTEGER (0..28)
    ACCESS  read-only
    STATUS  mandatory
    DESCRIPTION
           "This variable represents the channel number of
            the DS1/E1 on its parent Ds2/E2 or DS3/E3.  A
            value of 0 indicated this DS1/E1 does not have a
            parent DS3/E3."
    ::= { isarIdsx1ConfigEntry  19 }

isarIdsx1Channelization OBJECT-TYPE
    SYNTAX  INTEGER {
                      disabled(1),
                      enabledDs0(2),
                      enabledDs1(3)
            }
    ACCESS  read-only
    STATUS  mandatory
    DESCRIPTION
           "Indicates whether this ds1/e1 is channelized or
            unchannelized.  The value of enabledDs0 indicates
            that this is a DS1 channelized into DS0s.  The
            value of enabledDs1 indicated that this is a DS2
            channelized into DS1s.  Setting this value will
            cause the creation or deletion of entries in the
            ifTable for the DS0s that are within the DS1.
            IAD4700 v1 / v2.0 : no unstructured ports"
    ::= { isarIdsx1ConfigEntry  20 }


-- ISAR specific extension

isarIdsx1Ebit OBJECT-TYPE
    SYNTAX  INTEGER {
                      disabled(1),
                      enabled(2)
            }
    ACCESS  read-write
    STATUS  mandatory
    DESCRIPTION
           "Defines whether the E bit is used for indicating CRC results.
            REMARK : this field only applies to E1 links.  For Ds1 links
            the value is always 'disabled'."
    DEFVAL  { disabled }
    ::= { isarIdsx1ConfigEntry  21 }

isarIdsx1EbitPolarity OBJECT-TYPE
    SYNTAX  INTEGER {
                      true(1),
                      false(2)
            }
    ACCESS  read-write
    STATUS  mandatory
    DESCRIPTION
           "Indicates the polarity of the E bit when asynchronous.
            REMARK : this field only applies to E1 links.  For Ds1 links
            the value is always 'false'"
    DEFVAL  { false }
    ::= { isarIdsx1ConfigEntry  22 }

isarIdsx1NationalBits OBJECT-TYPE
    SYNTAX  INTEGER {
                      disabled(1),
                      enabled(2)
            }
    ACCESS  read-write
    STATUS  mandatory
    DESCRIPTION
           "Indicates whether national bits are to be processed.
            REMARK : this field only applies to E1 links.  For Ds1 links
            the value is always 'disabled'."
    DEFVAL  { disabled }
    ::= { isarIdsx1ConfigEntry  23 }

isarIdsx1AccessMode OBJECT-TYPE
    SYNTAX  INTEGER {
                      longHaul(1),
                      shortHaul(2),
                      notApplicable(3)
            }
    ACCESS  read-write
    STATUS  mandatory
    DESCRIPTION
           "Defines the access mode."
    DEFVAL  { notApplicable }
    ::= { isarIdsx1ConfigEntry  24 }

isarIdsx1RecSensitivity OBJECT-TYPE
    SYNTAX  INTEGER
    ACCESS  read-write
    STATUS  mandatory
    DESCRIPTION
           "Defines the receiver sensitivity setting of the termination
            point.  UNIT = dB.
            REMARK : this field only applies to Ds1 links with access mode
            = long haul. The value 0 is used for the others."
    DEFVAL  { 26 }
    ::= { isarIdsx1ConfigEntry  25 }

isarIdsx1LineAttenuation OBJECT-TYPE
    SYNTAX  INTEGER ( 0 | 75 | 150 | 225 )
    ACCESS  read-write
    STATUS  mandatory
    DESCRIPTION
           "Defines the line build out (i.e., equalisation) setting of the
            transmission line at the line termination.  UNIT = 0.1 dB.
            REMARK : this field only applies to Ds1 links with Access mode
            = long haul."
    DEFVAL  { 0 }
    ::= { isarIdsx1ConfigEntry  26 }

isarIdsx1LineEqualisation OBJECT-TYPE
    SYNTAX  INTEGER (1..7)
    ACCESS  read-write
    STATUS  mandatory
    DESCRIPTION
           "Defines the attenuation distortion equalisation setting of 
            the entity.  The value is (internally) mapped to a length in
            meters.  This mapping depends on the type of cable.
            REMARK : this field only applies to Ds1 links with Access mode
            = short haul."
    DEFVAL  { 1 }
    ::= { isarIdsx1ConfigEntry  27 }

isarIdsx1DataLink OBJECT-TYPE
    SYNTAX  INTEGER {
                      disabled(1),
                      enabled(2)
            }
    ACCESS  read-write
    STATUS  mandatory
    DESCRIPTION
           "Defines whether the EOC data link is used or not.
            REMARK : this field only applies to Ds1 links.  For E1 links
            the value is always 'disabled'."
    DEFVAL  { disabled }
    ::= { isarIdsx1ConfigEntry  28 }

isarIdsx1RaiFormat OBJECT-TYPE
    SYNTAX  INTEGER {
                      bit2(1),
                      fsbit(2)
            }
    ACCESS  read-write
    STATUS  mandatory
    DESCRIPTION
           "Defines the RAI format for FS frame format.
            REMARK : this field only applies to Ds1 links.  For E1 links
            the value is always 'disabled'."
    DEFVAL  { bit2 }
    ::= { isarIdsx1ConfigEntry  29 }

isarIdsx1InfoLock OBJECT-TYPE
    SYNTAX  INTEGER {
                      noLock(1),
                      oamFlowF1(2),
                      oamFlowF2(3),
                      oamFlowF3(4)
            }
    ACCESS  read-write
    STATUS  mandatory
    DESCRIPTION
           "Defines the OAM flow that has to be locked on this port."
    DEFVAL  { noLock }
    ::= { isarIdsx1ConfigEntry  30 }

isarIdsx1RefClock OBJECT-TYPE
    SYNTAX  INTEGER {
                      true(1),
                      false(2)
            }
    ACCESS  read-write
    STATUS  obsolete
    DESCRIPTION
           "."
    DEFVAL  { false }
    ::= { isarIdsx1ConfigEntry  31 }

isarIdsx1LoopTimeslot OBJECT-TYPE
    SYNTAX  INTEGER (1..31)
    ACCESS  read-write
    STATUS  mandatory
    DESCRIPTION
           "This object has only meaning when isarIdsx1LoopbackConfig is set to 
            dsx1OtherLoop."
    DEFVAL  { 1 }
    ::= { isarIdsx1ConfigEntry  32 }




-- The DS1 Current Table
-- implementation is mandatory

isarIdsx1CurrentTable OBJECT-TYPE
    SYNTAX  SEQUENCE OF IsarIdsx1CurrentEntry
    ACCESS  not-accessible
    STATUS  mandatory
    DESCRIPTION
           "The DS1 current table contains various statistics
            being collected for the current 15 minute
            interval."
    ::= { isarIds1MIBObjects  7 }

isarIdsx1CurrentEntry OBJECT-TYPE
    SYNTAX  IsarIdsx1CurrentEntry
    ACCESS  not-accessible
    STATUS  mandatory
    DESCRIPTION
           "An entry in the DS1 Current table."
    INDEX   { isarIdsx1CurrentIndex }
    ::= { isarIdsx1CurrentTable  1 }

IsarIdsx1CurrentEntry ::=
    SEQUENCE {
      isarIdsx1CurrentIndex
        INTEGER,

      isarIdsx1CurrentESs
        Gauge,

      isarIdsx1CurrentSESs
        Gauge,

      isarIdsx1CurrentSEFSs
        Gauge,

      isarIdsx1CurrentUASs
        Gauge,

      isarIdsx1CurrentCSSs
        Gauge,

      isarIdsx1CurrentPCVs
        Gauge,

      isarIdsx1CurrentLESs
        Gauge,

      isarIdsx1CurrentBESs
        Gauge,

      isarIdsx1CurrentDMs
        Gauge,

      isarIdsx1CurrentLCVs
        Gauge
    }

isarIdsx1CurrentIndex OBJECT-TYPE
    SYNTAX  INTEGER (1..2147483647)
    ACCESS  read-only
    STATUS  mandatory
    DESCRIPTION
           "The index value which uniquely identifies  the
            DS1 interface to which this entry is applicable.
            The interface identified by a particular value of
            this index is the same interface as identified by
            the same value as an isarIdsx1LineIndex object
            instance."
    ::= { isarIdsx1CurrentEntry  1 }

isarIdsx1CurrentESs OBJECT-TYPE
    SYNTAX  Gauge
    ACCESS  read-only
    STATUS  mandatory
    DESCRIPTION
           "The number of Errored Seconds."
    ::= { isarIdsx1CurrentEntry  2 }

isarIdsx1CurrentSESs OBJECT-TYPE
    SYNTAX  Gauge
    ACCESS  read-only
    STATUS  mandatory
    DESCRIPTION
           "The number of Severely Errored Seconds."
    ::= { isarIdsx1CurrentEntry  3 }

isarIdsx1CurrentSEFSs OBJECT-TYPE
    SYNTAX  Gauge
    ACCESS  read-only
    STATUS  mandatory
    DESCRIPTION
           "The number of Severely Errored Framing Seconds."
    ::= { isarIdsx1CurrentEntry  4 }

isarIdsx1CurrentUASs OBJECT-TYPE
    SYNTAX  Gauge
    ACCESS  read-only
    STATUS  mandatory
    DESCRIPTION
           "The number of Unavailable Seconds."
    ::= { isarIdsx1CurrentEntry  5 }

isarIdsx1CurrentCSSs OBJECT-TYPE
    SYNTAX  Gauge
    ACCESS  read-only
    STATUS  mandatory
    DESCRIPTION
           "The number of Controlled Slip Seconds."
    ::= { isarIdsx1CurrentEntry  6 }

isarIdsx1CurrentPCVs OBJECT-TYPE
    SYNTAX  Gauge
    ACCESS  read-only
    STATUS  mandatory
    DESCRIPTION
           "The number of Path Coding Violations."
    ::= { isarIdsx1CurrentEntry  7 }

isarIdsx1CurrentLESs OBJECT-TYPE
    SYNTAX  Gauge
    ACCESS  read-only
    STATUS  mandatory
    DESCRIPTION
           "The number of Line Errored Seconds."
    ::= { isarIdsx1CurrentEntry  8 }

isarIdsx1CurrentBESs OBJECT-TYPE
    SYNTAX  Gauge
    ACCESS  read-only
    STATUS  mandatory
    DESCRIPTION
           "The number of Bursty Errored Seconds."
    ::= { isarIdsx1CurrentEntry  9 }

isarIdsx1CurrentDMs OBJECT-TYPE
    SYNTAX  Gauge
    ACCESS  read-only
    STATUS  mandatory
    DESCRIPTION
           "The number of Degraded Minutes."
    ::= { isarIdsx1CurrentEntry  10 }

isarIdsx1CurrentLCVs OBJECT-TYPE
    SYNTAX  Gauge
    ACCESS  read-only
    STATUS  mandatory
    DESCRIPTION
           "The number of Line Code Violations (LCVs)."
    ::= { isarIdsx1CurrentEntry  11 }


-- The DS1 Interval Table
-- implementation is mandatory

isarIdsx1IntervalTable OBJECT-TYPE
    SYNTAX  SEQUENCE OF IsarIdsx1IntervalEntry
    ACCESS  not-accessible
    STATUS  mandatory
    DESCRIPTION
           "The DS1 Interval Table contains various
            statistics collected by each DS1 Interface over
            the previous 24 hours of operation.  The past 24
            hours are broken into 96 completed 15 minute
            intervals.  Each row in this table represents one
            such interval (identified by isarIdsx1IntervalNumber)
            for one specific instance (identified by
            isarIdsx1IntervalIndex)."
    ::= { isarIds1MIBObjects  8 }

isarIdsx1IntervalEntry OBJECT-TYPE
    SYNTAX  IsarIdsx1IntervalEntry
    ACCESS  not-accessible
    STATUS  mandatory
    DESCRIPTION
           "An entry in the DS1 Interval table."
    INDEX   { isarIdsx1IntervalIndex, isarIdsx1IntervalNumber }
    ::= { isarIdsx1IntervalTable  1 }

IsarIdsx1IntervalEntry ::=
    SEQUENCE {
      isarIdsx1IntervalIndex
        INTEGER,

      isarIdsx1IntervalNumber
        INTEGER,

      isarIdsx1IntervalESs
        Gauge,

      isarIdsx1IntervalSESs
        Gauge,

      isarIdsx1IntervalSEFSs
        Gauge,

      isarIdsx1IntervalUASs
        Gauge,

      isarIdsx1IntervalCSSs
        Gauge,

      isarIdsx1IntervalPCVs
        Gauge,

      isarIdsx1IntervalLESs
        Gauge,

      isarIdsx1IntervalBESs
        Gauge,

      isarIdsx1IntervalDMs
        Gauge,

      isarIdsx1IntervalLCVs
        Gauge,

      isarIdsx1IntervalValidData
        INTEGER,

      isarIdsx1IntervalTimeStamp
        TimeTicks
    }

isarIdsx1IntervalIndex OBJECT-TYPE
    SYNTAX  INTEGER (1..2147483647)
    ACCESS  read-only
    STATUS  mandatory
    DESCRIPTION
           "The index value which uniquely identifies the DS1
            interface to which this entry is applicable.  The
            interface identified by a particular value of this
            index is the same interface as identified by the
            same value as an isarIdsx1LineIndex object instance."
    ::= { isarIdsx1IntervalEntry  1 }

isarIdsx1IntervalNumber OBJECT-TYPE
    SYNTAX  INTEGER (1..96)
    ACCESS  read-only
    STATUS  mandatory
    DESCRIPTION
           "A number between 1 and 96, where 1 is the most
            recently completed 15 minute interval and 96 is
            the 15 minutes interval completed 23 hours and 45
            minutes prior to interval 1."
    ::= { isarIdsx1IntervalEntry  2 }

isarIdsx1IntervalESs OBJECT-TYPE
    SYNTAX  Gauge
    ACCESS  read-only
    STATUS  mandatory
    DESCRIPTION
           "The number of Errored Seconds."
    ::= { isarIdsx1IntervalEntry  3 }

isarIdsx1IntervalSESs OBJECT-TYPE
    SYNTAX  Gauge
    ACCESS  read-only
    STATUS  mandatory
    DESCRIPTION
           "The number of Severely Errored Seconds."
    ::= { isarIdsx1IntervalEntry  4 }

isarIdsx1IntervalSEFSs OBJECT-TYPE
    SYNTAX  Gauge
    ACCESS  read-only
    STATUS  mandatory
    DESCRIPTION
           "The number of Severely Errored Framing Seconds."
    ::= { isarIdsx1IntervalEntry  5 }

isarIdsx1IntervalUASs OBJECT-TYPE
    SYNTAX  Gauge
    ACCESS  read-only
    STATUS  mandatory
    DESCRIPTION
           "The number of Unavailable Seconds.  This object
            may decrease if the occurance of unavailable
            seconds occurs across an interval boundary."
    ::= { isarIdsx1IntervalEntry  6 }

isarIdsx1IntervalCSSs OBJECT-TYPE
    SYNTAX  Gauge
    ACCESS  read-only
    STATUS  mandatory
    DESCRIPTION
           "The number of Controlled Slip Seconds."
    ::= { isarIdsx1IntervalEntry  7 }

isarIdsx1IntervalPCVs OBJECT-TYPE
    SYNTAX  Gauge
    ACCESS  read-only
    STATUS  mandatory
    DESCRIPTION
           "The number of Path Coding Violations."
    ::= { isarIdsx1IntervalEntry  8 }

isarIdsx1IntervalLESs OBJECT-TYPE
    SYNTAX  Gauge
    ACCESS  read-only
    STATUS  mandatory
    DESCRIPTION
           "The number of Line Errored Seconds."
    ::= { isarIdsx1IntervalEntry  9 }

isarIdsx1IntervalBESs OBJECT-TYPE
    SYNTAX  Gauge
    ACCESS  read-only
    STATUS  mandatory
    DESCRIPTION
           "The number of Bursty Errored Seconds."
    ::= { isarIdsx1IntervalEntry  10 }

isarIdsx1IntervalDMs OBJECT-TYPE
    SYNTAX  Gauge
    ACCESS  read-only
    STATUS  mandatory
    DESCRIPTION
           "The number of Degraded Minutes."
    ::= { isarIdsx1IntervalEntry  11 }

isarIdsx1IntervalLCVs OBJECT-TYPE
    SYNTAX  Gauge
    ACCESS  read-only
    STATUS  mandatory
    DESCRIPTION
           "The number of Line Code Violations."
    ::= { isarIdsx1IntervalEntry  12 }

isarIdsx1IntervalValidData OBJECT-TYPE
    SYNTAX  INTEGER { true(1), false(2) }
    ACCESS  read-only
    STATUS  mandatory
    DESCRIPTION
           "This variable indicates if there is valid data
            for this interval."
    ::= { isarIdsx1IntervalEntry  13 }

isarIdsx1IntervalTimeStamp OBJECT-TYPE
    SYNTAX  TimeTicks
    ACCESS  read-only
    STATUS  mandatory
    DESCRIPTION
           "This variable indicates the start of 
            this interval."
    ::= { isarIdsx1IntervalEntry  14 }




-- The DS1 Total Table
-- implementation is mandatory

isarIdsx1TotalTable OBJECT-TYPE
    SYNTAX  SEQUENCE OF IsarIdsx1TotalEntry
    ACCESS  not-accessible
    STATUS  mandatory
    DESCRIPTION
           "The DS1 Total Table contains the cumulative sum
            of the various statistics for the 24 hour period
            preceding the current interval."
    ::= { isarIds1MIBObjects  9 }

isarIdsx1TotalEntry OBJECT-TYPE
    SYNTAX  IsarIdsx1TotalEntry
    ACCESS  not-accessible
    STATUS  mandatory
    DESCRIPTION
           "An entry in the DS1 Total table."
    INDEX   { isarIdsx1TotalIndex }
    ::= { isarIdsx1TotalTable  1 }

IsarIdsx1TotalEntry ::=
    SEQUENCE {
      isarIdsx1TotalIndex
        INTEGER,

      isarIdsx1TotalESs
        Gauge,

      isarIdsx1TotalSESs
        Gauge,

      isarIdsx1TotalSEFSs
        Gauge,

      isarIdsx1TotalUASs
        Gauge,

      isarIdsx1TotalCSSs
        Gauge,

      isarIdsx1TotalPCVs
        Gauge,

     isarIdsx1TotalLESs
        Gauge,

     isarIdsx1TotalBESs
        Gauge,

      isarIdsx1TotalDMs
        Gauge,

      isarIdsx1TotalLCVs
        Gauge,

      isarIdsx1TotalTimeStamp
        TimeTicks
    }

isarIdsx1TotalIndex OBJECT-TYPE
    SYNTAX  INTEGER (1..2147483647)
    ACCESS  read-only
    STATUS  mandatory
    DESCRIPTION
           "The index value which uniquely identifies the DS1
            interface to which this entry is applicable.  The
            interface identified by a particular value of this
            index is the same interface as identified by the
            same value as an isarIdsx1LineIndex object instance."
    ::= { isarIdsx1TotalEntry  1 }

isarIdsx1TotalESs OBJECT-TYPE
    SYNTAX  Gauge
    ACCESS  read-only
    STATUS  mandatory
    DESCRIPTION
           "The sum of Errored Seconds encountered by a DS1
            interface in the previous 24 hour interval.
            Invalid 15 minute intervals count as 0."
    ::= { isarIdsx1TotalEntry  2 }

isarIdsx1TotalSESs OBJECT-TYPE
    SYNTAX  Gauge
    ACCESS  read-only
    STATUS  mandatory
    DESCRIPTION
           "The number of Severely Errored Seconds
            encountered by a DS1 interface in the previous 24
            hour interval.  Invalid 15 minute intervals count
            as 0."
    ::= { isarIdsx1TotalEntry  3 }

isarIdsx1TotalSEFSs OBJECT-TYPE
    SYNTAX  Gauge
    ACCESS  read-only
    STATUS  mandatory
    DESCRIPTION
           "The number of Severely Errored Framing Seconds
            encountered by a DS1 interface in the previous 24
            hour interval.  Invalid 15 minute intervals count
            as 0."
    ::= { isarIdsx1TotalEntry  4 }

isarIdsx1TotalUASs OBJECT-TYPE
    SYNTAX  Gauge
    ACCESS  read-only
    STATUS  mandatory
    DESCRIPTION
           "The number of Unavailable Seconds encountered by
            a DS1 interface in the previous 24 hour interval.
            Invalid 15 minute intervals count as 0."
    ::= { isarIdsx1TotalEntry  5 }

isarIdsx1TotalCSSs OBJECT-TYPE
    SYNTAX  Gauge
    ACCESS  read-only
    STATUS  mandatory
    DESCRIPTION
           "The number of Controlled Slip Seconds encountered
            by a DS1 interface in the previous 24 hour
            interval.  Invalid 15 minute intervals count as
            0."
    ::= { isarIdsx1TotalEntry  6 }

isarIdsx1TotalPCVs OBJECT-TYPE
    SYNTAX  Gauge
    ACCESS  read-only
    STATUS  mandatory
    DESCRIPTION
           "The number of Path Coding Violations encountered
            by a DS1 interface in the previous 24 hour
            interval.  Invalid 15 minute intervals count as 0."
    ::= { isarIdsx1TotalEntry  7 }

isarIdsx1TotalLESs OBJECT-TYPE
    SYNTAX  Gauge
    ACCESS  read-only
    STATUS  mandatory
    DESCRIPTION
           "The number of Line Errored Seconds encountered by
            a DS1 interface in the previous 24 hour interval.
            Invalid 15 minute intervals count as 0."
    ::= { isarIdsx1TotalEntry  8 }

isarIdsx1TotalBESs OBJECT-TYPE
    SYNTAX  Gauge
    ACCESS  read-only
    STATUS  mandatory
    DESCRIPTION
           "The number of Bursty Errored Seconds (BESs)
            encountered by a DS1 interface in the previous 24
            hour interval. Invalid 15 minute intervals count
            as 0."
    ::= { isarIdsx1TotalEntry  9 }

isarIdsx1TotalDMs OBJECT-TYPE
    SYNTAX  Gauge
    ACCESS  read-only
    STATUS  mandatory
    DESCRIPTION
           "The number of Degraded Minutes (DMs) encountered
            by a DS1 interface in the previous 24 hour
            interval.  Invalid 15 minute intervals count as
            0."
    ::= { isarIdsx1TotalEntry  10 }

isarIdsx1TotalLCVs OBJECT-TYPE
    SYNTAX  Gauge
    ACCESS  read-only
    STATUS  mandatory
    DESCRIPTION
           "The number of Line Code Violations (LCVs)
            encountered by a DS1 interface in the current 15
            minute interval.  Invalid 15 minute intervals
            count as 0."
    ::= { isarIdsx1TotalEntry  11 }

isarIdsx1TotalTimeStamp OBJECT-TYPE
    SYNTAX  TimeTicks
    ACCESS  read-only
    STATUS  mandatory
    DESCRIPTION
           "Time of calculation."
    ::= { isarIdsx1TotalEntry  12 }




-- Ds1 TRAPS

isarIds1Traps OBJECT IDENTIFIER ::= { isarIds1MIBObjects  15 }

isarIdsx1LineStatusChange TRAP-TYPE
    ENTERPRISE  isarIds1Traps
    VARIABLES   { isarIdsx1LineIndex,
                  isarIdsx1LineStatus,
                  isarIdsx1LineStatusLastChange }
    DESCRIPTION
           "An isarIdsx1LineStatusChange trap is sent when the
            value of an instance isarIdsx1LineStatus changes. It
            can be utilized by an NMS to trigger polls.  When
            the line status change results from a higher level
            line status change (i.e. ds3), then no traps for
            the ds1 are sent."
    ::= 1


--
-- ISAR ds1MIBObjects : end
--  




-- This file cannot be used to create SNMP agent.
-- The file isarOneFile.my has to be used to create the agent.

-- isarIlanPortMIBObjects     OBJECT IDENTIFIER ::= { isar  7 }


--
-- ISAR lanPortMIBObjects : begin
--  
-- enterprise MIB for configuration of LAN port
-- The MIB is written for SNMPv1.




-- LAN port table


isarIlanPortConfigTable OBJECT-TYPE
    SYNTAX  SEQUENCE OF IsarIlanPortConfigEntry
    ACCESS  not-accessible
    STATUS  mandatory
    DESCRIPTION
           "Configuration of LAN port.
            The rows in this table are created by IAD4700 after creation of
            an entry in the ifTable."
    ::= { isarIlanPortMIBObjects  1 }

isarIlanPortConfigEntry OBJECT-TYPE
    SYNTAX  IsarIlanPortConfigEntry
    ACCESS  not-accessible
    STATUS  mandatory
    DESCRIPTION
           "One row in the isarIlanPortConfigTable."
    INDEX   { ifIndex }
    ::= { isarIlanPortConfigTable  1 }


IsarIlanPortConfigEntry ::=
    SEQUENCE { 
      isarIlanPortSpeed
        INTEGER,
        
      isarIlanPortDuplex
        INTEGER,
        
      isarIlanPortStatistics
        INTEGER,
        
      isarIlanPortCurrentSpeed
        INTEGER,
        
      isarIlanPortCurrentDuplex
        INTEGER

    }
    
isarIlanPortSpeed OBJECT-TYPE
    SYNTAX  INTEGER {
                      speed100Mbit(1),
                      speed10Mbit(2),
                      speed10or100Mbit(3)
            }
    ACCESS  read-write
    STATUS  mandatory
    DESCRIPTION
           "Required speed of LAN port.  Look at isarIlanPortCurrentSpeed
            for the actual speed."
    DEFVAL  { speed10Mbit }
    ::= { isarIlanPortConfigEntry  1 }

isarIlanPortDuplex OBJECT-TYPE
    SYNTAX  INTEGER {
                      fullDuplex(1),
                      halfDuplex(2),
                      negotiate(3)
            }
    ACCESS  read-write
    STATUS  mandatory
    DESCRIPTION
           "The required duplex mode of LAN port.  Look at 
            isarIlanPortCurrentDuplex for the actual mode."
    DEFVAL  { halfDuplex }
    ::= { isarIlanPortConfigEntry  2 }

isarIlanPortStatistics OBJECT-TYPE
    SYNTAX  INTEGER {
                      enabled(1),
                      disabled(2)
            }
    ACCESS  read-write
    STATUS  mandatory
    DESCRIPTION
           "Enable or disable the collection of statistics.
            The statistics objects are defined in rfc1643 and in
            isarIlanPortStatsTable."
    DEFVAL  { disabled }
    ::= { isarIlanPortConfigEntry  3 }

isarIlanPortCurrentSpeed OBJECT-TYPE
    SYNTAX  INTEGER {
                      speed100Mbit(1),
                      speed10Mbit(2),
                      speed10or100Mbit(3)
            }
    ACCESS  read-only
    STATUS  mandatory
    DESCRIPTION
           "Current speed of LAN port.  Look at isarIlanPortSpeed for
            the required speed."
    DEFVAL  { speed10Mbit }
    ::= { isarIlanPortConfigEntry  4 }

isarIlanPortCurrentDuplex OBJECT-TYPE
    SYNTAX  INTEGER {
                      fullDuplex(1),
                      halfDuplex(2),
                      negotiate(3)
            }
    ACCESS  read-only
    STATUS  mandatory
    DESCRIPTION
           "The current duplex mode of LAN port.  Look at 
            isarIlanPortDuplex for the required mode."
    DEFVAL  { halfDuplex }
    ::= { isarIlanPortConfigEntry  5 }


-- LAN port statistics table


isarIlanPortStatsTable OBJECT-TYPE
    SYNTAX  SEQUENCE OF IsarIlanPortStatsEntry
    ACCESS  not-accessible
    STATUS  mandatory
    DESCRIPTION
           "Statistics of LAN port (extra to the ones declared in rfc1643).
            The rows in this table are created by IAD4700 after creation of
            an entry in the ifTable."
    ::= { isarIlanPortMIBObjects  3 }

isarIlanPortStatsEntry OBJECT-TYPE
    SYNTAX  IsarIlanPortStatsEntry
    ACCESS  not-accessible
    STATUS  mandatory
    DESCRIPTION
           "One row in the isarIlanPortStatsTable."
    INDEX   { ifIndex }
    ::= { isarIlanPortStatsTable  1 }


IsarIlanPortStatsEntry ::=
    SEQUENCE { 
      isarIlanPortStatsTxUnderrun
        Counter,
        
      isarIlanPortStatsRxOverrun
        Counter

    }
    
isarIlanPortStatsTxUnderrun OBJECT-TYPE
    SYNTAX  Counter
    ACCESS  read-only
    STATUS  mandatory
    DESCRIPTION
           "Transmit underrun."
    DEFVAL  { 0 }
    ::= { isarIlanPortStatsEntry  1 }

isarIlanPortStatsRxOverrun OBJECT-TYPE
    SYNTAX  Counter
    ACCESS  read-only
    STATUS  mandatory
    DESCRIPTION
           "Receive overrun."
    DEFVAL  { 0 }
    ::= { isarIlanPortStatsEntry  2 }


-- TRAP

isarIlanPortTraps OBJECT IDENTIFIER ::= { isarIlanPortMIBObjects  2 }

isarIlanPortJabberDetected TRAP-TYPE
    ENTERPRISE  isarIlanPortTraps
    VARIABLES   { isarIifStackNumber,
                  isarIifSlotNumber,
                  isarIifphysPortId }
    DESCRIPTION
           "Jabber is detected."
    ::= 1

isarIlanPortRemoteFaultDetected TRAP-TYPE
    ENTERPRISE  isarIlanPortTraps
    VARIABLES   { isarIifStackNumber,
                  isarIifSlotNumber,
                  isarIifphysPortId }
    DESCRIPTION
           "A remote fault is detected."
    ::= 2


--
-- ISAR lanPortMIBObjects : end
--  




-- This file cannot be used to create SNMP agent.
-- The file isarOneFile.my has to be used to create the agent.




-- isarIhssiPortMIBObjects  OBJECT IDENTIFIER ::= { isar  8 }



--
-- ISAR hssiPortMIBObjects : begin
--  
-- enterprise MIB for configuration of HSSI (V.35/X.21) port
-- The MIB is written for SNMPv1.

-- REMARK : HSSI is named SI in management applications


-- High speed serial interface (V.35/X.21) port table


isarIhssiConfigTable OBJECT-TYPE
    SYNTAX  SEQUENCE OF IsarIhssiConfigEntry
    ACCESS  not-accessible
    STATUS  mandatory
    DESCRIPTION
           "Configuration of HSSI (V.35/X.21) port.
            The rows in this table are created by IAD4700 after creation of
            an entry in the ifTable."
    ::= { isarIhssiPortMIBObjects  1 }

isarIhssiConfigEntry OBJECT-TYPE
    SYNTAX  IsarIhssiConfigEntry
    ACCESS  not-accessible
    STATUS  mandatory
    DESCRIPTION
           "One row in the isarIhssiConfigTable."
    INDEX   { ifIndex }
    ::= { isarIhssiConfigTable  1 }


IsarIhssiConfigEntry ::=
    SEQUENCE { 
      isarIhssiSpeed
        INTEGER,
        
      isarIhssiClockMode
        INTEGER,

      isarIhssiPortMode
        INTEGER,

      isarIhssiPinConfMode
        INTEGER,

      isarIhssiCtrlLeads
        INTEGER,

      isarIhssiCurrentSpeed
        INTEGER
        
    }
    
isarIhssiSpeed OBJECT-TYPE
    SYNTAX  INTEGER (0..8000000)
    ACCESS  read-write
    STATUS  mandatory
    DESCRIPTION
           "Required Speed (in bits/sec) of HSSI (V.35/X.21) port. The maximum 
            value is 8 Mbits/sec.  Look at isarIhssiCurrentSpeed for the actual
            speed."
    ::= { isarIhssiConfigEntry  1 }

isarIhssiClockMode OBJECT-TYPE
    SYNTAX  INTEGER {
                      dte(1),
                      dce(2),
                      normal(3)
            }
    ACCESS  read-write
    STATUS  mandatory
    DESCRIPTION
           "Clock coming from DTE or DCE side.
            For isarIhssiPinConfMode=x21 only normal clock mode is
            supported."
    DEFVAL  { normal }
    ::= { isarIhssiConfigEntry  2 }

isarIhssiPortMode OBJECT-TYPE
    SYNTAX  INTEGER {
                      dte(1),
                      dce(2)
            }
    ACCESS  read-only
    STATUS  mandatory
    DESCRIPTION
           "Port mode is always DCE."
    DEFVAL  { dce }
    ::= { isarIhssiConfigEntry  3 }

isarIhssiPinConfMode OBJECT-TYPE
    SYNTAX  INTEGER {
                      x21(1),
                      eia530A(2),
                      eia530(3),
                      v35(4),
                      v36(5)
            }
    ACCESS  read-write
    STATUS  mandatory
    DESCRIPTION
           "Pin configuration mode."
    DEFVAL  { eia530A }
    ::= { isarIhssiConfigEntry  4 }

isarIhssiCtrlLeads OBJECT-TYPE
    SYNTAX  INTEGER {
                      enabled(1),
                      disabled(2)
            }
    ACCESS  read-write
    STATUS  mandatory
    DESCRIPTION
           "Control leads enabled means that control signals taht are 
            relevant for the selected pin configuration mode are 
            supported
            For EIA-530A, EIA-530, V35,V36 these are: RTS(105), CTS(106),
            DSR(107), DTR(108), DCD(109).
            For X21 these are: RTS(105), DCD(109).
            When the DTE or cable does not support any of these controls,
            the control leads should be disabled, otherwise, an error is
            assumed (not app. for X21)."
    DEFVAL  { enabled }
    ::= { isarIhssiConfigEntry  5 }

isarIhssiCurrentSpeed OBJECT-TYPE
    SYNTAX  INTEGER (0..8000000)
    ACCESS  read-only
    STATUS  mandatory
    DESCRIPTION
           "Current Speed (in bits/sec) of HSSI (V.35/X.21) port. The maximum 
            value is 8 Mbits/sec.  Look at isarIhssiSpeed for the required
            speed."
    ::= { isarIhssiConfigEntry  6 }




--
-- ISAR hssiPortMIBObjects : end
--  




-- This file cannot be used to create SNMP agent.
-- The file isarOneFile.my has to be used to create the agent.



-- isarIfrnetservMIBObjects   OBJECT IDENTIFIER ::= { isar  9 }


--
-- ISAR frnetservMIBObjects : begin
-- 
-- This MIB is based on the MIB described in IETF draft
-- draft-ietf-frnetmib-frs-mib-02.
-- The MIB is written for SNMPv1.
-- The textual conventions have been replaced by their base types
-- (because the 45020 does not know these textual conventions).

-- Replaced textual conventions

-- imported textual conventions

-- TimeStamp is replaced by TimeTicks


-- RowStatus : The RowStatus textual convention is used to manage the
--             creation and deletion of conceptual rows. See RFC1903.
-- is replaced by INTEGER {...}
-- originally used in : frPVCEndptRowStatus

-- next logical port index value

isarIfrLportNextIndex OBJECT-TYPE
    SYNTAX  INTEGER (0..2147483647)
    ACCESS  read-only
    STATUS  mandatory
    DESCRIPTION
           "This object contains an appropriate value to be used for a
            isarIfrLportIndex when creating entries in the
            isarIfrLportTable.
            The value 0 indicates that no unassigned entries are
            available. To obtain the isarIfrLportIndex  value for
            a new entry, the manager issues a management  protocol
            retrieval operation to obtain the current value of this
            object. After creation of the row, the agent will
            modify the value to the next unassigned index."
    ::= { isarIfrnetservMIBObjects  1 }


-- The Frame Relay Service Logical Port Group

--  the Frame Relay Logical Port Group
--  This table is an interface specific addendum
--  to the generic ifTable from MIB-II.

isarIfrLportTable OBJECT-TYPE
    SYNTAX  SEQUENCE OF IsarIfrLportEntry
    ACCESS  not-accessible
    STATUS  mandatory
    DESCRIPTION
           "The Frame Relay Logical Port Information table.
            When an entry in this table is created it is necessary to
            create an entry in the ifTable.  When an entry of this table
            is deleted, it is necessary to delete the corresponding
            entry in the ifTable."
    ::= { isarIfrnetservMIBObjects  2 }

isarIfrLportEntry OBJECT-TYPE
    SYNTAX  IsarIfrLportEntry
    ACCESS  not-accessible
    STATUS  mandatory
    DESCRIPTION
           "An entry in the Frame Relay Logical Port
            Information table."
    INDEX   { isarIfrLportIndex }
    ::= { isarIfrLportTable  1 }

IsarIfrLportEntry ::=
    SEQUENCE {
      isarIfrLportIndex
        INTEGER,

      isarIfrLportIfIndex
        INTEGER,

      isarIfrLportLowerLayerIfIndex
        INTEGER,

      isarIfrLportNumPlan
        INTEGER,

      isarIfrLportContact
        DisplayString,

      isarIfrLportLocation
        DisplayString,

      isarIfrLportType
        INTEGER,

      isarIfrLportAddrDLCILen
        INTEGER,

      isarIfrLportVCSigProtocol
        INTEGER,

      isarIfrLportServiceIndex
        INTEGER,

      isarIfrLportMaxFrameSize
        INTEGER,

      isarIfrLportRowStatus
        INTEGER,

      isarIfrLportInterworkingType
        INTEGER

    }

isarIfrLportIndex OBJECT-TYPE
    SYNTAX  INTEGER (1..2147483647)
    ACCESS  read-only
    STATUS  mandatory
    DESCRIPTION
           "The index of the frame relay logical port."
    ::= { isarIfrLportEntry  1 }

isarIfrLportIfIndex OBJECT-TYPE
    SYNTAX  INTEGER (1..2147483647)
    ACCESS  read-only
    STATUS  mandatory
    DESCRIPTION
           "The ifIndex of the frame relay logical port.  This index is
            determined after creation of a row in the ifTable."
    ::= { isarIfrLportEntry  2 }

isarIfrLportLowerLayerIfIndex OBJECT-TYPE
    SYNTAX  INTEGER (1..2147483647)
    ACCESS  read-write
    STATUS  mandatory
    DESCRIPTION
           "The ifIndex of the layer on which this frame relay logical 
            port is defined.
            Modify of this value is not allowed.
            The SNMPv2 MAX-ACCESS is read(-only)-create."
    ::= { isarIfrLportEntry  3 }

isarIfrLportNumPlan OBJECT-TYPE
    SYNTAX  INTEGER {
                      other(1),
                      e164(2),
                      x121(3),
                      none(4)
            }
    ACCESS  read-only
    STATUS  mandatory
    DESCRIPTION
           "The value of this object identifies the network
            address numbering plan for this UNI/NNI logical
            port. The network address is the object
            ifPhysAddress. The value none implies that there
            is no ifPhysAddress.  The SNMP proxy-agent will
            return an octet string of zero length for
            ifPhysAddress. The value other means that an
            address has been assigned to this interface, but
            the numbering plan is not enumerated here.

            IAD4700 : will always be equal to 'none'."
    ::= { isarIfrLportEntry  4 }

isarIfrLportContact OBJECT-TYPE
    SYNTAX  DisplayString (SIZE(0..255))
    ACCESS  read-write
    STATUS  mandatory
    DESCRIPTION
           "The value of this object identifies the network
            contact for this UNI/NNI logical port.
            The SNMPv2 MAX-ACCESS is read-create."
    ::= { isarIfrLportEntry  5 }

isarIfrLportLocation OBJECT-TYPE
    SYNTAX  DisplayString (SIZE(0..255))
    ACCESS  read-write
    STATUS  mandatory
    DESCRIPTION
           "The value of this object identifies the Frame
            Relay network location for this UNI/NNI logical
            port.
            Modification of this value is not allowed.
            The SNMPv2 MAX-ACCESS is read(-only)-create."
    ::= { isarIfrLportEntry  6 }

isarIfrLportType OBJECT-TYPE
    SYNTAX  INTEGER {
                      uni(1),
                      nni(2)
            }
    ACCESS  read-write
    STATUS  mandatory
    DESCRIPTION
           "The value of this object identifies the type of
            network interface for this logical port.
            Modification of this value is not allowed.
            The SNMPv2 MAX-ACCESS is read(-only)-create."
    ::= { isarIfrLportEntry  7 }

isarIfrLportAddrDLCILen OBJECT-TYPE
    SYNTAX  INTEGER {
                      twoOctets(2),
                      threeOctets(3),
                      fourOctets(4)
            }
    ACCESS  read-only
    STATUS  mandatory
    DESCRIPTION
           "The value of this object identifies the Q.922
            Address field length and DLCI length for this
            UNI/NNI logical port.

            IAD4700 : will always be equal to 'twoOctets(2)'."
    ::= { isarIfrLportEntry  8 }

isarIfrLportVCSigProtocol OBJECT-TYPE
    SYNTAX  INTEGER {
                      none(1),
                      lmi(2),
                      ansiT1617D(3),
                      ccittQ933A(4)
            }
    ACCESS  read-write
    STATUS  mandatory
    DESCRIPTION
           "The value of this object identifies the Local
            In-Channel Signaling Protocol that is used for
            this frame relay UNI/NNI logical port.
            When the value differs from 'none', meaning that
            a certain LMI type is used, an entry will be created
            in the isarIfrMgtVCSigTable.
            Modification of this value is not allowed.
            The SNMPv2 MAX-ACCESS is read(-only)-create."
    ::= { isarIfrLportEntry  9 }

isarIfrLportServiceIndex OBJECT-TYPE
    SYNTAX  INTEGER
    ACCESS  read-write
    STATUS  mandatory
    DESCRIPTION
           "The index of the service to which this logical port belongs.
            This is the same index as serviceIndex of isarIserviceTable.
            The SNMPv2 MAX-ACCESS is read-(only)-create."
    ::= { isarIfrLportEntry  10 }

isarIfrLportMaxFrameSize OBJECT-TYPE
    SYNTAX  INTEGER (16..8192)
    ACCESS  read-write
    STATUS  mandatory
    DESCRIPTION
           "The value of this object is the size in octets of
            the largest frame relay frame (incl. header) for the
            PVC end-points on the logical port. The value of
            isarIfrLportMaxFrameSize must be less than or equal
            to the corresponding ifMtu for this Frame Relay
            UNI/NNI logical port.
            Modification of this value is not allowed.
            The SNMPv2 MAX-ACCESS is read(-only)-create."
    ::= { isarIfrLportEntry  11 }

isarIfrLportRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
                    }
    ACCESS  read-write
    STATUS  mandatory
    DESCRIPTION
           "This object is used to create and delete rows in the
            isarIfrLportTable.
            The SNMPv2 MAX-ACCESS is read-create."
    ::= { isarIfrLportEntry  12 }

isarIfrLportInterworkingType OBJECT-TYPE
    SYNTAX  INTEGER {
                      serviceinterworking(1),
                      networkinterworking(2)
            }
    ACCESS  read-write
    STATUS  mandatory
    DESCRIPTION
           "The value of this object identifies the type of
            interworking for this logical port.
            Modification of this value is not allowed.
            The SNMPv2 MAX-ACCESS is read-create."
    ::= { isarIfrLportEntry  13 }


-- mapping table

isarIfrLportMappingTable OBJECT-TYPE
    SYNTAX  SEQUENCE OF IsarIfrLportMappingEntry
    ACCESS  not-accessible
    STATUS  mandatory
    DESCRIPTION
           "The Frame Relay Logical Port Information table.
            When an entry in this table is created it is necessary to
            create an entry in the ifTable.  When an entry of this table
            is deleted, it is necessary to delete the corresponding
            entry in the ifTable."
    ::= { isarIfrnetservMIBObjects  7 }

isarIfrLportMappingEntry OBJECT-TYPE
    SYNTAX  IsarIfrLportMappingEntry
    ACCESS  not-accessible
    STATUS  mandatory
    DESCRIPTION
           "An entry in the Frame Relay Logical Port
            Information table."
    INDEX   { isarIfrLportIfIndex }
    ::= { isarIfrLportMappingTable  1 }

IsarIfrLportMappingEntry ::=
    SEQUENCE {
      isarIfrLportMappingIndex
        INTEGER

    }

isarIfrLportMappingIndex OBJECT-TYPE
    SYNTAX  INTEGER (1..2147483647)
    ACCESS  read-only
    STATUS  mandatory
    DESCRIPTION
           "The index of the frame relay logical port."
    ::= { isarIfrLportMappingEntry  1 }


-- the Frame Relay Management VC Signaling Group

-- This Group contains managed objects for the
-- Local In-Channel Signaling Parameters and
-- for signaling errors.

isarIfrMgtVCSigTable OBJECT-TYPE
    SYNTAX  SEQUENCE OF IsarIfrMgtVCSigEntry
    ACCESS  not-accessible
    STATUS  mandatory
    DESCRIPTION
           "The Frame Relay Management VC Signaling
            Parameters and Errors table."
    ::= { isarIfrnetservMIBObjects  3 }

isarIfrMgtVCSigEntry OBJECT-TYPE
    SYNTAX  IsarIfrMgtVCSigEntry
    ACCESS  not-accessible
    STATUS  mandatory
    DESCRIPTION
           "An entry in the Frame Relay Management VC
            Signaling Parameters Errors table."
    INDEX   { isarIfrMgtVCSigLportIfIndex }
    ::= { isarIfrMgtVCSigTable  1 }

IsarIfrMgtVCSigEntry ::=
    SEQUENCE {
      isarIfrMgtVCSigLportIfIndex
        INTEGER,

      isarIfrMgtVCSigProced
        INTEGER,

      isarIfrMgtVCSigAsyncStatusEnabled
        INTEGER,

      isarIfrMgtVCSigUserN391
        INTEGER,

      isarIfrMgtVCSigUserN392
        INTEGER,

      isarIfrMgtVCSigUserN393
        INTEGER,

      isarIfrMgtVCSigUserT391
        INTEGER,

      isarIfrMgtVCSigNetN392
        INTEGER,

      isarIfrMgtVCSigNetN393
        INTEGER,

      isarIfrMgtVCSigNetT392
        INTEGER,

      isarIfrMgtVCSigNetnN4
        INTEGER,

      isarIfrMgtVCSigNetnT3
        INTEGER,

      isarIfrMgtVCSigUserLinkRelErrors
        Counter,

      isarIfrMgtVCSigUserProtErrors
        Counter,

      isarIfrMgtVCSigNetLinkRelErrors
        Counter,

      isarIfrMgtVCSigNetProtErrors
        Counter,

      isarIfrMgtVCSigServiceIndex
        INTEGER
    }

isarIfrMgtVCSigLportIfIndex OBJECT-TYPE
    SYNTAX  INTEGER
    ACCESS  read-only
    STATUS  mandatory
    DESCRIPTION
           "The index in the ifTable that identifies the Frame Relay
            logical port."
    ::= { isarIfrMgtVCSigEntry  1 }

isarIfrMgtVCSigProced OBJECT-TYPE
    SYNTAX  INTEGER {
                      unidirect(1),   -- UNI (net)
                      bidirect(2)     -- NNI or UNI
            }
    ACCESS  read-write
    STATUS  mandatory
    DESCRIPTION
           "The value of this object identifies the Local
            In-Channel Signaling Procedure that is used for
            this UNI/NNI logical port.  Bidirectional
            procedures implies that both user-side and
            network-side procedures are used.
            Bidirectional procedures are optional for UNI,
            (isarIfrLportType is configured as uni(1)).
            When unidirectional procedures are used at the UNI,
            the network side is implemented (DCE).
            The default value for UNI is unidirect(1)."
    ::= { isarIfrMgtVCSigEntry  2 }

isarIfrMgtVCSigAsyncStatusEnabled OBJECT-TYPE
    SYNTAX  INTEGER {
                      enabled(1),
                      disabled(2)
            }
    ACCESS  read-write
    STATUS  mandatory
    DESCRIPTION
           "The value of this object specifies whether the optional
            - single PVC - status messages are used."
    ::= { isarIfrMgtVCSigEntry  3 }

isarIfrMgtVCSigUserN391 OBJECT-TYPE
    SYNTAX  INTEGER (1..255)
    ACCESS  read-write
    STATUS  mandatory
    DESCRIPTION
           "The value of this object identifies the User-side
            N391 full status polling cycle value for this
            UNI/NNI logical port.  If the logical port is not
            performing user-side (bidirectional) procedures,
            then this value is equal to zero. This
            object applies to Q.933 Annex A and T1.617 Annex
            D."
    DEFVAL  { 6 }
    ::= { isarIfrMgtVCSigEntry  4 }

isarIfrMgtVCSigUserN392 OBJECT-TYPE
    SYNTAX  INTEGER (1..10)
    ACCESS  read-write
    STATUS  mandatory
    DESCRIPTION
           "The value of this object identifies the User-side
            N392 error threshold value for this UNI/NNI
            logical port.  If the logical port is not
            performing user-side (bidirectional) procedures,
            then this value is equal to zero. This
            object applies to Q.933 Annex A and T1.617 Annex
            D."
    DEFVAL  { 3 }
    ::= { isarIfrMgtVCSigEntry  5 }

isarIfrMgtVCSigUserN393 OBJECT-TYPE
    SYNTAX  INTEGER (1..10)
    ACCESS  read-write
    STATUS  mandatory
    DESCRIPTION
           "The value of this object identifies the User-side
            N393 monitored events count value for this UNI/NNI
            logical port.  If the logical port is not
            performing user-side (bidirectional) procedures,
            then this value is equal to zero. This
            object applies to Q.933 Annex A and T1.617 Annex
            D."
    DEFVAL  { 4 }
    ::= { isarIfrMgtVCSigEntry  6 }

isarIfrMgtVCSigUserT391 OBJECT-TYPE
    SYNTAX  INTEGER (5..30)
    ACCESS  read-write
    STATUS  mandatory
    DESCRIPTION
           "The value of this object identifies the User-side
            T391 link integrity verification polling timer
            value for this UNI/NNI logical port.  If the
            logical port is not performing user-side
            procedures, then this value is equal to
            zero. This object applies to Q.933
            Annex A and T1.617 Annex D."
    DEFVAL  { 10 }
    ::= { isarIfrMgtVCSigEntry  7 }

isarIfrMgtVCSigNetN392 OBJECT-TYPE
    SYNTAX  INTEGER (1..10)
    ACCESS  read-write
    STATUS  mandatory
    DESCRIPTION
           "The value of this object identifies the Network-
            side N392 error threshold value (nN2 for LMI) for
            this UNI/NNI logical port.  If the logical port is
            not performing network-side procedures, then this
            value is equal to zero. This object
            applies to Q.933 Annex A, T1.617 Annex D and LMI."
    DEFVAL  { 3 }
    ::= { isarIfrMgtVCSigEntry  8 }

isarIfrMgtVCSigNetN393 OBJECT-TYPE
    SYNTAX  INTEGER (1..10)
    ACCESS  read-write
    STATUS  mandatory
    DESCRIPTION
           "The value of this object identifies the Network-
            side N393 monitored events count value (nN3 for
            LMI) for this UNI/NNI logical port.  If the
            logical port is not performing network-side
            procedures, then this value is equal to
            zero. This object applies to Q.933 Annex
            A, T1.617 Annex D and LMI."
    DEFVAL  { 4 }
    ::= { isarIfrMgtVCSigEntry  9 }

isarIfrMgtVCSigNetT392 OBJECT-TYPE
    SYNTAX  INTEGER (5..30)
    ACCESS  read-write
    STATUS  mandatory
    DESCRIPTION
           "The value of this object identifies the Network-
            side T392 polling verification timer value (nT2
            for LMI)  for this UNI/NNI logical port.  If the
            logical port is not performing network-side
            procedures, then this value is equal to
            zero. This object applies to Q.933 Annex
            A, T1.617 Annex D and LMI."
    DEFVAL  { 15 }
    ::= { isarIfrMgtVCSigEntry  10 }

isarIfrMgtVCSigNetnN4 OBJECT-TYPE
    SYNTAX  INTEGER (5..5)
    ACCESS  read-only
    STATUS  mandatory
    DESCRIPTION
           "The value of this object identifies the Network-
            side nN4 maximum status enquires received value
            for this UNI/NNI logical port.  If the logical
            port is not performing network-side procedures or
            is not performing LMI procedures, then this value
            is equal to zero. This object applies
            only to LMI and always has a value of 5."
    ::= { isarIfrMgtVCSigEntry  11 }

isarIfrMgtVCSigNetnT3 OBJECT-TYPE
    SYNTAX  INTEGER (5 | 10 | 15 | 20 | 25 | 30)
    ACCESS  read-write
    STATUS  mandatory
    DESCRIPTION
           "The value of this object identifies the Network-
            side nT3 timer (for nN4 status enquires received)
            value for this UNI/NNI logical port.  If the
            logical port is not performing network-side
            procedures or is not performing LMI procedures,
            then this value is equal to zero. This
            object applies only to LMI."
    DEFVAL  { 20 }
    ::= { isarIfrMgtVCSigEntry  12 }

isarIfrMgtVCSigUserLinkRelErrors OBJECT-TYPE
    SYNTAX  Counter
    ACCESS  read-only
    STATUS  mandatory
    DESCRIPTION
           "The number of user-side local in-channel
            signaling link reliability errors (i.e., non-
            receipt of Status/Status Enquiry messages or
            invalid sequence numbers in a Link Integrity
            Verification Information Element) for this UNI/NNI
            logical port.  If the logical port is not
            performing user-side procedures, then this value
            is equal to zero and not applicable."
    ::= { isarIfrMgtVCSigEntry  13 }

isarIfrMgtVCSigUserProtErrors OBJECT-TYPE
    SYNTAX  Counter
    ACCESS  read-only
    STATUS  mandatory
    DESCRIPTION
           "The number of user-side local in-channel
            signaling protocol errors (i.e., protocol
            discriminator, unnumbered information, message
            type, call reference, and mandatory information
            element errors) for this UNI/NNI logical port.  If
            the logical port is not performing user-side
            procedures, then this value is equal to
            zero and not applicable."
    ::= { isarIfrMgtVCSigEntry  14 }

-- isarIfrMgtVCSigUserChanInactive  { isarIfrMgtVCSigEntry  15 }

isarIfrMgtVCSigNetLinkRelErrors OBJECT-TYPE
    SYNTAX  Counter
    ACCESS  read-only
    STATUS  mandatory
    DESCRIPTION
           "The number of network-side local in-channel
            signaling link reliability errors (i.e., non-
            receipt of Status/Status Enquiry messages or
            invalid sequence numbers in a Link Integrity
            Verification Information Element) for this UNI/NNI
            logical port."
    ::= { isarIfrMgtVCSigEntry  16 }

isarIfrMgtVCSigNetProtErrors OBJECT-TYPE
    SYNTAX  Counter
    ACCESS  read-only
    STATUS  mandatory
    DESCRIPTION
           "The number of network-side local in-channel
            signaling protocol errors (i.e., protocol
            discriminator, message type, call reference, and
            mandatory information element errors) for this
            UNI/NNI logical port."
    ::= { isarIfrMgtVCSigEntry  17 }

-- isarIfrMgtVCSigNetChanInactive  { isarIfrMgtVCSigEntry  18 }

isarIfrMgtVCSigServiceIndex OBJECT-TYPE
    SYNTAX  INTEGER
    ACCESS  read-only
    STATUS  mandatory
    DESCRIPTION
           "The index of the service.
            This is the same index as serviceIndex of isarIserviceTable."
    ::= { isarIfrMgtVCSigEntry  19 }




-- The PVC End-Point Group

-- This table is used to identify the traffic parameters
-- for a bi-directional PVC segment end-point, and it also
-- provides statistics for a PVC segment
-- end-point.

-- A PVC segment end-point is identified by a UNI/NNI
-- logical port index value and DLCI index value.

-- If the Frame Relay service provider allows
-- the Frame Relay CNM subscriber to create, modify
-- or delete PVCs using SNMP, then this table is used
-- to identify and reserve
-- the requested traffic parameters of each
-- PVC segment end-point.
-- Not all implementations will support the
-- capability of creating/modifying/deleting
-- PVCs using SNMP as a feature of Frame Relay
-- CNM service.

-- Uni-directional PVCs are modeled with zero
-- valued traffic parameters in one of the
-- directions (In or Out direction) in this table.


-- The Frame Relay PVC End-point Table

isarIfrPVCEndptTable OBJECT-TYPE
    SYNTAX  SEQUENCE OF IsarIfrPVCEndptEntry
    ACCESS  not-accessible
    STATUS  mandatory
    DESCRIPTION
           "The Frame Relay PVC End-Point table.  This table
            is used to model a PVC end-point.  This table
            contains the traffic parameters and statistics for
            a PVC end-point."
    ::= { isarIfrnetservMIBObjects  4 }

isarIfrPVCEndptEntry OBJECT-TYPE
    SYNTAX  IsarIfrPVCEndptEntry
    ACCESS  not-accessible
    STATUS  mandatory
    DESCRIPTION
           "An entry in the Frame Relay PVC Endpoint table."
    INDEX   { isarIfrPVCEndptLportIfIndex,  isarIfrPVCEndptDLCIIndex }
    ::= { isarIfrPVCEndptTable  1 }

IsarIfrPVCEndptEntry ::=
    SEQUENCE {
      isarIfrPVCEndptLportIfIndex
        INTEGER,

      isarIfrPVCEndptDLCIIndex
        INTEGER,

      isarIfrPVCEndptInBc
        INTEGER,

      isarIfrPVCEndptInBe
        INTEGER,

      isarIfrPVCEndptInCIR
        INTEGER,

      isarIfrPVCEndptOutBc
        INTEGER,

      isarIfrPVCEndptOutBe
        INTEGER,

      isarIfrPVCEndptOutCIR
        INTEGER,

      isarIfrPVCEndptConnectIdentifier
        INTEGER,

      isarIfrPVCEndptRowStatus
        INTEGER,

      isarIfrPVCEndptRcvdSigStatus
        INTEGER,

      isarIfrPVCEndptInFrames
        Counter,

      isarIfrPVCEndptOutFrames
        Counter,

      isarIfrPVCEndptInOctets
        Counter,

      isarIfrPVCEndptOutOctets
        Counter,

      isarIfrPVCEndptServiceIndex
        INTEGER,

      isarIfrPVCEndptInDiscardedFrames
        Counter,

      isarIfrPVCEndptOutDiscardedFrames
        Counter,

      isarIfrPVCEndptInDEFrames
        Counter,

      isarIfrPVCEndptOutDEFrames
        Counter
    }

isarIfrPVCEndptLportIfIndex OBJECT-TYPE
    SYNTAX  INTEGER
    ACCESS  read-only
    STATUS  mandatory
    DESCRIPTION
           "The index in the ifTable that identifies the Frame Relay
            logical port."
    ::= { isarIfrPVCEndptEntry  1 }

isarIfrPVCEndptDLCIIndex OBJECT-TYPE
    SYNTAX  INTEGER (0..1023)
    ACCESS  read-only
    STATUS  mandatory
    DESCRIPTION
           "The value of this object is equal to the DLCI
            value for this PVC end-point.
            Allowed DLCI values depend on the selected LMI type of the 
            frame relay logical port (isarIfrLportVCSigProtocol):
             (1) No LMI selected:     16-1007, 1023
             (2) (Original)LMI:       16-1007
             (3) ANSI T1.617 Annex D: 16-991
             (4) ITU Q.933 Annex A:   16-991."
    DEFVAL  { 16 }
    ::= { isarIfrPVCEndptEntry  2 }

isarIfrPVCEndptInBc OBJECT-TYPE
    SYNTAX  INTEGER (0..2147483647)
    ACCESS  read-write
    STATUS  mandatory
    DESCRIPTION
           "The value of this object is equal to the
            committed burst size (Bc) parameter (measured in
            bits) for this PVC end-point in the ingress
            direction (into the frame relay network).
            Modify of this value is not allowed.
            The SNMPv2 MAX-ACCESS is read(-only)-create."
    ::= { isarIfrPVCEndptEntry  4 }

isarIfrPVCEndptInBe OBJECT-TYPE
    SYNTAX  INTEGER (0..2147483647)
    ACCESS  read-write
    STATUS  mandatory
    DESCRIPTION
           "The value of this object is equal to the excess
            burst size (Be) parameter (measured in bits) for
            this PVC end-point in the ingress direction (into
            the frame relay network).
            Modify of this value is not allowed.
            The SNMPv2 MAX-ACCESS is read(-only)-create."
    ::= { isarIfrPVCEndptEntry  5 }

isarIfrPVCEndptInCIR OBJECT-TYPE
    SYNTAX  INTEGER (0..2147483647)
    ACCESS  read-write
    STATUS  mandatory
    DESCRIPTION
           "The value of this object is equal to the
            committed information rate (CIR) parameter
            (measured in bits per second) for this PVC end-
            point in the ingress direction (into the frame
            relay network).
            Modify of this value is not allowed.
            The SNMPv2 MAX-ACCESS is read(-only)-create."
    ::= { isarIfrPVCEndptEntry  6 }

isarIfrPVCEndptOutBc OBJECT-TYPE
    SYNTAX  INTEGER (0..2147483647)
    ACCESS  read-write
    STATUS  mandatory
    DESCRIPTION
           "The value of this object is equal to the
            committed burst size (Bc) parameter (measured in
            bits) for this PVC end-point in the egress
            direction (out of the frame relay network).
            Modify of this value is not allowed.
            The SNMPv2 MAX-ACCESS is read(-only)-create."
    ::= { isarIfrPVCEndptEntry  8 }

isarIfrPVCEndptOutBe OBJECT-TYPE
    SYNTAX  INTEGER (0..2147483647)
    ACCESS  read-write
    STATUS  mandatory
    DESCRIPTION
           "The value of this object is equal to the excess
            burst size (Be) parameter (measured in bits) for
            this PVC end-point in the egress direction (out of
            the frame relay network).
            Modify of this value is not allowed.
            The SNMPv2 MAX-ACCESS is read(-only)-create."
    ::= { isarIfrPVCEndptEntry  9 }

isarIfrPVCEndptOutCIR OBJECT-TYPE
    SYNTAX  INTEGER (0..2147483647)
    ACCESS  read-write
    STATUS  mandatory
    DESCRIPTION
           "The value of this object is equal to the
            committed information rate (CIR) parameter
            (measured in bits per second) for this PVC end-
            point in the egress direction (out of the frame
            relay network).
            Modify of this value is not allowed.
            The SNMPv2 MAX-ACCESS is read(-only)-create."
    ::= { isarIfrPVCEndptEntry  10 }

isarIfrPVCEndptConnectIdentifier OBJECT-TYPE
    SYNTAX  INTEGER
    ACCESS  read-only
    STATUS  mandatory
    DESCRIPTION
           "This object is used to associate PVC end-points
            as being part of one FR-ATM interworking connection.

            The value of this object is equal to the value of
            isarIfrAtm<Si/Ni>IwfConnIndex, which is in the
            isarIfrAtmSiIwfConnectionTable and
            isarIfrAtmNiIwfConnectionTable.  The value of
            this object is provided by the agent, after the associated
            entries in the isarIfrAtm<Si/Ni>IwfConnectionTable have
            been created.
            This index must be converted via the
            isarIfrAtm<Si/Ni>IwfMapTable when access to the
            corresponding entry in isarIfrAtm<Si/Ni>IwfConnectionTable
            is wanted."
    ::= { isarIfrPVCEndptEntry  11 }

isarIfrPVCEndptRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create new rows in this
            table, modify existing rows, and to delete
            existing rows.  To create a new PVC, the entries
            for the PVC segment end-points in the
            isarIfrPVCEndptTable must first be created.  Next, the
            isarIfrPVCConnectTable is used to associate the Frame
            Relay PVC segment end-points.  In order for the
            manager to have the necessary error diagnostics,
            the isarIfrPVCEndptRowStatus object must initially be
            set to `createAndWait'.  While the
            isarIfrPVCEndptRowStatus object is in the
            `createAndWait' state, the manager can set each
            columnar object and get the necessary error
            diagnostics.  The isarIfrPVCEndptRowStatus object may
            not be set to `active' unless the following
            columnar objects exist in this row:
            isarIfrPVCEndptInMaxFrameSize, isarIfrPVCEndptInBc,
            isarIfrPVCEndptInBe, isarIfrPVCEndptInCIR,
            isarIfrPVCEndptOutMaxFrameSize, isarIfrPVCEndptOutBc,
            isarIfrPVCEndptOutBe, and isarIfrPVCEndptOutCIR.
            The SNMPv2 MAX-ACCESS is read-create."
    ::= { isarIfrPVCEndptEntry  12 }

isarIfrPVCEndptRcvdSigStatus OBJECT-TYPE
    SYNTAX  INTEGER {
                      deleted(1),
                      active(2),
                      inactive(3),
                      none(4)
            }
    ACCESS  read-only
    STATUS  mandatory
    DESCRIPTION
           "The value of this object identifies the PVC
            status received via the local in-channel signaling
            procedures for this PVC end-point.  This object is
            only pertinent for interfaces that perform the
            bidirectional procedures.

            Each value has the following meaning:
              deleted(1):  This PVC is not listed in the full
                           status reports received from the
                           user device.  The object retains
                           this value for as long as the PVC
                           is not listed in the full status
                           reports

              active(2):   This PVC is reported as active, or
                           operational, by the user device.

              inactive(3): This PVC is reported as inactive,
                           or non-operational, by the user
                           device.

              none(4):     This interface is only using the
                           network-side in-channel signaling
                           procedures, so this object does
                           not apply."
    ::= { isarIfrPVCEndptEntry  13 }

isarIfrPVCEndptInFrames OBJECT-TYPE
    SYNTAX  Counter
    ACCESS  read-only
    STATUS  mandatory
    DESCRIPTION
           "The number of frames received by the network
            (ingress) for this PVC end-point. This includes
            any frames discarded by the network due to
            submitting more than Bc + Be data or due to any
            network congestion recovery procedures."
    ::= { isarIfrPVCEndptEntry  14 }

isarIfrPVCEndptOutFrames OBJECT-TYPE
    SYNTAX  Counter
    ACCESS  read-only
    STATUS  mandatory
    DESCRIPTION
           "The number of frames sent by the network (egress)
            regardless of whether they are Bc or Be frames for
            this PVC end-point."
    ::= { isarIfrPVCEndptEntry  15 }

-- isarIfrPVCEndptInDEFrames  { isarIfrPVCEndptEntry  16 }

-- isarIfrPVCEndptInExcessFrames  { isarIfrPVCEndptEntry  17 }

-- isarIfrPVCEndptOutExcessFrames  { isarIfrPVCEndptEntry  18 }

-- isarIfrPVCEndptInDiscards  { isarIfrPVCEndptEntry  19 }

isarIfrPVCEndptInOctets OBJECT-TYPE
    SYNTAX  Counter
    ACCESS  read-only
    STATUS  mandatory
    DESCRIPTION
           "The number of octets received by the network
            (ingress) for this PVC end-point.  This counter
            should only count octets from the beginning of the
            frame relay header field to the end of user data.
            If the network supporting Frame Relay can not
            count octets, then this count should be an
            approximation."
    ::= { isarIfrPVCEndptEntry  20 }

isarIfrPVCEndptOutOctets OBJECT-TYPE
    SYNTAX  Counter
    ACCESS  read-only
    STATUS  mandatory
    DESCRIPTION
           "The number of octets sent by the network (egress)
            for this PVC end-point.  This counter should only
            count octets from the beginning of the frame relay
            header field to the end of user data.  If the
            network supporting Frame Relay can not count
            octets, then this count should be an
            approximation."
    ::= { isarIfrPVCEndptEntry  21 }

-- isarIfrPVCEndptInDiscardsDESet  { isarIfrPVCEndptEntry  22 }

-- isarIfrPVCEndptInFramesFECNSet  { isarIfrPVCEndptEntry  23 }

-- isarIfrPVCEndptOutFramesFECNSet  { isarIfrPVCEndptEntry  24 }

-- isarIfrPVCEndptInFramesBECNSet  { isarIfrPVCEndptEntry  25 }

-- isarIfrPVCEndptOutFramesBECNSet  { isarIfrPVCEndptEntry  26 }

-- isarIfrPVCEndptInCongDiscards  { isarIfrPVCEndptEntry  27 }

-- isarIfrPVCEndptInDECongDiscards  { isarIfrPVCEndptEntry  28 }

-- isarIfrPVCEndptOutCongDiscards  { isarIfrPVCEndptEntry  29 }

-- isarIfrPVCEndptOutDECongDiscards  { isarIfrPVCEndptEntry  30 }

-- isarIfrPVCEndptOutDEFrames  { isarIfrPVCEndptEntry  31 }

isarIfrPVCEndptServiceIndex OBJECT-TYPE
    SYNTAX  INTEGER
    ACCESS  read-only
    STATUS  mandatory
    DESCRIPTION
           "The index of the service.
            This is the same index as serviceIndex of isarIserviceTable."
    ::= { isarIfrPVCEndptEntry  32 }

isarIfrPVCEndptInDiscardedFrames OBJECT-TYPE
    SYNTAX  Counter
    ACCESS  read-only
    STATUS  mandatory
    DESCRIPTION
           "The number of incoming frames that were discarded because they
            didn't fulfill the Frame Relay traffic contract."
    ::= { isarIfrPVCEndptEntry  33 }

isarIfrPVCEndptOutDiscardedFrames OBJECT-TYPE
    SYNTAX  Counter
    ACCESS  read-only
    STATUS  mandatory
    DESCRIPTION
           "The number of outgoing frames that were discarded because they
            didn't fulfill the Frame Relay traffic contract."
    ::= { isarIfrPVCEndptEntry  34 }

isarIfrPVCEndptInDEFrames OBJECT-TYPE
    SYNTAX  Counter
    ACCESS  read-only
    STATUS  mandatory
    DESCRIPTION
           "The number of incoming excess frames on which the DE-bit 
            was set."
    ::= { isarIfrPVCEndptEntry  35 }

isarIfrPVCEndptOutDEFrames OBJECT-TYPE
    SYNTAX  Counter
    ACCESS  read-only
    STATUS  mandatory
    DESCRIPTION
           "The number of outgoing excess frames on which the DE-bit 
            was set."
    ::= { isarIfrPVCEndptEntry  36 }





-- Frame Relay Network Service TRAPS

isarIfrnetservTraps OBJECT IDENTIFIER ::= { isarIfrnetservMIBObjects 8 }

isarIfrPVCEndptStatusChange TRAP-TYPE
    ENTERPRISE  isarIfrnetservTraps
    VARIABLES   { isarIfrPVCEndptServiceIndex,
                  isarIfrPVCEndptLportIfIndex,
                  isarIfrPVCEndptDLCIIndex,
                  isarIfrPVCEndptRcvdSigStatus }
    DESCRIPTION
           "This trap indicates that the indicated PVC endpoint has
            changed state.  This trap is not sent if an FR-LogPort
            changes state; a linkDown or linkUp trap should be
            sent instead."
    ::= 1

--
-- ISAR frnetservMIBObjects : end
--




-- This file cannot be used to create SNMP agent.
-- The file isarOneFile.my has to be used to create the agent.


-- isarIatmfCESMIBObjects     OBJECT IDENTIFIER ::= { isar  10 }


--
-- ISAR atmfCESMIBObjects : begin
--  
-- This MIB is based on the MIB described in ATM Forum document
-- af-vtoa-0078.
-- The MIB is written for SNMPv1.
-- The textual conventions have been replaced by their base types
-- (because the 45020 does not know these textual conventions).


-- Replaced textual conventions

-- imported textual conventions

-- RowStatus : The RowStatus textual convention is used to manage the
--             creation and deletion of conceptual rows.  See RFC1903.
-- is replaced by INTEGER {...}
-- originally used in : atmfCESConfRowStatus

-- InterfaceIndex : A unique value, greater than zero, for each interface
--                  or interface sub-layer in the managed system.  It is
--                  recommended that values are assigned contiguously
--                  starting from 1.  The value for each interface sub-
--                  layer must remain constant at least from one re-
--                  initialization of the entity's network management
--                 system to the next re-initialization.  See RFC2233.
-- is replaced by INTEGER  (1..2147483647)
-- originally used in : atmfCESCbrIndex atmfCESMappingCbrIndex 


-- textual conventions defined in the document

-- VpiInteger : An integer large enough to hold a VPI
-- is replaced by INTEGER (0..4095)
-- originally used in : atmfCESAtmVpi

-- VciInteger : An integer large enough to hold a VCI
-- is replaced by INTEGER (0..65535)
-- originally used in : atmfCESAtmVci

-- CESConnectionPort : Indicates the port associated with a Circuit 
--             Emulationconnection.  Objects of this type are always
--             defined as part of a set that includes
--                fooPort       CESConnectionPort
--                fooVpi        VpiInteger
--                fooVci        VciInteger
--             The interpretation of these objects is as follows:
--             1. If no connection exists, 'fooPort' has a value of 0.
--                Because Interface table entries always have 'ifIndex'
--                values greater than 0, 'fooPort' reliably serves as a
--                'connection exists' flag.
--                If no connection exists, 'fooVpi' and 'fooVci' are 
--                not relevant and have a value of 0.
--             2. If a PVC or SVC exists, 'fooPort' is defined to have
--                the value of the MIB-II/RFC1573 'ifIndex' of the ATM
--                interface associated with the VCC.  The ifType
--                associated with such an ifIndex value is either
--                atm(37) or atmLogical(80). 'fooVpi' and 'fooVci'
--                will contain its VPI/VCI.
-- is replaced by INTEGER (0..2147483647)
-- originally used in : atmfCESAtmIndex 

-- AtmAddr : The ATM address used by the network entity.  The address
--           types are: no address (0 octets), E.164 (8 octets), and
--           NSAP-encoded ATM Endsystem Address (20 octets).
--           Note: The E.164 address is encoded in BCD format.
--           DISPLAY-HINT "1x"
-- is replaced by OCTET STRING (SIZE(0|8|20))
-- originally used in : atmfCESLocalAddr atmfCESRemoteAddr 




-- This is the MIB module for the ATM Forum Circuit Emulation
-- Service Interoperability Specification Version 2.0.
-- 
-- This MIB contains four tables:
--    CES Configuration Table
--    CES Mapping Table
--    CES Statistics Table
--    CES Active SVC Table


-- CES Configuration Table

isarIatmfCESObjects OBJECT IDENTIFIER ::= { isarIatmfCESMIBObjects  1 }

isarIatmfCESConfTable OBJECT-TYPE
    SYNTAX  SEQUENCE OF IsarIatmfCESConfEntry
    ACCESS  not-accessible
    STATUS  mandatory
    DESCRIPTION
           "The CES configuration table used to manage interworking
            between CBR interfaces or channels and ATM Virtual Channel
            Links (VCLs).  The reverse mapping is shown in the
            isarIatmfCESMappingTable.

            When a row in this table is created, an entry in the
            isarIatmfCESIwfMappingTable is made by IAD4700 (inverse 
            mapping of index).
            
            At the same time another table must be updated :
             - set field isarIatmVclCrossConnectIdentifier of the 
               corresponding entry in IsarIatmVclEntry with the
               value of isarIatmfCESConfIwfConnIndex and
             - set field isarIatmVclServiceType of the 
               corresponding entry in IsarIatmVclEntry to 'ces'."
    ::= { isarIatmfCESObjects  1 }

isarIatmfCESConfEntry OBJECT-TYPE
    SYNTAX  IsarIatmfCESConfEntry
    ACCESS  not-accessible
    STATUS  mandatory
    DESCRIPTION
           "An entry in the CES configuration table.  There is one
            entry in the table per CES entity, mapping one CBR
            interface, channel, or bundle to an ATM VCL.

            Creation of a row in this table with a non-zero
            isarIatmfCESAtmIndex causes a corresponding entry in the
            isarIatmVclTable of the ISAR-ATM-MIB (enterprise based on
            RFC1695) to be created."
    INDEX   { isarIatmfCESCbrIndex }
    ::= { isarIatmfCESConfTable  1 }

IsarIatmfCESConfEntry ::=
    SEQUENCE {
      isarIatmfCESCbrIndex
        INTEGER,

      isarIatmfCESAtmIndex
        INTEGER,

      isarIatmfCESAtmVpi
        INTEGER,

      isarIatmfCESAtmVci
        INTEGER,

      isarIatmfCESCbrService
        INTEGER,

      isarIatmfCESCbrClockMode
        INTEGER,

      isarIatmfCESCas
        INTEGER,

      isarIatmfCESPartialFill
        INTEGER,

      isarIatmfCESBufMaxSize
        INTEGER,

      isarIatmfCESCdvRxT
        INTEGER,

      isarIatmfCESCellLossIntegrationPeriod
        INTEGER,

      isarIatmfCESConnType
        INTEGER,

      isarIatmfCESLocalAddr
        OCTET STRING,

      isarIatmfCESAdminStatus
        INTEGER,

      isarIatmfCESOperStatus
        INTEGER,

      isarIatmfCESConfRowStatus
        INTEGER,

      isarIatmfCESConfServiceIndex
        INTEGER,

      isarIatmfCESConfIwfConnIndex
        INTEGER,

      isarIatmfCESConfUserDefData
        INTEGER,

      isarIatmfCESConfUserDefSigCode1
        INTEGER,

      isarIatmfCESConfUserDefSigCode2
        INTEGER,

      isarIatmfCESConfTCEnabled
        INTEGER,

      isarIatmfCESConfS0PortMap
        INTEGER
    }

isarIatmfCESCbrIndex OBJECT-TYPE
    SYNTAX  INTEGER (1..2147483647)
    ACCESS  not-accessible
    STATUS  mandatory
    DESCRIPTION
           "The value of this object is equal to MIB II's ifIndex value
            of the CBR interface, channel, or bundle that is being
            cross-connected to an ATM VCL."
    ::= { isarIatmfCESConfEntry  1 }

isarIatmfCESAtmIndex OBJECT-TYPE
    SYNTAX  INTEGER (1..2147483647)
    ACCESS  read-write
    STATUS  mandatory
    DESCRIPTION
           "The value of this object is equal to MIB II's
            ifIndex value of the ATM Port interface mapped 
            through this CES IWF to a CBR interface.

            The distinguished value zero indicates that no ATM
            interface has been specified.

            IAD4700 : The ifIndex of the ATM interface to which this
            interworking function belongs.  The value 0 is not allowed
            for IAD4700. Modification of the value is not allowed.
            The SNMPv2 MAX-ACCESS is read-create."
    ::= { isarIatmfCESConfEntry  2 }

isarIatmfCESAtmVpi OBJECT-TYPE
    SYNTAX  INTEGER (0..4095)
    ACCESS  read-write
    STATUS  mandatory
    DESCRIPTION
           "The value of this object is equal to the VPI used
            by the ATM VCL mapped through this CES IWF to a CBR
            interface.
            
            The value is not relevant if no ATM interface has been
            specified (i.e., isarIatmfCESAtmIndex is set to zero).
            
            IAD4700 : The VPI value of the VCL used for this interworking
            function. Modification of the value is not allowed.
            The SNMPv2 MAX-ACCESS is read-create."
    ::= { isarIatmfCESConfEntry  3 }

isarIatmfCESAtmVci OBJECT-TYPE
    SYNTAX  INTEGER (0..65535)
    ACCESS  read-write
    STATUS  mandatory
    DESCRIPTION
           "The value of this object is equal to the VCI used
            by the ATM VCL mapped through this CES IWF to a CBR
            interface.

            The distinguished value zero indicates that no ATM
            VCL has been specified.
            
            IAD4700 : The VCI value of the CVL used for this interworking
            function. Modification of the value is not allowed.
            The SNMPv2 MAX-ACCESS is read-create."
    ::= { isarIatmfCESConfEntry  4 }

isarIatmfCESCbrService OBJECT-TYPE
    SYNTAX  INTEGER {
                      unstructured(1),
                      structured(2)
            }
    ACCESS  read-only
    STATUS  mandatory
    DESCRIPTION
           "Define if DSx/Ex service is structured or unstructured. A
            structured(2) interface is some nx64kbKbps. An unstructured
            (1) interface is 1.544Mbps, 2.048Mbps, 6.312Mbps, 
            44.736 Mbps, or 34.368 Mbps. unstructured(1) passes all bits
            through the ATM network.  strucutured(2) passes data bits 
            through the ATM network, and may also pass signalling bits.
            
            At this time, only unstructured mode is defined for the
            44.736 Mbps and 34.368 Mbps services.
            The SNMPv2 MAX-ACCESS is read-create.
            
            IAD4700 v1 / v2.0 : only the value 'structured' is supported."
    DEFVAL { structured }
    ::= { isarIatmfCESConfEntry  5 }

isarIatmfCESCbrClockMode OBJECT-TYPE
    SYNTAX  INTEGER {
                      synchronous(1),
                      srts(2),
                      adaptive(3)
            }
    ACCESS  read-only
    STATUS  mandatory
    DESCRIPTION
           "Define if DSx/Ex service clocking mode. This maps into
            transmit clock source of CBR interface.

            For structured modes this value, if present, must be set to
            synchronous(1).
            IAD4700 v1 / v2.0 : only the value 'synchronous' is supported."
    DEFVAL  { synchronous }
    ::= { isarIatmfCESConfEntry  6 }

isarIatmfCESCas OBJECT-TYPE
    SYNTAX  INTEGER {
                      basic(1),
                      e1Cas(2),
                      ds1SfCas(3),
                      ds1EsfCas(4),
                      j2Cas(5)
            }
    ACCESS  read-only
    STATUS  mandatory
    DESCRIPTION
           "This parameter selects which AAL1 Format should be used:
            Basic does not carry CAS bits, and uses a single 125 usec 
            frame.
            e1Cas, ds1SfCas, dS1EsfCas and j2Cas carry CAS bits in a
            multiframe structure for E1, DS1 SF, DS1 ESF and J2 
            respectively.
            This applies to structured interfaces only. Default is
            basic (1). For unstructured interfaces this value, if 
            present, must be set to the default of basic (1).

            IAD4700 v1 / v2.0 : only the values 'basic' and 'e1Cas' are
            allowed."
    DEFVAL  { basic }
    ::= { isarIatmfCESConfEntry  7 }

isarIatmfCESPartialFill OBJECT-TYPE
    SYNTAX  INTEGER (0 | 4 .. 47)
    ACCESS  read-write
    STATUS  mandatory
    DESCRIPTION
           "If partial cell fill is used, the number of user octets per
            cell must be set with this parameter.  Setting this 
            parameter to zero disables partial cell fill, and causes all
            cells to be completely filled before they are sent.
            The SNMPv2 MAX-ACCESS is read-create."
    DEFVAL  { 0 }
    ::= { isarIatmfCESConfEntry  8 }

isarIatmfCESBufMaxSize OBJECT-TYPE
    SYNTAX  INTEGER  (1..65536)
    -- UNITS 10 usec
    ACCESS  read-only
    STATUS  mandatory
    DESCRIPTION
           "Define maximum size in 10 microsecond increments of the
            reassembly buffer. Some implementations may want allow the
            maximum buffer size to be programmed to a size less than
            the physical limit to reduce the maximum delay through a 
            circuit."
    DEFVAL  { 128 }
    ::= { isarIatmfCESConfEntry  9 }

isarIatmfCESCdvRxT OBJECT-TYPE
    SYNTAX  INTEGER (1..65535)
    -- UNITS 10 usec
    ACCESS  read-only
    STATUS  mandatory
    DESCRIPTION
           "The maximum cell arrival jitter in 10 usec increments that 
            the reassembly process will tolerate in the cell stream
            without producing errors on the CBR service interface.
            IAD4700 : req. spec : CDV = 1 cell, so this depends on cell
            rate."
    DEFVAL  { 100 }
    ::= { isarIatmfCESConfEntry  10 }

isarIatmfCESCellLossIntegrationPeriod OBJECT-TYPE
    SYNTAX  INTEGER (1000 .. 65535)
    -- UNITS msec
    ACCESS  read-only
    STATUS  mandatory
    DESCRIPTION
           "The time in milliseconds for the cell loss integration 
            period.  If cells are continuously lost for this period 
            of time, isarIatmfCESCellLossStatus is set to loss (2). 
            The default definition is 2500.
            IAD4700 : this value is constant."
    DEFVAL  { 2500 }
    ::= { isarIatmfCESConfEntry  11 }

isarIatmfCESConnType OBJECT-TYPE
    SYNTAX  INTEGER {
                      other(1),
                      pvc(2),
                      activeSvc(3),
                      passiveSvc(4)
            }
    ACCESS  read-only
    STATUS  mandatory
    DESCRIPTION
           "The type of ATM connectivity between associated CES IWF's.
            Valid values are:
               other      - none of the types specified below
               pvc        - supporting connectivity is a permanent
                            virtual connection
               activeSvc  - attempt calls whenever none established
               passiveSvc - accept calls.

            IAD4700 v1 / v2.0 : only 'pvc' is supported."
    DEFVAL { pvc }
    ::= { isarIatmfCESConfEntry  12 }

isarIatmfCESLocalAddr OBJECT-TYPE
    SYNTAX  OCTET STRING (SIZE(0|8|20))
    ACCESS  read-only
    STATUS  mandatory
    DESCRIPTION
           "The ATM address of the local CES IWF process. This address
            may be used by the automatic SVC establishment procedures to
            identify the intended recipient CES IWF of an incoming 
            automatic SVC call request.
            The ATM address used by the network entity.  The address
            types are: no address (0 octets), E.164 (8 octets), and
            NSAP-encoded ATM Endsystem Address (20 octets).
            Note: The E.164 address is encoded in BCD format.          
            Optionally, the MAX-ACCESS of this object may be read-only,
            for those implementations where it is not desired to 
            manually configure this address."
    ::= { isarIatmfCESConfEntry  13 }

isarIatmfCESAdminStatus OBJECT-TYPE
    SYNTAX  INTEGER {
                      up(1),
                      down(2)
            }
    ACCESS  read-write
    STATUS  optional
    DESCRIPTION
           "The desired administrative status of the CES interworking
            function.  The up and down states indicate that the traffic
            flow is enabled or disabled respectively across the CES
            interworking function.
            The SNMPv2 MAX-ACCESS is read-create."
    ::= { isarIatmfCESConfEntry  14 }

isarIatmfCESOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  optional
    DESCRIPTION
           "The operational status of the CES interworking function.
            The up and down states indicate that the traffic flow is
            enabled or disabled respectively across the CES interworking
            function.  The unknown state indicates that the state of the
            CES interworking function cannot be determined.  The state
            will be down or unknown if the supporting CBR or ATM
            interfaces are down or unknown, respectively.
            Refer to RFC 2233 for the other states."
    ::= { isarIatmfCESConfEntry  15 }

isarIatmfCESConfRowStatus OBJECT-TYPE
    SYNTAX  INTEGER {
                      -- the following two values are states:
                      -- these values may be read or written
                      active(1),
                      notInService(2),

                      -- the following value is a state:
                      -- this value may be read, but not written
                      notReady(3),
 
                      -- the following three values are
                      -- actions: these values may be written,
                      --   but are never read
                      createAndGo(4),
                      createAndWait(5),
                      destroy(6)
            }
    ACCESS  read-write
    STATUS  mandatory
    DESCRIPTION
           "This object is used to create new rows in this table, modify
            existing rows, and to delete existing rows.
            The SNMPv2 MAX-ACCESS is read-create."
    ::= { isarIatmfCESConfEntry  16 }

isarIatmfCESConfServiceIndex OBJECT-TYPE
    SYNTAX  INTEGER
    ACCESS  read-write
    STATUS  mandatory
    DESCRIPTION
           "The index of the service to which this interworking function
            belongs.
            This is the same index as serviceIndex of isarIserviceTable.
            (it must be possible to add rows but it must be 
            impossible to modify this index)
            The SNMPv2 MAX-ACCESS is read-create."
    ::= { isarIatmfCESConfEntry  17 }

isarIatmfCESConfIwfConnIndex OBJECT-TYPE
    SYNTAX  INTEGER
    ACCESS  read-only
    STATUS  mandatory
    DESCRIPTION
           "The value of this object is equal to the 
            isarIiwfNextConnIndex obtained (by IAD4700) to uniqely identify 
            this IWF."
    ::= { isarIatmfCESConfEntry  18 }

isarIatmfCESConfUserDefData OBJECT-TYPE
    SYNTAX  INTEGER (0..255)
    ACCESS  read-only
    STATUS  mandatory
    DESCRIPTION
           "Data pattern for trunk conditioning.
            The HW does not allow this field to be different for each
            IWF.  The field will be set in the ini-file."
    DEFVAL { 127 }
    ::= { isarIatmfCESConfEntry  19 }

isarIatmfCESConfUserDefSigCode1 OBJECT-TYPE
    SYNTAX  INTEGER (0..15)
    ACCESS  read-write
    STATUS  mandatory
    DESCRIPTION
           "Signaling value applied during the first 2.5 sec after a
            failure is declared."
    DEFVAL { 0 }
    ::= { isarIatmfCESConfEntry  20 }

isarIatmfCESConfUserDefSigCode2 OBJECT-TYPE
    SYNTAX  INTEGER (0..15)
    ACCESS  read-write
    STATUS  mandatory
    DESCRIPTION
           "Signaling value applied for the duration of the detected
            failure."
    DEFVAL { 15 }
    ::= { isarIatmfCESConfEntry  21 }

isarIatmfCESConfTCEnabled OBJECT-TYPE
    SYNTAX  INTEGER {
                      true(1),
                      false(2)
            }
    ACCESS  read-write
    STATUS  mandatory
    DESCRIPTION
           "When set to 'true', the trunk conditioning is enabled."
    DEFVAL { false }
    ::= { isarIatmfCESConfEntry  22 }

isarIatmfCESConfS0PortMap OBJECT-TYPE
    SYNTAX  INTEGER
    ACCESS  read-write
    STATUS  optional
    DESCRIPTION
           "This object is only to be filled in in case of SlottedS0 (LES)
            or CES over S0.
            A value different from 0 indicates SlottedS0 or CES over S0.
            It is a bitmap indicating via bit31 whether it is used for CES over
            S0 or for slottedS0.
            
             bit31 (=MSB) : 0 = Ces on S0
                            1 = SlottedS0
             bit0 (=LSB) indicates S0 port 0 on PM in slot1, ...
             bit7 indicates S0 port 7 on PM in slot1,
             bit8 indicates S0 port 0 on PM in slot2, ...
             bit15 indicates S0 port 7 on PM in slot2,
             bit16 indicates S0 port 0 on PM in slot3, ...
             bit23 indicates S0 port 7 on PM in slot3.
            Modification of this value is not allowed.
            The SNMPv2 MAX-ACCESS is read-(only-)create."
    DEFVAL { 0 }
    ::= { isarIatmfCESConfEntry  23 }




-- CES Mapping Tables

isarIatmfCESMappingTable OBJECT-TYPE
    SYNTAX  SEQUENCE OF IsarIatmfCESMappingEntry
    ACCESS  not-accessible
    STATUS  mandatory
    DESCRIPTION
           "The CES mapping table used to show the mapping from ATM
            VCLs to CBR interfaces or channels.  The mapping and
            interworking functions are configured in the
            isarIatmfCESConfTable."
    ::= { isarIatmfCESObjects  2 }

isarIatmfCESMappingEntry OBJECT-TYPE
    SYNTAX  IsarIatmfCESMappingEntry
    ACCESS  not-accessible
    STATUS  mandatory
    DESCRIPTION
           "An entry in the CES mapping table.  There is one entry
            in the table corresponding to each active row in the
            isarIatmfCESConfTable for which there is a non-zero
            isarIatmfCESAtmIndex."
    INDEX   { isarIatmfCESAtmIndex, 
              isarIatmfCESAtmVpi,
              isarIatmfCESAtmVci }
    ::= { isarIatmfCESMappingTable  1 }

IsarIatmfCESMappingEntry ::=
    SEQUENCE {
      isarIatmfCESMappingCbrIndex
        INTEGER
    }

isarIatmfCESMappingCbrIndex OBJECT-TYPE
    SYNTAX  INTEGER
    ACCESS  read-only
    STATUS  mandatory
    DESCRIPTION
           "The value of this object is equal to MIB II's ifIndex value
            of the CBR interface, channel, or bundle that is being
            cross-connected to an ATM VCL.  Examples of the ifType
            value for the CBR entity are ds1(18), ds3(30), ds0(81), or
            ds0bundle(82)."
    ::= { isarIatmfCESMappingEntry  1 }



-- mapping IWF index into index of isarIatmfCESConfTable

isarIatmfCESIwfMappingTable OBJECT-TYPE
    SYNTAX  SEQUENCE OF IsarIatmfCESIwfMappingEntry
    ACCESS  not-accessible
    STATUS  mandatory
    DESCRIPTION
           "The CESIwf mapping table is used to map the IWF index
            into the index of the corresponding entry in the
            isarIatmfCESConfTable."
    ::= { isarIatmfCESObjects  5 }

isarIatmfCESIwfMappingEntry OBJECT-TYPE
    SYNTAX  IsarIatmfCESIwfMappingEntry
    ACCESS  not-accessible
    STATUS  mandatory
    DESCRIPTION
           "An entry in the CES IWF mapping table."
    INDEX   { isarIatmfCESConfIwfConnIndex }
    ::= { isarIatmfCESIwfMappingTable  1 }

IsarIatmfCESIwfMappingEntry ::=
    SEQUENCE {
      isarIatmfCESIwfMapCbrIndex
        INTEGER
    }

isarIatmfCESIwfMapCbrIndex OBJECT-TYPE
    SYNTAX  INTEGER (1..2147483647)
    ACCESS  read-only
    STATUS  mandatory
    DESCRIPTION
           "Mapped index."
    ::= { isarIatmfCESIwfMappingEntry  1 }




-- CES Statistics Table

isarIatmfCESStatsTable OBJECT-TYPE
    SYNTAX  SEQUENCE OF IsarIatmfCESStatsEntry
    ACCESS  not-accessible
    STATUS  mandatory
    DESCRIPTION
           "The CES AAL1 statistical data table.
            
            IAD4700 : the counters are the counters of the port on which
                   the AAL1 channel is located.  The information
                   is not CES specific when more than one channel is 
                   located on the port."
    ::= { isarIatmfCESObjects  3 }

isarIatmfCESStatsEntry OBJECT-TYPE
    SYNTAX  IsarIatmfCESStatsEntry
    ACCESS  not-accessible
    STATUS  mandatory
    DESCRIPTION
           "An entry in the CES AAL1 Stats table.  There is one
            entry in this table corresponding to each entry in the
            atmfCESConfTable."
    INDEX   { isarIatmfCESCbrIndex }
-- AUGMENTS { atmfCESConfEntry } 
    ::= { isarIatmfCESStatsTable  1 }

IsarIatmfCESStatsEntry ::=
    SEQUENCE {
      isarIatmfCESReassCells
        Counter,

      isarIatmfCESHdrErrors
        Counter,

      isarIatmfCESPointerReframes
        Counter,

      isarIatmfCESPointerParityErrors
        Counter,

      isarIatmfCESAal1SeqErrors
        Counter,

      isarIatmfCESLostCells
        Counter,

      isarIatmfCESMisinsertedCells
        Counter,

      isarIatmfCESBufUnderflows
        Counter,

      isarIatmfCESBufOverflows
        Counter,

      isarIatmfCESCellLossStatus
        INTEGER
    }

isarIatmfCESReassCells OBJECT-TYPE
    SYNTAX  Counter
    ACCESS  read-only
    STATUS  mandatory
    DESCRIPTION
           "This count gives the number of cells played out to the
            CES Service Interface. It excludes cells that were
            discarded for any reason, including cells that were not used
            due to being declared misinserted, or discarded while the
            reassembler was waiting to achieve synchronization."
    ::= { isarIatmfCESStatsEntry  1 }

isarIatmfCESHdrErrors OBJECT-TYPE
    SYNTAX  Counter
    ACCESS  read-only
    STATUS  mandatory
    DESCRIPTION
           "The count of the number of AAL1 header errors detected,
            including those corrected.  Header errors include 
            correctable and uncorrectable CRC, plus bad parity."
    ::= { isarIatmfCESStatsEntry  2 }

isarIatmfCESPointerReframes OBJECT-TYPE
    SYNTAX  Counter
    ACCESS  read-only
    STATUS  mandatory
    DESCRIPTION
           "This records the count of the number of events in which the
            AAL1 reassembler found that an SDT pointer is not where it 
            is expected, and the pointer must be reacquired. This count 
            is only meaningful for structured CES modes, as unstructured
            CES modes do not use pointers. For unstructured CES modes, 
            this count, if present, should indicate zero."
    ::= { isarIatmfCESStatsEntry  3 }

isarIatmfCESPointerParityErrors OBJECT-TYPE
    SYNTAX  Counter
    ACCESS  read-only
    STATUS  mandatory
    DESCRIPTION
           "This records the count of the number of events in which the
            AAL1 reassembler detects a parity check failure at the point
            where a structured data pointer is expected. This count is 
            only meaningful for structured CES modes, as unstructured 
            CES modes do not use pointers. For unstructured CES modes, 
            this count, if present, should indicate zero."
    ::= { isarIatmfCESStatsEntry  4 }

isarIatmfCESAal1SeqErrors OBJECT-TYPE
    SYNTAX  Counter
    ACCESS  read-only
    STATUS  optional
    DESCRIPTION
           "Number of times that the sequence number of an incoming AAL1
            Type 1 SAR-PDU causes a transition from the 'sync' state to
            the 'out of sequence' state, as defined by ITU-T I.363.1."
    ::= { isarIatmfCESStatsEntry  5 }

isarIatmfCESLostCells OBJECT-TYPE
    SYNTAX  Counter
    ACCESS  read-only
    STATUS  optional
    DESCRIPTION
           "Number of lost cells, as detected by the AAL1 sequence 
            number processing, for example. This records the count of 
            the number of cells detected as lost in the network prior 
            to the destination CES IWF AAL1 layer processing."
    ::= { isarIatmfCESStatsEntry  6 }

isarIatmfCESMisinsertedCells OBJECT-TYPE
    SYNTAX  Counter
    ACCESS  read-only
    STATUS  optional
    DESCRIPTION
           "Number of AAL1 sequence violations which the AAL Convergence
            sublayer interprets as a misinserted cell, as defined by
            ITU-T I.363.1."
    ::= { isarIatmfCESStatsEntry  7 }

isarIatmfCESBufUnderflows OBJECT-TYPE
    SYNTAX  Counter
    ACCESS  read-only
    STATUS  mandatory
    DESCRIPTION
           "Number of buffer underflows. This records the count of the
            number of times the CES reassembly buffer underflows. In the
            case of a continuous underflow caused by a loss of ATM cell
            flow, a single buffer underflow should be counted. If the
            CES IWF is implemented with multiple buffers (such as a cell
            level buffer and a bit level buffer), then either buffer 
            underflow will cause this count to be incremented."
    ::= { isarIatmfCESStatsEntry  8 }

isarIatmfCESBufOverflows OBJECT-TYPE
    SYNTAX  Counter
    ACCESS  read-only
    STATUS  mandatory
    DESCRIPTION
           "Number of buffer overflows. This records the count of the
            number of times the CES reassembly buffer overflows. If the 
            CES IWF is implemented with multiple buffers (such as a cell
            level buffer and a bit level buffer), then either buffer 
            overflow will cause this count to be incremented."
    ::= { isarIatmfCESStatsEntry  9 }

isarIatmfCESCellLossStatus OBJECT-TYPE
    SYNTAX  INTEGER {
                      noLoss(1),
                      loss(2)
            }
    ACCESS  read-only
    STATUS  mandatory
    DESCRIPTION
           "When cells are continuously lost for the number of 
            milliseconds specified by 
            isarIatmfCESCellLossIntegrationPeriod, the value is set to 
            loss (2). When cells are no longer lost, the value is set 
            to noLoss (1)."
    ::= { isarIatmfCESStatsEntry  10 }




-- CES Active SVC Table

isarIatmfCESActiveSvcTable OBJECT-TYPE
    SYNTAX  SEQUENCE OF IsarIatmfCESActiveSvcEntry
    ACCESS  not-accessible
    STATUS  mandatory
    DESCRIPTION
           "The table used to manage active SVCs established across ATM
            networks between CES entities."
    ::= { isarIatmfCESObjects  4 }

isarIatmfCESActiveSvcEntry OBJECT-TYPE
    SYNTAX  IsarIatmfCESActiveSvcEntry
    ACCESS  not-accessible
    STATUS  mandatory
    DESCRIPTION
           "An entry in the CES active SVC table.  There is one
            entry in the table corresponding to each active row in
            the isarIatmfCESConfTable for which the atmfCESConnType 
            takes the value 'activeSvc'."
    INDEX   { isarIatmfCESCbrIndex }
    ::= { isarIatmfCESActiveSvcTable  1 }

IsarIatmfCESActiveSvcEntry ::=
    SEQUENCE {
      isarIatmfCESRemoteAddr
        OCTET STRING,

      isarIatmfCESFirstRetryInterval
        INTEGER,

      isarIatmfCESRetryTimer
        INTEGER,

      isarIatmfCESRetryLimit
        INTEGER,

      isarIatmfCESRetryFailures
        Gauge,

      isarIatmfCESActiveSvcRestart
        INTEGER,

      isarIatmfCESActiveSvcOperStatus
        INTEGER,

      isarIatmfCESLastReleaseCause
        INTEGER,

      isarIatmfCESLastReleaseDiagnostics
        OCTET STRING
    }

isarIatmfCESRemoteAddr OBJECT-TYPE
    SYNTAX  OCTET STRING (SIZE(0|8|20))
    ACCESS  read-write
    STATUS  mandatory
    DESCRIPTION
           "The ATM address supporting the corresponding far end
            CES IWF process.  If no address is supplied, no attempts
            to establish the active SVC are initiated.
            The ATM address used by the network entity.  The address
            types are: no address (0 octets), E.164 (8 octets), and
            NSAP-encoded ATM Endsystem Address (20 octets).
            Note: The E.164 address is encoded in BCD format."
    ::= { isarIatmfCESActiveSvcEntry  1 }

isarIatmfCESFirstRetryInterval OBJECT-TYPE
    SYNTAX  INTEGER (1..3600)
    -- UNITS seconds
    ACCESS  read-write
    STATUS  mandatory
    DESCRIPTION
           "The time (in seconds) to wait before attempting to establish
            the SVC after the first failed call attempt.  The time to 
            to wait between subsequent call attempts may differ to
            implement a backoff scheme.  Zero represents an infinite
            interval indicating no retries."
    DEFVAL  { 10 }
    ::= { isarIatmfCESActiveSvcEntry  2 }

isarIatmfCESRetryTimer OBJECT-TYPE
    SYNTAX  INTEGER (0..86400)
    -- UNITS seconds
    ACCESS  read-only
    STATUS  mandatory
    DESCRIPTION
           "Indicates the current value (in seconds) of the retry timer 
            for this connection.  When the value reaches zero an 
            attempt will be made to establish the active SVC.  When the 
            timer is not running, the value zero shall be returned."
    ::= { isarIatmfCESActiveSvcEntry  3 }

isarIatmfCESRetryLimit OBJECT-TYPE
    SYNTAX  INTEGER (0..65535)
    ACCESS  read-write
    STATUS  mandatory
    DESCRIPTION
           "Sets a maximum limit on how many consecutive unsuccessful
            call setup attempts can be made before stopping the attempt
            to set up the connection.  If this limit is reached then
            management action will be required (e.g. setting
            isarIatmfCESActiveSvcRestart to 'restart') to initiate a new
            attempt to establish the connection.  A value of zero
            indicates no limit - the attempts will continue until
            successful. If this object is not present, no limit on call
            attempts is assumed."
    DEFVAL  { 0 }
    ::= { isarIatmfCESActiveSvcEntry  4 }

isarIatmfCESRetryFailures OBJECT-TYPE
    SYNTAX  Gauge
    ACCESS  read-only
    STATUS  mandatory
    DESCRIPTION
           "Indicates how many attempts to establish the connection
            have failed.  This count is reset whenever a connection
            is successfully established or the active SVC is restarted."
    ::= { isarIatmfCESActiveSvcEntry  5 }

isarIatmfCESActiveSvcRestart OBJECT-TYPE
    SYNTAX  INTEGER {
                      restart(1),
                      noop(2)
            }
    ACCESS  read-write
    STATUS  mandatory
    DESCRIPTION
           "When the value is set to 'restart' the active SVC
            is released if necessary and a new setup procedure
            is begun.  As a result of this action, the
            isarIatmfCESActiveSvcOperStatus object transitions to
            'establishmentInProgress' (if not already in this state)
            and the isarIatmfCESRetryFailures object is cleared.

            When the value is set to 'noop' no operation is
            performed.  When read, the value 'noop' is returned."
    ::= { isarIatmfCESActiveSvcEntry  6 }

isarIatmfCESActiveSvcOperStatus OBJECT-TYPE
    SYNTAX  INTEGER {
                      other(1),
                      establishmentInProgress(2),
                      connected(3),
                      retriesExhausted(4),
                      noAddressSupplied(5),
                      lowerLayerDown(6)
            }
    ACCESS  read-only
    STATUS  mandatory
    DESCRIPTION
           "Describes the status of the active SVC.  Valid values are:
               other              - none of the types specified below
               establishmentInProgress - connection is not operational,
                                         but call attempts are ongoing
               connected          - connection is currently operational
               retriesExhausted   - retry limit has been reached and 
                                    call attempts have ceased
               noAddressSupplied  - no remote address has been 
                                    configured, so no call attempts are
                                    initiated
               lowerLayerDown     - underlying CES IWF is not 
                                    operational

            When the row is not 'active', the value of this object is
            'other'."
    ::= { isarIatmfCESActiveSvcEntry  7 }

isarIatmfCESLastReleaseCause OBJECT-TYPE
    SYNTAX  INTEGER (1..127)
    ACCESS  read-only
    STATUS  mandatory
    DESCRIPTION
           "Value of the Cause field of the Cause information element
            in the last RELEASE signalling message received for this
            active SVC.  Indicates the reason for the release."
    ::= { isarIatmfCESActiveSvcEntry  8 }

isarIatmfCESLastReleaseDiagnostics OBJECT-TYPE
    SYNTAX  OCTET STRING (SIZE(0..8))
    ACCESS  read-only
    STATUS  mandatory
    DESCRIPTION
           "Value of the first 8 bytes of diagnostic information
            from the Cause field of the Cause information element
            in the last RELEASE signalling message received for this
            active SVC."
    ::= { isarIatmfCESActiveSvcEntry  9 }


-- CES Conf read-only table

isarIatmfCESConfRoTable OBJECT-TYPE
    SYNTAX  SEQUENCE OF IsarIatmfCESConfRoEntry
    ACCESS  not-accessible
    STATUS  mandatory
    DESCRIPTION
           "The CES configuration table used to manage interworking
            between CBR interfaces or channels and ATM Virtual Channel
            Links (VCLs).  The reverse mapping is shown in the
            isarIatmfCESMappingRoTable.

            When a row in this table is created, an entry in the
            isarIatmfCESIwfMappingRoTable is made by IAD4700 (inverse 
            mapping of index).
            
            At the same time another table must be updated :
             - set field isarIatmVclRoCrossConnectIdentifier of the 
               corresponding entry in IsarIatmVclRoEntry with the
               value of isarIatmfCESRoConfIwfConnIndex and
             - set field isarIatmVclRoServiceType of the 
               corresponding entry in IsarIatmVclRoEntry to 'ces'.

            This table is a duplicate of the isarIatmfCESConfTable with all
            fields, except row status, set to read-only.  The operator
            is not allowed to modify entries in this table, only delete
            is permitted.
            Duplication is done for Call and connection control because
            this software creates its own CESs.
            Rows are created/deleted by IAD4700."
    ::= { isarIatmfCESObjects  6 }

isarIatmfCESConfRoEntry OBJECT-TYPE
    SYNTAX  IsarIatmfCESConfRoEntry
    ACCESS  not-accessible
    STATUS  mandatory
    DESCRIPTION
           "An entry in the CES configuration read-only table.  There is 
            one entry in the table per CES entity, mapping one CBR
            interface, channel, or bundle to an ATM VCL."
    INDEX   { isarIatmfCESRoCbrIndex }
    ::= { isarIatmfCESConfRoTable  1 }

IsarIatmfCESConfRoEntry ::=
    SEQUENCE {
      isarIatmfCESRoCbrIndex
        INTEGER,

      isarIatmfCESRoAtmIndex
        INTEGER,

      isarIatmfCESRoAtmVpi
        INTEGER,

      isarIatmfCESRoAtmVci
        INTEGER,

      isarIatmfCESRoCbrService
        INTEGER,

      isarIatmfCESRoCbrClockMode
        INTEGER,

      isarIatmfCESRoCas
        INTEGER,

      isarIatmfCESRoPartialFill
        INTEGER,

      isarIatmfCESRoBufMaxSize
        INTEGER,

      isarIatmfCESRoCdvRxT
        INTEGER,

      isarIatmfCESRoCellLossIntegrationPeriod
        INTEGER,

      isarIatmfCESRoConnType
        INTEGER,

      isarIatmfCESRoLocalAddr
        OCTET STRING,

      isarIatmfCESRoOperStatus
        INTEGER,

      isarIatmfCESRoConfRowStatus
        INTEGER,

      isarIatmfCESRoConfServiceIndex
        INTEGER,

      isarIatmfCESRoConfIwfConnIndex
        INTEGER,

      isarIatmfCESRoConfUserDefData
        INTEGER,

      isarIatmfCESRoConfUserDefSigCode1
        INTEGER,

      isarIatmfCESRoConfUserDefSigCode2
        INTEGER,

      isarIatmfCESRoConfTCEnabled
        INTEGER,

      isarIatmfCESRoConfSlotNumber
        INTEGER,

      isarIatmfCESRoConfPhysPortId
        INTEGER,

      isarIatmfCESRoConfDsx0BundleMap
        INTEGER
    }

isarIatmfCESRoCbrIndex OBJECT-TYPE
    SYNTAX  INTEGER (1..2147483647)
    ACCESS  not-accessible
    STATUS  mandatory
    DESCRIPTION
           "The value of this object is equal to MIB II's ifIndex value
            of the CBR interface, channel, or bundle that is being
            cross-connected to an ATM VCL."
    ::= { isarIatmfCESConfRoEntry  1 }

isarIatmfCESRoAtmIndex OBJECT-TYPE
    SYNTAX  INTEGER (1..2147483647)
    ACCESS  read-only
    STATUS  mandatory
    DESCRIPTION
           "The value of this object is equal to MIB II's
            ifIndex value of the ATM Port interface mapped 
            through this CES IWF to a CBR interface.

            The distinguished value zero indicates that no ATM
            interface has been specified.

            IAD4700 : The ifIndex of the ATM interface to which this
            interworking function belongs.  The value 0 is not allowed
            for IAD4700."
    ::= { isarIatmfCESConfRoEntry  2 }

isarIatmfCESRoAtmVpi OBJECT-TYPE
    SYNTAX  INTEGER (0..4095)
    ACCESS  read-only
    STATUS  mandatory
    DESCRIPTION
           "The value of this object is equal to the VPI used
            by the ATM VCL mapped through this CES IWF to a CBR
            interface.
            
            The value is not relevant if no ATM interface has been
            specified (i.e., isarIatmfCESAtmIndex is set to zero).
            
            IAD4700 : The VPI value of the VCL used for this interworking
            function."
    ::= { isarIatmfCESConfRoEntry  3 }

isarIatmfCESRoAtmVci OBJECT-TYPE
    SYNTAX  INTEGER (0..65535)
    ACCESS  read-only
    STATUS  mandatory
    DESCRIPTION
           "The value of this object is equal to the VCI used
            by the ATM VCL mapped through this CES IWF to a CBR
            interface.

            The distinguished value zero indicates that no ATM
            VCL has been specified.
            
            IAD4700 : The VCI value of the CVL used for this interworking
            function."
    ::= { isarIatmfCESConfRoEntry  4 }

isarIatmfCESRoCbrService OBJECT-TYPE
    SYNTAX  INTEGER {
                      unstructured(1),
                      structured(2)
            }
    ACCESS  read-only
    STATUS  mandatory
    DESCRIPTION
           "Define if DSx/Ex service is structured or unstructured. A
            structured(2) interface is some nx64kbKbps. An unstructured
            (1) interface is 1.544Mbps, 2.048Mbps, 6.312Mbps, 
            44.736 Mbps, or 34.368 Mbps. unstructured(1) passes all bits
            through the ATM network.  strucutured(2) passes data bits 
            through the ATM network, and may also pass signalling bits.
            
            At this time, only unstructured mode is defined for the
            44.736 Mbps and 34.368 Mbps services.
            
            IAD4700 v1 / v2.0 : only the value 'structured' is supported."
    DEFVAL { structured }
    ::= { isarIatmfCESConfRoEntry  5 }

isarIatmfCESRoCbrClockMode OBJECT-TYPE
    SYNTAX  INTEGER {
                      synchronous(1),
                      srts(2),
                      adaptive(3)
            }
    ACCESS  read-only
    STATUS  mandatory
    DESCRIPTION
           "Define if DSx/Ex service clocking mode. This maps into
            transmit clock source of CBR interface.

            For structured modes this value, if present, must be set to
            synchronous(1).
            IAD4700 v1 / v2.0 : only the value 'synchronous' is supported."
    DEFVAL  { synchronous }
    ::= { isarIatmfCESConfRoEntry  6 }

isarIatmfCESRoCas OBJECT-TYPE
    SYNTAX  INTEGER {
                      basic(1),
                      e1Cas(2),
                      ds1SfCas(3),
                      ds1EsfCas(4),
                      j2Cas(5)
            }
    ACCESS  read-only
    STATUS  mandatory
    DESCRIPTION
           "This parameter selects which AAL1 Format should be used:
            Basic does not carry CAS bits, and uses a single 125 usec 
            frame.
            e1Cas, ds1SfCas, dS1EsfCas and j2Cas carry CAS bits in a
            multiframe structure for E1, DS1 SF, DS1 ESF and J2 
            respectively.
            This applies to structured interfaces only. Default is
            basic (1). For unstructured interfaces this value, if 
            present, must be set to the default of basic (1).

            IAD4700 v1 / v2.0 : only the values 'basic' and 'e1Cas' are
            allowed."
    DEFVAL  { basic }
    ::= { isarIatmfCESConfRoEntry  7 }

isarIatmfCESRoPartialFill OBJECT-TYPE
    SYNTAX  INTEGER (0 | 4 .. 47)
    ACCESS  read-only
    STATUS  mandatory
    DESCRIPTION
           "If partial cell fill is used, the number of user octets per
            cell must be set with this parameter.  Setting this 
            parameter to zero disables partial cell fill, and causes all
            cells to be completely filled before they are sent."
    DEFVAL  { 0 }
    ::= { isarIatmfCESConfRoEntry  8 }

isarIatmfCESRoBufMaxSize OBJECT-TYPE
    SYNTAX  INTEGER  (1..65536)
    -- UNITS 10 usec
    ACCESS  read-only
    STATUS  mandatory
    DESCRIPTION
           "Define maximum size in 10 microsecond increments of the
            reassembly buffer. Some implementations may want allow the
            maximum buffer size to be programmed to a size less than
            the physical limit to reduce the maximum delay through a 
            circuit."
    DEFVAL  { 128 }
    ::= { isarIatmfCESConfRoEntry  9 }

isarIatmfCESRoCdvRxT OBJECT-TYPE
    SYNTAX  INTEGER (1..65535)
    -- UNITS 10 usec
    ACCESS  read-only
    STATUS  mandatory
    DESCRIPTION
           "The maximum cell arrival jitter in 10 usec increments that 
            the reassembly process will tolerate in the cell stream
            without producing errors on the CBR service interface.
            IAD4700 : req. spec : CDV = 1 cell, so this depends on cell
            rate."
    DEFVAL  { 100 }
    ::= { isarIatmfCESConfRoEntry  10 }

isarIatmfCESRoCellLossIntegrationPeriod OBJECT-TYPE
    SYNTAX  INTEGER (1000 .. 65535)
    -- UNITS msec
    ACCESS  read-only
    STATUS  mandatory
    DESCRIPTION
           "The time in milliseconds for the cell loss integration 
            period.  If cells are continuously lost for this period 
            of time, isarIatmfCESCellLossStatus is set to loss (2). 
            The default definition is 2500.
            IAD4700 : this value is constant."
    DEFVAL  { 2500 }
    ::= { isarIatmfCESConfRoEntry  11 }

isarIatmfCESRoConnType OBJECT-TYPE
    SYNTAX  INTEGER {
                      other(1),
                      pvc(2),
                      activeSvc(3),
                      passiveSvc(4)
            }
    ACCESS  read-only
    STATUS  mandatory
    DESCRIPTION
           "The type of ATM connectivity between associated CES IWF's.
            Valid values are:
               other      - none of the types specified below
               pvc        - supporting connectivity is a permanent
                            virtual connection
               activeSvc  - attempt calls whenever none established
               passiveSvc - accept calls.

            IAD4700 v2.0 : only 'passiveSvc' is supported."
    DEFVAL { pvc }
    ::= { isarIatmfCESConfRoEntry  12 }

isarIatmfCESRoLocalAddr OBJECT-TYPE
    SYNTAX  OCTET STRING (SIZE(0|8|20))
    ACCESS  read-only
    STATUS  mandatory
    DESCRIPTION
           "The ATM address of the local CES IWF process. This address
            may be used by the automatic SVC establishment procedures to
            identify the intended recipient CES IWF of an incoming 
            automatic SVC call request.
            The ATM address used by the network entity.  The address
            types are: no address (0 octets), E.164 (8 octets), and
            NSAP-encoded ATM Endsystem Address (20 octets).
            Note: The E.164 address is encoded in BCD format."
    ::= { isarIatmfCESConfRoEntry  13 }

isarIatmfCESRoOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  optional
    DESCRIPTION
           "The operational status of the CES interworking function.
            The up and down states indicate that the traffic flow is
            enabled or disabled respectively across the CES interworking
            function.  The unknown state indicates that the state of the
            CES interworking function cannot be determined.  The state
            will be down or unknown if the supporting CBR or ATM
            interfaces are down or unknown, respectively.
            Refer to RFC 2233 for the other states."
    ::= { isarIatmfCESConfRoEntry  15 }

isarIatmfCESRoConfRowStatus OBJECT-TYPE
    SYNTAX  INTEGER {
                      -- the following two values are states:
                      -- these values may be read or written
                      active(1),
                      notInService(2),

                      -- the following value is a state:
                      -- this value may be read, but not written
                      notReady(3),
 
                      -- the following three values are
                      -- actions: these values may be written,
                      --   but are never read
                      createAndGo(4),
                      createAndWait(5),
                      destroy(6)
            }
    ACCESS  read-write
    STATUS  mandatory
    DESCRIPTION
           "This object is used to create new rows in this table, modify
            existing rows, and to delete existing rows.
            The SNMPv2 MAX-ACCESS is read-create."
    ::= { isarIatmfCESConfRoEntry  16 }

isarIatmfCESRoConfServiceIndex OBJECT-TYPE
    SYNTAX  INTEGER
    ACCESS  read-only
    STATUS  mandatory
    DESCRIPTION
           "The index of the service to which this interworking function
            belongs.
            This is the same index as serviceIndex of isarIserviceTable."
    ::= { isarIatmfCESConfRoEntry  17 }

isarIatmfCESRoConfIwfConnIndex OBJECT-TYPE
    SYNTAX  INTEGER
    ACCESS  read-only
    STATUS  mandatory
    DESCRIPTION
           "The value of this object is equal to the 
            isarIiwfNextConnIndex obtained (by IAD4700) to uniqely identify 
            this IWF."
    ::= { isarIatmfCESConfRoEntry  18 }

isarIatmfCESRoConfUserDefData OBJECT-TYPE
    SYNTAX  INTEGER (0..255)
    ACCESS  read-only
    STATUS  mandatory
    DESCRIPTION
           "Data pattern for trunk conditioning.
            The HW does not allow this field to be different for each
            IWF.  The field will be set in the ini-file."
    DEFVAL { 127 }
    ::= { isarIatmfCESConfRoEntry  19 }

isarIatmfCESRoConfUserDefSigCode1 OBJECT-TYPE
    SYNTAX  INTEGER (0..15)
    ACCESS  read-only
    STATUS  mandatory
    DESCRIPTION
           "Signaling value applied during the first 2.5 sec after a
            failure is declared."
    DEFVAL { 0 }
    ::= { isarIatmfCESConfRoEntry  20 }

isarIatmfCESRoConfUserDefSigCode2 OBJECT-TYPE
    SYNTAX  INTEGER (0..15)
    ACCESS  read-only
    STATUS  mandatory
    DESCRIPTION
           "Signaling value applied for the duration of the detected
            failure."
    DEFVAL { 15 }
    ::= { isarIatmfCESConfRoEntry  21 }

isarIatmfCESRoConfTCEnabled OBJECT-TYPE
    SYNTAX  INTEGER {
                      true(1),
                      false(2)
            }
    ACCESS  read-only
    STATUS  mandatory
    DESCRIPTION
           "When set to 'true', the trunk conditioning is enabled."
    DEFVAL { false }
    ::= { isarIatmfCESConfRoEntry  22 }

isarIatmfCESRoConfSlotNumber OBJECT-TYPE
    SYNTAX  INTEGER (0..3)
    ACCESS  read-only
    STATUS  mandatory
    DESCRIPTION
           "The slot number on which the physical port of the connection
            is located.
            This is the same as isarIifSlotNumber in the corresponding
            isarIifXEntry.  It is made available here for use by 
            45020."
    ::= { isarIatmfCESConfRoEntry  23 }

isarIatmfCESRoConfPhysPortId OBJECT-TYPE
    SYNTAX  INTEGER
    ACCESS  read-only
    STATUS  mandatory
    DESCRIPTION
           "The physical port ID of the connection.
            This is the same as isarIifphysPortId in the corresponding
            isarIifXEntry.  It is made available here for use by 
            45020."
    ::= { isarIatmfCESConfRoEntry  24 }

isarIatmfCESRoConfDsx0BundleMap OBJECT-TYPE
    SYNTAX  INTEGER
    ACCESS  read-only
    STATUS  mandatory
    DESCRIPTION
           "A bitmap that indicates which ds0 channels belong to
            this bundle.
            This is the same as isarIdsx0BundleMap in the corresponding
            isarIdsx0BundleEntry.  It is made available here for use by 
            45020."
    ::= { isarIatmfCESConfRoEntry  25 }




-- CES Mapping read-only Tables

isarIatmfCESMappingRoTable OBJECT-TYPE
    SYNTAX  SEQUENCE OF IsarIatmfCESMappingRoEntry
    ACCESS  not-accessible
    STATUS  mandatory
    DESCRIPTION
           "The CES mapping table used to show the mapping from ATM
            VCLs to CBR interfaces or channels.  The mapping and
            interworking functions are configured in the
            isarIatmfCESConfRoTable."
    ::= { isarIatmfCESObjects  7 }

isarIatmfCESMappingRoEntry OBJECT-TYPE
    SYNTAX  IsarIatmfCESMappingRoEntry
    ACCESS  not-accessible
    STATUS  mandatory
    DESCRIPTION
           "An entry in the CES mapping table.  There is one entry
            in the table corresponding to each active row in the
            isarIatmfCESConfRoTable for which there is a non-zero
            isarIatmfCESRoAtmIndex."
    INDEX   { isarIatmfCESRoAtmIndex, 
              isarIatmfCESRoAtmVpi,
              isarIatmfCESRoAtmVci }
    ::= { isarIatmfCESMappingRoTable  1 }

IsarIatmfCESMappingRoEntry ::=
    SEQUENCE {
      isarIatmfCESMappingRoCbrIndex
        INTEGER
    }

isarIatmfCESMappingRoCbrIndex OBJECT-TYPE
    SYNTAX  INTEGER
    ACCESS  read-only
    STATUS  mandatory
    DESCRIPTION
           "The value of this object is equal to MIB II's ifIndex value
            of the CBR interface, channel, or bundle that is being
            cross-connected to an ATM VCL.  Examples of the ifType
            value for the CBR entity are ds1(18), ds3(30), ds0(81), or
            ds0bundle(82)."
    ::= { isarIatmfCESMappingRoEntry  1 }



-- mapping IWF index into index of isarIatmfCESConfRoTable

isarIatmfCESIwfMappingRoTable OBJECT-TYPE
    SYNTAX  SEQUENCE OF IsarIatmfCESIwfMappingRoEntry
    ACCESS  not-accessible
    STATUS  mandatory
    DESCRIPTION
           "The CESIwf mapping read-only table is used to map the IWF index
            into the index of the corresponding entry in the
            isarIatmfCESConfRoTable."
    ::= { isarIatmfCESObjects  8 }

isarIatmfCESIwfMappingRoEntry OBJECT-TYPE
    SYNTAX  IsarIatmfCESIwfMappingRoEntry
    ACCESS  not-accessible
    STATUS  mandatory
    DESCRIPTION
           "An entry in the CES IWF mapping read-only table."
    INDEX   { isarIatmfCESRoConfIwfConnIndex }
    ::= { isarIatmfCESIwfMappingRoTable  1 }

IsarIatmfCESIwfMappingRoEntry ::=
    SEQUENCE {
      isarIatmfCESIwfMapCbrRoIndex
        INTEGER
    }

isarIatmfCESIwfMapCbrRoIndex OBJECT-TYPE
    SYNTAX  INTEGER (1..2147483647)
    ACCESS  read-only
    STATUS  mandatory
    DESCRIPTION
           "Mapped index."
    ::= { isarIatmfCESIwfMappingRoEntry  1 }



-- thresholds for all CES


isarIatmfCESReassCellsThreshold OBJECT-TYPE 
    SYNTAX  INTEGER (0..1073741824) 
    ACCESS  read-write 
    STATUS  mandatory 
    DESCRIPTION 
           "Indicates when the corresponding counter of every CES IWF 
            results in a trap .
            0 = no threshold = default." 
    ::= { isarIatmfCESObjects  9 } 

isarIatmfCESHdrErrorsThreshold OBJECT-TYPE 
    SYNTAX  INTEGER (0..1073741824) 
    ACCESS  read-write 
    STATUS  mandatory 
    DESCRIPTION 
           "Indicates when the corresponding counter of every CES IWF 
            results in a trap. 
            0 = no threshold = default." 
    ::= { isarIatmfCESObjects  10 } 

isarIatmfCESPointerReframesThreshold OBJECT-TYPE 
    SYNTAX  INTEGER (0..1073741824) 
    ACCESS  read-write 
    STATUS  mandatory 
    DESCRIPTION 
           "Indicates when the corresponding counter of every CES IWF results in a trap 
            0 = no threshold = default." 
    ::= { isarIatmfCESObjects  11 } 

isarIatmfCESPointerParityErrorsThreshold OBJECT-TYPE 
    SYNTAX  INTEGER (0..1073741824) 
    ACCESS  read-write 
    STATUS  mandatory 
    DESCRIPTION 
           "Indicates when the corresponding counter of every CES IWF results in a trap 
            0 = no threshold = default." 
    ::= { isarIatmfCESObjects  12 } 

isarIatmfCESAal1SeqErrorsThreshold OBJECT-TYPE 
    SYNTAX  INTEGER (0..1073741824) 
    ACCESS  read-write 
    STATUS  mandatory 
    DESCRIPTION 
           "Indicates when the corresponding counter of every CES IWF 
            results in a trap.
            0 = no threshold = default." 
    ::= { isarIatmfCESObjects  13 } 

isarIatmfCESLostCellsThreshold OBJECT-TYPE 
    SYNTAX  INTEGER (0..1073741824) 
    ACCESS  read-write 
    STATUS  mandatory 
    DESCRIPTION 
           "Indicates when the corresponding counter of every CES IWF
            results in a trap.
            0 = no threshold = default." 
    ::= { isarIatmfCESObjects  14 } 

isarIatmfCESMisinsertedCellsThreshold OBJECT-TYPE 
    SYNTAX  INTEGER (0..1073741824) 
    ACCESS  read-write 
    STATUS  mandatory 
    DESCRIPTION 
           "Indicates when the corresponding counter of every CES IWF 
            results in a trap.
            0 = no threshold = default." 
    ::= { isarIatmfCESObjects  15 } 

isarIatmfCESBufUnderflowsThreshold OBJECT-TYPE 
    SYNTAX  INTEGER (0..1073741824) 
    ACCESS  read-write 
    STATUS  mandatory 
    DESCRIPTION 
           "Indicates when the corresponding counter of every CES IWF
            results in a trap.
            0 = no threshold = default." 
    ::= { isarIatmfCESObjects  16 } 

isarIatmfCESBufOverflowsThreshold OBJECT-TYPE 
    SYNTAX  INTEGER (0..1073741824) 
    ACCESS  read-write 
    STATUS  mandatory 
    DESCRIPTION 
           "Indicates when the corresponding counter of every CES IWF
            results in a trap.
            0 = no threshold = default." 
    ::= { isarIatmfCESObjects  17 } 

isarIatmfCESCellLossStatusThreshold OBJECT-TYPE 
    SYNTAX  INTEGER (0..1073741824) 
    ACCESS  read-write 
    STATUS  mandatory 
    DESCRIPTION 
           "Indicates when the corresponding counter of every CES IWF
            results in a trap.
            0 = no threshold = default." 
    ::= { isarIatmfCESObjects  18 } 



-- CES on S0 IWF Statistics Table

isarIatmfCESOnS0IwfStatsTable OBJECT-TYPE
    SYNTAX  SEQUENCE OF IsarIatmfCESOnS0IwfStatsEntry
    ACCESS  not-accessible
    STATUS  mandatory
    DESCRIPTION
           "The CES on S0 statistical data table."
    ::= { isarIatmfCESObjects  19 }

isarIatmfCESOnS0IwfStatsEntry OBJECT-TYPE
    SYNTAX  IsarIatmfCESOnS0IwfStatsEntry
    ACCESS  not-accessible
    STATUS  mandatory
    DESCRIPTION
           "An entry in the CES On S0 Iwf Stats table.  There is one
            entry in this table corresponding to each entry in the
            atmfCESConfTable.  However, the counters only heave meaning
            when it concerns a CES on S0 IWF (S0PortMap /= 0)."
    INDEX   { isarIatmfCESCbrIndex }
    ::= { isarIatmfCESOnS0IwfStatsTable  1 }

IsarIatmfCESOnS0IwfStatsEntry ::=
    SEQUENCE {
      isarIatmfCESOnS0IwfStatsDsToAsTransmFrames
        Counter,

      isarIatmfCESOnS0IwfStatsAsToDsTransmFrames
        Counter,

      isarIatmfCESOnS0IwfStatsDsToAsDroppedFrames
        Counter,

      isarIatmfCESOnS0IwfStatsAsToDsDroppedFrames
        Counter
    }

isarIatmfCESOnS0IwfStatsDsToAsTransmFrames OBJECT-TYPE
    SYNTAX  Counter
    ACCESS  read-only
    STATUS  mandatory
    DESCRIPTION
           "The number of frames that have been received from the drop
            side and have been sent to the aggregate side by this
            interworking function."
    ::= { isarIatmfCESOnS0IwfStatsEntry  1 }

isarIatmfCESOnS0IwfStatsAsToDsTransmFrames OBJECT-TYPE
    SYNTAX  Counter
    ACCESS  read-only
    STATUS  mandatory
    DESCRIPTION
           "The number of frames that have been received from the 
            aggregate side and have been sent to the drop side by this
            interworking function."
    ::= { isarIatmfCESOnS0IwfStatsEntry  2 }

isarIatmfCESOnS0IwfStatsDsToAsDroppedFrames OBJECT-TYPE
    SYNTAX  Counter
    ACCESS  read-only
    STATUS  mandatory
    DESCRIPTION
           "The number of frames that have been received from the drop
            side and have been dropped by the store and forward function."
    ::= { isarIatmfCESOnS0IwfStatsEntry  3 }

isarIatmfCESOnS0IwfStatsAsToDsDroppedFrames OBJECT-TYPE
    SYNTAX  Counter
    ACCESS  read-only
    STATUS  mandatory
    DESCRIPTION
           "The number of frames that have been received from the 
            aggregate side and have been dropped by the store and forward
            function."
    ::= { isarIatmfCESOnS0IwfStatsEntry  4 }


-- Slotted S0 Statistics Table

isarIatmfCESSlottedS0StatsTable OBJECT-TYPE
    SYNTAX  SEQUENCE OF IsarIatmfCESSlottedS0StatsEntry
    ACCESS  not-accessible
    STATUS  mandatory
    DESCRIPTION
           "The CES on S0 statistical data table."
    ::= { isarIatmfCESObjects  20 }

isarIatmfCESSlottedS0StatsEntry OBJECT-TYPE
    SYNTAX  IsarIatmfCESSlottedS0StatsEntry
    ACCESS  not-accessible
    STATUS  mandatory
    DESCRIPTION
           "An entry in the slotted S0 Stats table.  There is one
            entry in this table corresponding to each entry in the
            atmfCESConfTable.  However, the counters only heave meaning
            when it concerns a slotted S0 IWF (S0PortMap /= 0)."
    INDEX   { isarIatmfCESCbrIndex }
    ::= { isarIatmfCESSlottedS0StatsTable  1 }

IsarIatmfCESSlottedS0StatsEntry ::=
    SEQUENCE {
      isarIatmfCESSlottedS0StatsDsToAsTransmDChannelMsgs
        Counter,

      isarIatmfCESSlottedS0StatsAsToDsTransmDChannelMsgs
        Counter,

      isarIatmfCESSlottedS0StatsDsToAsDroppedDChannelMsgs
        Counter,

      isarIatmfCESSlottedS0StatsAsToDsDroppedDChannelMsgs
        Counter,
        
      isarIatmfCESSlottedS0StatsTxControlMsgs
        Counter,

      isarIatmfCESSlottedS0StatsRxControlMsgs
        Counter,

      isarIatmfCESSlottedS0StatsTxFaultControlMsgs
        Counter,

      isarIatmfCESSlottedS0StatsRxFaultControlMsgs
        Counter
    }

isarIatmfCESSlottedS0StatsDsToAsTransmDChannelMsgs OBJECT-TYPE
    SYNTAX  Counter
    ACCESS  read-only
    STATUS  mandatory
    DESCRIPTION
           "The number of D-channel messages that have been received 
            from the drop side and have been sent to the aggregate side by
            this interworking function."
    ::= { isarIatmfCESSlottedS0StatsEntry  1 }

isarIatmfCESSlottedS0StatsAsToDsTransmDChannelMsgs OBJECT-TYPE
    SYNTAX  Counter
    ACCESS  read-only
    STATUS  mandatory
    DESCRIPTION
           "The number of D-channel messages that have been received from
            the aggregate side and have been sent to the drop side by this
            interworking function."
    ::= { isarIatmfCESSlottedS0StatsEntry  2 }

isarIatmfCESSlottedS0StatsDsToAsDroppedDChannelMsgs OBJECT-TYPE
    SYNTAX  Counter
    ACCESS  read-only
    STATUS  mandatory
    DESCRIPTION
           "The number of D-channel messages that have been received from
            the drop side and have been dropped by the store and forward 
            function."
    ::= { isarIatmfCESSlottedS0StatsEntry  3 }

isarIatmfCESSlottedS0StatsAsToDsDroppedDChannelMsgs OBJECT-TYPE
    SYNTAX  Counter
    ACCESS  read-only
    STATUS  mandatory
    DESCRIPTION
           "The number of D-channel messages that have been received from
            the aggregate side and have been dropped by the store and
            forward function."
    ::= { isarIatmfCESSlottedS0StatsEntry  4 }

isarIatmfCESSlottedS0StatsTxControlMsgs OBJECT-TYPE
    SYNTAX  Counter
    ACCESS  read-only
    STATUS  mandatory
    DESCRIPTION
           "The number of control messages that have been constructed by
            the store and forward function and have been sent to the 
            aggregate side."
    ::= { isarIatmfCESSlottedS0StatsEntry  5 }

isarIatmfCESSlottedS0StatsRxControlMsgs OBJECT-TYPE
    SYNTAX  Counter
    ACCESS  read-only
    STATUS  mandatory
    DESCRIPTION
           "The number of control messages that have been received from
            the aggregate side and have been processed successfully by the
            store and forward function."
    ::= { isarIatmfCESSlottedS0StatsEntry  6 }

isarIatmfCESSlottedS0StatsTxFaultControlMsgs OBJECT-TYPE
    SYNTAX  Counter
    ACCESS  read-only
    STATUS  mandatory
    DESCRIPTION
           "The number of control messages that have been constructed by
            this interworking function but could not be sent to the
            aggregate side and have been dropped by the store and forward 
            function."
    ::= { isarIatmfCESSlottedS0StatsEntry  7 }

isarIatmfCESSlottedS0StatsRxFaultControlMsgs OBJECT-TYPE
    SYNTAX  Counter
    ACCESS  read-only
    STATUS  mandatory
    DESCRIPTION
           "The number of control messages that have been received from
            the aggregate side but could not be processed and have been
            dropped by the store and forward function."
    ::= { isarIatmfCESSlottedS0StatsEntry  8 }



-- trap defined in isarIiwfMIBObjects


--
-- ISAR atmfCESMIBObjects : end
--  



-- This file cannot be used to create SNMP agent.
-- The file isarOneFile.my has to be used to create the agent.


-- isarIatmfImaMIBObjects     OBJECT IDENTIFIER ::= { isar  11 }


--
-- ISAR atmfImaMIBObjects : begin
--  
-- This MIB is based on the MIB described in ATM Forum document
-- af-phy-0086.
-- The MIB is written for SNMPv1.
-- The textual conventions have been replaced by their base types
-- (because the 45020 does not know these textual conventions).

-- This MIB consists of the IMA group subtree.
-- The IMA group subtree consists of the number of IMA groups and a 
-- table of IMA groups. Each entry in the table of IMA groups contains
-- information (configuration and status) specific to each group.



-- Replaced textual conventions

-- imported textual conventions

-- DateAndTime : A date-time specification. See RFC1903.
-- is replaced by OCTET STRING (SIZE (8 | 11))
-- originally used in : imaGroupLastChange 

-- RowStatus : The RowStatus textual convention is used to manage the
--             creation and deletion of conceptual rows. See RFC1903.
-- is replaced by INTEGER {...}
-- originally used in : imaGroupRowStatus imaLinkRowStatus


-- textual conventions defined in the document

-- IfIndex : it is the ifIndex of ifTable
-- is replaced by INTEGER
-- originally used in : imaGroupIfIndex imaGroupTxTimingRefLink
-- imaGroupRxTimingRefLink imaGroupLeastDelayLink imaGroupTestLinkIfIndex

-- MilliSeconds : Time in milliseconds
-- is replaced by INTEGER
-- originally used in : imaGroupDiffDelayMax imaGroupDiffDelayMaxObs

-- ImaGroupState : State of the IMA group.
-- is replaced by INTEGER {...}
-- originally used in : imaGroupNeState imaGroupFeState

-- ImaGroupFailureStatus : Failure reason of an IMA group.
-- is replaced by INTEGER {...}
-- originally used in : imaGroupFailureStatus

-- ImaAlarmStatus : A qualification of the IMA trap which indicates if 
--                  the condition causing the trap has been detected  
--                  (declared) or is no longer present (cleared).
-- is replaced by INTEGER {...}
-- originally used in : imaAlarmStatus

-- ImaAlarmType : An identification of the event that caused the 
--                generation of the IMA trap.
-- is replaced by INTEGER {...}

-- ImaGroupTxClkMode : Indicate the transmit clock mode of the IMA group.
--                     There are two possible modes: the Common Transmit 
--                     Clock (CTC) and the Independent Transmit Clock 
--                     (ITC).  The CTC mode corresponds to the case when 
--                     the transmit clock of all IMA links are derived 
--                     from the same source. The ITC configuration
--                     corresponds to the case where there is at least 
--                     one IMA link whose transmit clock is derived from 
--                     a source different than at least another link 
--                     transmit clock.
-- is replaced by INTEGER {...}
-- originally used in : imaGroupNeTxClkMode imaGroupFeTxClkMode

-- ImaGroupSymmetry : The symmetry mode adjusted during the group 
--                    start-up.
-- is replaced by INTEGER {...}
-- originally used in : imaGroupSymmetry



-- The IMA Group subtree


isarIimaGroupTable OBJECT-TYPE
    SYNTAX  SEQUENCE OF IsarIimaGroupEntry
    ACCESS  not-accessible
    STATUS  mandatory
    DESCRIPTION
           "The IMA Group Configuration table. 
            IAD4700 : the entry in this table is created at startup."
    ::= { isarIatmfImaMIBObjects  1 }

isarIimaGroupEntry OBJECT-TYPE
    SYNTAX  IsarIimaGroupEntry
    ACCESS  not-accessible
    STATUS  mandatory
    DESCRIPTION
           "An entry in the IMA Group table."
    INDEX   { isarIimaGroupIndex }
    ::= { isarIimaGroupTable  1 }

IsarIimaGroupEntry ::=
    SEQUENCE {
      isarIimaGroupIndex
        INTEGER,

      isarIimaGroupIfIndex
        INTEGER,

      isarIimaGroupNeState
        INTEGER,

      isarIimaGroupFeState
        INTEGER,

      isarIimaGroupFailureStatus
        INTEGER,

      isarIimaGroupSymmetry
        INTEGER,

      isarIimaGroupMinNumTxLinks
        INTEGER (1..32),

      isarIimaGroupMinNumRxLinks
        INTEGER (1..32),

      isarIimaGroupNeTxClkMode
        INTEGER,

      isarIimaGroupFeTxClkMode
        INTEGER,

      isarIimaGroupTxTimingRefLink
        INTEGER,

      isarIimaGroupRxTimingRefLink
        INTEGER,

      isarIimaGroupLastChange
        OCTET STRING,

      isarIimaGroupTxImaId
        INTEGER (0..255),

      isarIimaGroupRxImaId
        INTEGER (0..255),

      isarIimaGroupTxFrameLength
        INTEGER,

      isarIimaGroupRxFrameLength
        INTEGER,

      isarIimaGroupDiffDelayMax
        INTEGER,

      isarIimaGroupLeastDelayLink
        INTEGER,

      isarIimaGroupDiffDelayMaxObs
        INTEGER,

      isarIimaGroupAlphaValue
        INTEGER (1..2),

      isarIimaGroupBetaValue
        INTEGER (1..5),

      isarIimaGroupGammaValue
        INTEGER (1..5),

      isarIimaGroupRunningSecs
        INTEGER,

      isarIimaGroupUnavailSecs
        INTEGER,

      isarIimaGroupNeNumFailures
        INTEGER,

      isarIimaGroupFeNumFailures
        INTEGER,

      isarIimaGroupTxAvailCellRate
        INTEGER,

      isarIimaGroupRxAvailCellRate
        INTEGER,

      isarIimaGroupNumTxCfgLnks
        INTEGER,

      isarIimaGroupNumRxCfgLnks
        INTEGER,

      isarIimaGroupNumTxActLnks
        INTEGER,

      isarIimaGroupNumRxActLnks
        INTEGER,

      isarIimaGroupTestLinkIfIndex
        INTEGER,

      isarIimaGroupTestPattern
        INTEGER,

      isarIimaGroupTestProcStatus
        INTEGER
    }

isarIimaGroupIndex OBJECT-TYPE
    SYNTAX  INTEGER
    ACCESS  read-only
    STATUS  mandatory
    DESCRIPTION
           "A unique value for the IMA Group."
    ::= { isarIimaGroupEntry  1 }

-- isarIimaGroupRowStatus ::= { isarIimaGroupEntry  2 } : REMOVED

isarIimaGroupIfIndex OBJECT-TYPE
    SYNTAX  INTEGER
    ACCESS  read-only
    STATUS  mandatory
    DESCRIPTION
           "This object identifies the logical interface number
            ('ifIndex') assigned to this IMA group, and is used to 
            identify corresponding rows in the Interfaces MIB.
       
            Note that re-initialization of the management agent may 
            cause a client's 'isarIimaGroupIfIndex' to change."
    ::= { isarIimaGroupEntry  3 }

isarIimaGroupNeState OBJECT-TYPE
    SYNTAX  INTEGER {
                      notConfigured(1),
                      startUp(2),
                      startUpAck(3),
                      configAbortUnsupportedM(4),
                      configAbortIncompatibleSymmetry(5),
                      configAbortOther(6),
                      insufficientLinks(7),
                      blocked(8),
                      operational(9)
            }
    ACCESS  read-only
    STATUS  mandatory
    DESCRIPTION
           "The current operational state of the near-end IMA 
            Group State Machine."
    ::= { isarIimaGroupEntry  4 }

isarIimaGroupFeState OBJECT-TYPE
    SYNTAX  INTEGER {
                      notConfigured(1),
                      startUp(2),
                      startUpAck(3),
                      configAbortUnsupportedM(4),
                      configAbortIncompatibleSymmetry(5),
                      configAbortOther(6),
                      insufficientLinks(7),
                      blocked(8),
                      operational(9)
            }
    ACCESS  read-only
    STATUS  mandatory
    DESCRIPTION
           "The current operational state of the far-end IMA 
            Group State Machine."
    ::= { isarIimaGroupEntry  5 }

isarIimaGroupFailureStatus OBJECT-TYPE
    SYNTAX  INTEGER {
                      noFailure(1),
                      startUpNe(2),
                      startUpFe(3),
                      invalidMValueNe(4),
                      invalidMValueFe(5),
                      failedAssymetricNe(6),
                      failedAssymetricFe(7),
                      insufficientLinksNe(8),
                      insufficientLinksFe(9),
                      blockedNe(10),
                      blockedFe(11),
                      otherFailure(12)
            }

    ACCESS  read-only
    STATUS  mandatory
    DESCRIPTION
           "The current failure status of the IMA group (the reason why 
            the GTSM is in the down state."
    ::= { isarIimaGroupEntry  6 }

isarIimaGroupSymmetry OBJECT-TYPE
    SYNTAX  INTEGER {
                      symmetricOperation(1),
                      asymmetricOperation(2),
                      asymmetricConfiguration(3)
            }
    ACCESS  read-write
    STATUS  mandatory
    DESCRIPTION
           "Symmetry of the IMA group."
    DEFVAL  { symmetricOperation }
    ::= { isarIimaGroupEntry  7 }

isarIimaGroupMinNumTxLinks OBJECT-TYPE
    SYNTAX  INTEGER (1..32)
    ACCESS  read-write
    STATUS  mandatory
    DESCRIPTION
           "Minimum number of transmit links required to be Active for 
            the IMA group to be in the Up state."
    ::= { isarIimaGroupEntry  8 }

isarIimaGroupMinNumRxLinks OBJECT-TYPE
    SYNTAX  INTEGER (1..32)
    ACCESS  read-write
    STATUS  mandatory
    DESCRIPTION
           "Minimum number of receive links required to be Active for 
            the IMA group to be in the Up state."
    ::= { isarIimaGroupEntry  9 }

isarIimaGroupNeTxClkMode OBJECT-TYPE
    SYNTAX  INTEGER {
                      ctc(1),
                      itc(2)
            }
    ACCESS  read-write
    STATUS  mandatory
    DESCRIPTION
           "Transmit clocking mode used by the near-end IMA group.
            There are two possible modes: the Common Transmit 
            Clock (CTC) and the Independent Transmit Clock (ITC). 
            The CTC mode corresponds to the case when the transmit 
            clock of all IMA links are derived from the same source. 
            The ITC configuration corresponds to the case where there 
            is at least one IMA link whose transmit clock is derived 
            from a source different than at least another link transmit
            clock."           
    DEFVAL  { ctc }
    ::= { isarIimaGroupEntry  10 }

isarIimaGroupFeTxClkMode OBJECT-TYPE
    SYNTAX  INTEGER {
                      ctc(1),
                      itc(2)
            }
    ACCESS  read-only
    STATUS  mandatory
    DESCRIPTION
           "Transmit clocking mode used by the far-end IMA group.
            There are two possible modes: the Common Transmit 
            Clock (CTC) and the Independent Transmit Clock (ITC). 
            The CTC mode corresponds to the case when the transmit 
            clock of all IMA links are derived from the same source. 
            The ITC configuration corresponds to the case where there 
            is at least one IMA link whose transmit clock is derived 
            from a source different than at least another link transmit
            clock."
    ::= { isarIimaGroupEntry  11 }

isarIimaGroupTxTimingRefLink OBJECT-TYPE
    SYNTAX  INTEGER
    ACCESS  read-only
    STATUS  mandatory
    DESCRIPTION
           "The ifIndex of the transmit timing reference link to 
            be used by the near-end for IMA data cell clock recovery 
            from the ATM layer."
    ::= { isarIimaGroupEntry  12 }

isarIimaGroupRxTimingRefLink OBJECT-TYPE
    SYNTAX  INTEGER
    ACCESS  read-only
    STATUS  mandatory
    DESCRIPTION
           "The ifIndex of the receive timing reference link to be
            used by near-end for IMA data cell clock recovery toward 
            the ATM layer."
    ::= { isarIimaGroupEntry  13 }

isarIimaGroupLastChange OBJECT-TYPE
    SYNTAX  OCTET STRING (SIZE (8 | 11))
    ACCESS  read-only
    STATUS  mandatory
    DESCRIPTION
           "Not used by IAD4700 (always empty string).
            The entry of the ifTable has to be used."
    ::= { isarIimaGroupEntry  14 }

isarIimaGroupTxImaId OBJECT-TYPE
    SYNTAX  INTEGER (0..255)
    ACCESS  read-write
    STATUS  mandatory
    DESCRIPTION
           "The IMA ID currently in use by the near-end IMA function."
    ::= { isarIimaGroupEntry  15 }

isarIimaGroupRxImaId OBJECT-TYPE
    SYNTAX  INTEGER (0..255)
    ACCESS  read-only
    STATUS  mandatory
    DESCRIPTION
           "The IMA ID currently in use by the far-end IMA function."
    ::= { isarIimaGroupEntry  16 }

isarIimaGroupTxFrameLength OBJECT-TYPE
    SYNTAX  INTEGER {
                      m32(32),
                      m64(64),
                      m128(128),
                      m256(256)
            }
    ACCESS  read-write
    STATUS  mandatory
    DESCRIPTION
           "The frame length to be used by the IMA group in the 
            transmit  direction. Can only be set when the IMA group 
            is startup."
    DEFVAL  { m128 }
    ::= { isarIimaGroupEntry  17 }

isarIimaGroupRxFrameLength OBJECT-TYPE
    SYNTAX  INTEGER {
                      m32(32),
                      m64(64),
                      m128(128),
                      m256(256)
            }
    ACCESS  read-only
    STATUS  mandatory
    DESCRIPTION
           "Value of IMA frame length as received from remote IMA 
            function."
    ::= { isarIimaGroupEntry  18 }

isarIimaGroupDiffDelayMax OBJECT-TYPE
    SYNTAX  INTEGER
    ACCESS  read-write
    STATUS  mandatory
    DESCRIPTION
           "The maximum number of milliseconds of delay differential 
            among the links that will be tolerated on this interface."
    DEFVAL  { 25 }
    ::= { isarIimaGroupEntry  19 }

isarIimaGroupLeastDelayLink OBJECT-TYPE
    SYNTAX  INTEGER
    ACCESS  read-only
    STATUS  mandatory
    DESCRIPTION
           "The ifIndex of the link configured in the IMA 
            group which has the smallest link propagation delay. This 
            value has meaning only if at least 1 link has been 
            configured in the IMA group."
    ::= { isarIimaGroupEntry  20 }

isarIimaGroupDiffDelayMaxObs OBJECT-TYPE
    SYNTAX  INTEGER
    ACCESS  read-only
    STATUS  mandatory
    DESCRIPTION
           "The latest maximum differential delay observed (in 
            milliseconds), i.e. between the links having the least and 
            most link propagation delay, among the receive links that 
            are currently configured in the IMA group."
    ::= { isarIimaGroupEntry  21 }

isarIimaGroupAlphaValue OBJECT-TYPE
    SYNTAX  INTEGER (1..2)
    ACCESS  read-write
    STATUS  mandatory
    DESCRIPTION
           "This indicates the 'alpha' value used to specify the 
            number of consecutive invalid ICP cells to be detected 
            before moving to the IMA HUNT state."
    DEFVAL  { 2 }
    ::= { isarIimaGroupEntry  22 }

isarIimaGroupBetaValue OBJECT-TYPE
    SYNTAX  INTEGER (1..5)
    ACCESS  read-write
    STATUS  mandatory
    DESCRIPTION
           "This indicates the 'beta' value used to specify the 
            number of consecutive errored ICP cells to be detected 
            before moving to the IMA HUNT state."
    DEFVAL  { 2 }
    ::= { isarIimaGroupEntry  23 }

isarIimaGroupGammaValue OBJECT-TYPE
    SYNTAX  INTEGER (1..5)
    ACCESS  read-write
    STATUS  mandatory
    DESCRIPTION
           "This indicates the 'gamma' value used to specify the 
            number of consecutive valid ICP cells to be detected before 
            moving to the IMA SYNC state from the PRESYNC state."
    DEFVAL  { 1 }
    ::= { isarIimaGroupEntry  24 }

isarIimaGroupRunningSecs OBJECT-TYPE
    SYNTAX  INTEGER
    ACCESS  read-only
    STATUS  mandatory
    DESCRIPTION
           "The amount of time (in seconds) since this IMA group has 
            been in operation (up or down)."
    ::= { isarIimaGroupEntry  25 }

isarIimaGroupUnavailSecs OBJECT-TYPE
    SYNTAX  INTEGER
    ACCESS  read-only
    STATUS  mandatory
    DESCRIPTION
           "Count of one second intervals where the IMA Group Traffic 
            State Machine is Down."
    ::= { isarIimaGroupEntry  26 }

isarIimaGroupNeNumFailures OBJECT-TYPE
    SYNTAX  INTEGER
    ACCESS  read-only
    STATUS  mandatory
    DESCRIPTION
           "The number of times a near-end group failure (Config-Abort, 
            Insufficient-Links) has been reported since power-up or 
            reboot."
    ::= { isarIimaGroupEntry  27 }

isarIimaGroupFeNumFailures OBJECT-TYPE
    SYNTAX  INTEGER
    ACCESS  read-only
    STATUS  mandatory
    DESCRIPTION
           "The number of times a far-end group failure 
            (Config-Abort-FE, Insufficient-Links-FE, Blocked-FE) has 
            been reported since power-up or reboot. This is an optional 
            attribute."
    ::= { isarIimaGroupEntry  28 }

isarIimaGroupTxAvailCellRate OBJECT-TYPE
    SYNTAX  INTEGER
    ACCESS  read-only
    STATUS  mandatory
    DESCRIPTION
           "The current cell rate (truncated value in cells per second)
            provided by this IMA group in the transmit direction, 
            considering all the transmit links in the Active state."
    ::= { isarIimaGroupEntry  29 }

isarIimaGroupRxAvailCellRate OBJECT-TYPE
    SYNTAX  INTEGER
    ACCESS  read-only
    STATUS  mandatory
    DESCRIPTION
           "The current cell rate (truncated value in cells per second) 
            provided by this IMA group in the receive direction, 
            considering all the receive links in the Active state."
    ::= { isarIimaGroupEntry  30 }


-- isarIimaGroupNumTxCfgLnks is used by a network operator to tell how 
-- many links are configured for transmit in the IMA group.

isarIimaGroupNumTxCfgLnks OBJECT-TYPE
    SYNTAX  INTEGER
    ACCESS  read-only
    STATUS  mandatory
    DESCRIPTION
           "The number of links that are configured to transmit in this
            IMA group."
    ::= { isarIimaGroupEntry  31 }


-- isarIimaGroupNumRxCfgLnks is used by a network operator to tell how 
-- many links are configured for receive in the IMA group.

isarIimaGroupNumRxCfgLnks OBJECT-TYPE
    SYNTAX  INTEGER
    ACCESS  read-only
    STATUS  mandatory
    DESCRIPTION
           "The number of links that are configured to receive in this 
            IMA group."
    ::= { isarIimaGroupEntry  32 }


-- isarIimaGroupNumTxActLnks is used by a network operator to tell how
-- many links which are configured for transmit are also Active.

isarIimaGroupNumTxActLnks OBJECT-TYPE
    SYNTAX  INTEGER
    ACCESS  read-only
    STATUS  mandatory
    DESCRIPTION
           "The number of links which are configured to transmit and 
            are currently Active in this IMA group."
    ::= { isarIimaGroupEntry  33 }


-- isarIimaGroupNumRxActLnks is used by a network operator to tell how
-- many links which are configured for receive are also Active.

isarIimaGroupNumRxActLnks OBJECT-TYPE
    SYNTAX  INTEGER
    ACCESS  read-only
    STATUS  mandatory
    DESCRIPTION
           "The number of links which are configured to receive and are
            currently Active in this IMA group."
    ::= { isarIimaGroupEntry  34 }


--
-- Test Pattern Procedure control objects. These objects are
-- implemented if the IMA implements the Test Pattern Procedure. 
-- In this case all test pattern procedure related objects must be
-- implemented. Specifically these are
-- 
-- isarIimaGroupTestLinkIfIndex
-- isarIimaGroupTestPattern
-- isarIimaGroupTestProcStatus
-- isarIimaLinkTestProcStatus
-- isarIimaLinkRxTestPattern
--

isarIimaGroupTestLinkIfIndex OBJECT-TYPE
    SYNTAX  INTEGER
    ACCESS  read-only
    STATUS  optional
    DESCRIPTION
           "This object is used to designate an interface as the Test 
            Link.  A value of -1 specifies that the implementation may 
            choose the Test Link. In this case, the implementation may 
            also choose the value of 'isarIimaGroupTestPattern'.
            IAD4700 v1 / v2.0 : not supported.
            (DEFVAL is not used because of compiling errors)"
--    DEFVAL  { -1 }
    ::= { isarIimaGroupEntry  35 }

isarIimaGroupTestPattern OBJECT-TYPE
    SYNTAX  INTEGER
    ACCESS  read-only
    STATUS  optional
    DESCRIPTION
           "The value of this object is used to specify the test pattern
            in an IMA group loopback operation. A value in the range 0 
            to 255 designates a specific pattern. A value of -1 
            specifies that the implementation may choose the value. In 
            this case, the implementation may also choose the value of
            'isarIimaGroupTestLinkIfIndex'.
            IAD4700 v1 / v2.0 : not supported.
            (DEFVAL is not used because of compiling errors)"
--    DEFVAL  { -1 }
    ::= { isarIimaGroupEntry  36 }

isarIimaGroupTestProcStatus OBJECT-TYPE
    SYNTAX  INTEGER {
                      disabled(1),
                      operating(2),
                      linkFail(3)
            }
    ACCESS  read-only
    STATUS  optional
    DESCRIPTION
           "This object is used to enable or disable the
            Test Pattern Procedure, and to note whether at least one
            link failed the test.

            The test is started by setting operating(2) status. If any
            link should fail the test, the IMA will set the status to
            linkfail(3). The linkfail(3) state will persist until
            either the disabled(1) state is set or until no instance
            of isarIimaLinkTestProcStatus has the value linkfail(3).

            Only the values disabled(1) and operating(2) may be written.
            Writing the operating(2) value will not cause clearing of
            the linkfail(3) state.
            IAD4700 v1 / v2.0 : not supported."
    DEFVAL  { disabled }
    ::= { isarIimaGroupEntry  37 }



--
-- The IMA Group - ifIndex Mapping Table
--
-- Note that the Group Index is different than the ifIndex.
--
-- The "ifIndex Mapping" table allows the Unit Management to
-- perform easy look-ups (no searches and sorts). 
 

isarIimaGroupMappingTable OBJECT-TYPE
    SYNTAX  SEQUENCE OF IsarIimaGroupMappingEntry
    ACCESS  not-accessible
    STATUS  mandatory
    DESCRIPTION
           "A table mapping the 'ifIndex' values of 
            'isarIimaGroupIfIndex' to the 'isarIimaGroupIndex' values 
            of the corresponding IMA group."
    ::= { isarIatmfImaMIBObjects  2 }

isarIimaGroupMappingEntry OBJECT-TYPE
    SYNTAX  IsarIimaGroupMappingEntry
    ACCESS  not-accessible
    STATUS  mandatory
    DESCRIPTION
           "Each row describes one ifIndex --> isarIimaGroupIndex 
            mapping."
    INDEX   { ifIndex }
    ::= { isarIimaGroupMappingTable  1 }

IsarIimaGroupMappingEntry ::=
    SEQUENCE {
      isarIimaGroupMappingIndex
        INTEGER
    }

isarIimaGroupMappingIndex OBJECT-TYPE
    SYNTAX  INTEGER
    ACCESS  read-only
    STATUS  mandatory
    DESCRIPTION
           "The isarIimaGroupIndex of the IMA Group which implements the
            specified interface."
    ::= { isarIimaGroupMappingEntry  1 }



-- The IMA link status and configuration table
-- Each entry in the table contains status information about a link
-- which is part of an IMA group.


isarIimaLinkTable OBJECT-TYPE
    SYNTAX  SEQUENCE OF IsarIimaLinkEntry
    ACCESS  not-accessible
    STATUS  mandatory
    DESCRIPTION
           "The IMA group Link Status and Configuration table."
    ::= { isarIatmfImaMIBObjects  3 }

isarIimaLinkEntry OBJECT-TYPE
    SYNTAX  IsarIimaLinkEntry
    ACCESS  not-accessible
    STATUS  mandatory
    DESCRIPTION
           "An entry in the IMA Group Link table."
    INDEX   { isarIimaLinkIfIndex }
    ::= { isarIimaLinkTable  1 }

IsarIimaLinkEntry ::=
    SEQUENCE {
      isarIimaLinkIfIndex
        INTEGER,

      isarIimaLinkRowStatus
        INTEGER,

      isarIimaLinkGroupIndex
        INTEGER,

      isarIimaLinkNeTxState
        INTEGER,

      isarIimaLinkNeRxState
        INTEGER,

      isarIimaLinkFeTxState
        INTEGER,

      isarIimaLinkFeRxState
        INTEGER,

      isarIimaLinkNeRxFailureStatus
        INTEGER,

      isarIimaLinkFeRxFailureStatus
        INTEGER,

      isarIimaLinkTxLid
        INTEGER (0..31),

      isarIimaLinkRxLid
        INTEGER (0..31),

      isarIimaLinkRelDelay
        INTEGER,

      isarIimaLinkImaViolations
        INTEGER,

      isarIimaLinkOifAnomalies
        INTEGER,

      isarIimaLinkNeSevErroredSec
        INTEGER,

      isarIimaLinkFeSevErroredSec
        INTEGER,

      isarIimaLinkNeUnavailSec
        INTEGER,

      isarIimaLinkFeUnavailSec
        INTEGER,

      isarIimaLinkNeTxUnusableSec
        INTEGER,

      isarIimaLinkNeRxUnusableSec
        INTEGER,

      isarIimaLinkFeTxUnusableSec
        INTEGER,

      isarIimaLinkFeRxUnusableSec
        INTEGER,

      isarIimaLinkNeTxNumFailures
        INTEGER,

      isarIimaLinkNeRxNumFailures
        INTEGER,

      isarIimaLinkFeTxNumFailures
        INTEGER,

      isarIimaLinkFeRxNumFailures
        INTEGER,

      isarIimaLinkTxStuffs
        INTEGER,

      isarIimaLinkRxStuffs
        INTEGER,

      isarIimaLinkRxTestPattern
        INTEGER (0..255),

      isarIimaLinkTestProcStatus
        INTEGER,

      isarIimaLinkTransmitClockSource
        INTEGER
    }

isarIimaLinkIfIndex OBJECT-TYPE
    SYNTAX  INTEGER
    ACCESS  read-only
    STATUS  mandatory
    DESCRIPTION
           "This corresponds to the 'ifIndex' of the MIB-II interface 
            on which this link is established. This object also
            corresponds to the logical number ('ifIndex') assigned to 
            this IMA link."
    ::= { isarIimaLinkEntry  1 }

isarIimaLinkRowStatus OBJECT-TYPE
    SYNTAX  INTEGER {
                      -- the following two values are states:
                      -- these values may be read or written
                      active(1),
                      notInService(2),
 
                      -- the following value is a state:
                      -- this value may be read, but not written
                      notReady(3),
 
                      -- the following three values are
                      -- actions: these values may be written,
                      --   but are never read
                      createAndGo(4),
                      createAndWait(5),
                      destroy(6)
            }
    ACCESS  read-write
    STATUS  mandatory
    DESCRIPTION
           "The isarIimaLinkRowStatus object allows create, change and 
            delete operations on isarIimaLinkTable entries.  
       
            To create a new conceptual row (or instance) of the 
            isarIimaLinkTable, isarIimaLinkRowStatus must be set to 
            'createAndWait' or 'createAndGo.'
            A successful set of the object isarIimaLinkGroupIndex must 
            be performed before the RowStatus of this new row can 
            transition to the 'Active' state. The isarIimaLinkGroupIndex
            provides the association between a physical IMA link to an 
            IMA group.

            To change (modify) an isarIimaLinkTable entry, the 
            isarIimaLinkRowStatus object must be set to 'notInService'.
            Only then can the conceptual row be changed. Setting object
            isarIimaLinkGroupIndex to a different value has the effect 
            of changing the association between a physical IMA link and
            an IMA group. To place the link 'in group', the 
            isarIimaLinkRowStatus object is set to 'Active'. 
            While the row is not in 'Active' state, both the Transmit 
            and Receive IMA state machines are in the 'Not In Group' 
            state.

            To remove (delete) an isarIimaLinkTable entry from this 
            table, set this object to 'destroy.'

            A network manager may elect to perform a delete operation 
            followed immediately by a create operation instead of a 
            modify operation. The net effect of the delete/create is to 
            re-instantiate (reset) agent counters defined in this table.
            The SNMPv2 MAX-ACCESS is read-create."
    ::= { isarIimaLinkEntry  2 }

isarIimaLinkGroupIndex OBJECT-TYPE
    SYNTAX  INTEGER
    ACCESS  read-write
    STATUS  mandatory
    DESCRIPTION
           "The value which identifies the IMA group (imaGroupIndex) 
            of which this link is a member.
            The SNMPv2 MAX-ACCESS is read-create."
    ::= { isarIimaLinkEntry  3 }

isarIimaLinkNeTxState OBJECT-TYPE
    SYNTAX  INTEGER {
                      notInGroup(1),
                      unusableNoGivenReason(2),
                      unusableFault(3),
                      unusableMisconnected(4),
                      unusableBlocked(5),
                      unusableFailed(6),
                      usable(7),
                      active(8)
            }
    ACCESS  read-only
    STATUS  mandatory
    DESCRIPTION
           "The current state of the near-end transmit link."
    ::= { isarIimaLinkEntry  4 }

isarIimaLinkNeRxState OBJECT-TYPE
    SYNTAX  INTEGER {
                      notInGroup(1),
                      unusableNoGivenReason(2),
                      unusableFault(3),
                      unusableMisconnected(4),
                      unusableBlocked(5),
                      unusableFailed(6),
                      usable(7),
                      active(8)
            }
    ACCESS  read-only
    STATUS  mandatory
    DESCRIPTION
           "The current state of the near-end receive link."
    ::= { isarIimaLinkEntry  5 }

isarIimaLinkFeTxState OBJECT-TYPE
    SYNTAX  INTEGER {
                      notInGroup(1),
                      unusableNoGivenReason(2),
                      unusableFault(3),
                      unusableMisconnected(4),
                      unusableBlocked(5),
                      unusableFailed(6),
                      usable(7),
                      active(8)
            }
    ACCESS  read-only
    STATUS  mandatory
    DESCRIPTION
           "The current state of the far-end transmit link as reported
            via ICP cells."
    ::= { isarIimaLinkEntry  6 }

isarIimaLinkFeRxState OBJECT-TYPE
    SYNTAX  INTEGER {
                      notInGroup(1),
                      unusableNoGivenReason(2),
                      unusableFault(3),
                      unusableMisconnected(4),
                      unusableBlocked(5),
                      unusableFailed(6),
                      usable(7),
                      active(8)
            }
    ACCESS  read-only
    STATUS  mandatory
    DESCRIPTION
           "The current state of the far-end receive link as reported
            via ICP cells."
    ::= { isarIimaLinkEntry  7 }

isarIimaLinkNeRxFailureStatus OBJECT-TYPE
    SYNTAX  INTEGER {
                      noFailure(1),
                      imaLinkFailure(2),
                      lifFailure(3),
                      lodsFailure(4),
                      misConnected(5),
                      blocked(6),
                      fault(7),
                      farEndTxLinkUnusable(8),
                      farEndRxLinkUnusable(9)
            }
    ACCESS  read-only
    STATUS  mandatory
    DESCRIPTION
           "The current link failure status of the near-end receive 
            link."
    ::= { isarIimaLinkEntry  8 }

isarIimaLinkFeRxFailureStatus OBJECT-TYPE
    SYNTAX  INTEGER {
                      noFailure(1),
                      imaLinkFailure(2),
                      lifFailure(3),
                      lodsFailure(4),
                      misConnected(5),
                      blocked(6),
                      fault(7),
                      farEndTxLinkUnusable(8),
                      farEndRxLinkUnusable(9)
            }
    ACCESS  read-only
    STATUS  mandatory
    DESCRIPTION
           "The current link failure status of the far-end receive link 
            as reported via ICP cells."
    ::= { isarIimaLinkEntry  9 }

isarIimaLinkTxLid OBJECT-TYPE
    SYNTAX  INTEGER (0..31)
    ACCESS  read-only
    STATUS  mandatory
    DESCRIPTION
           "The outgoing LID used currently on the link by the local 
            end. This value has meaning only if the link belongs to an 
            IMA group."
    ::= { isarIimaLinkEntry  10 }

isarIimaLinkRxLid OBJECT-TYPE
    SYNTAX  INTEGER (0..31)
    ACCESS  read-only
    STATUS  mandatory
    DESCRIPTION
           "The incoming LID used currently on the link by the remote 
            end as reported via ICP cells. This value has meaning only 
            if the link belongs to an IMA group."
    ::= { isarIimaLinkEntry  11 }

isarIimaLinkRelDelay OBJECT-TYPE
    SYNTAX  INTEGER
    ACCESS  read-only
    STATUS  mandatory
    DESCRIPTION
           "The latest measured delay (in milliseconds) on this link 
            relative to the link, in the same IMA group, with the least 
            delay."
    ::= { isarIimaLinkEntry  12 }

isarIimaLinkImaViolations OBJECT-TYPE
    SYNTAX  INTEGER
    ACCESS  read-only
    STATUS  mandatory
    DESCRIPTION
           "ICP violations: count of errored, invalid or missing ICP 
            cells during non-SES-IMA condition."
    ::= { isarIimaLinkEntry  13 }

isarIimaLinkOifAnomalies OBJECT-TYPE
    SYNTAX  INTEGER
    ACCESS  read-only
    STATUS  mandatory
    DESCRIPTION
           "The number of OIF anomalies during non-SES-IMA condition at 
            the near-end. This is an optional attribute."
    ::= { isarIimaLinkEntry  14 }

isarIimaLinkNeSevErroredSec OBJECT-TYPE
    SYNTAX  INTEGER
    ACCESS  read-only
    STATUS  mandatory
    DESCRIPTION
           "Count of one second intervals containing several IV-IMA, 
            or one or more link defects (e.g., LOS, OOF/LOF, AIS, LCD), 
            LIF, LODS defects during non-UAS-IMA condition."
    ::= { isarIimaLinkEntry  15 }

isarIimaLinkFeSevErroredSec OBJECT-TYPE
    SYNTAX  INTEGER
    ACCESS  read-only
    STATUS  mandatory
    DESCRIPTION
           "Count of one second intervals containing one or more 
            RDI-IMA defects."
    ::= { isarIimaLinkEntry  16 }

isarIimaLinkNeUnavailSec OBJECT-TYPE
    SYNTAX  INTEGER
    ACCESS  read-only
    STATUS  mandatory
    DESCRIPTION
           "Count of unavailable seconds at near-end: unavailability 
            begins at the onset of 10 contiguous SES-IMA and ends at 
            the onset of 10 contiguous seconds with no SES-IMA."
    ::= { isarIimaLinkEntry  17 }

isarIimaLinkFeUnavailSec OBJECT-TYPE
    SYNTAX  INTEGER
    ACCESS  read-only
    STATUS  mandatory
    DESCRIPTION
           "Count of unavailable seconds at far-end: unavailability 
            begins at the onset of 10 contiguous SES-IMA-FE and ends 
            at the onset of 10 contiguous seconds with no SES-IMA-FE."
    ::= { isarIimaLinkEntry  18 }

isarIimaLinkNeTxUnusableSec OBJECT-TYPE
    SYNTAX  INTEGER
    ACCESS  read-only
    STATUS  mandatory
    DESCRIPTION
           "Tx Unusable seconds: count of Unusable seconds at the near 
            end Tx LSM."
    ::= { isarIimaLinkEntry  19 }

isarIimaLinkNeRxUnusableSec OBJECT-TYPE
    SYNTAX  INTEGER
    ACCESS  read-only
    STATUS  mandatory
    DESCRIPTION
           "Rx Unusable seconds: count of Unusable seconds at the near 
            end Rx LSM."
    ::= { isarIimaLinkEntry  20 }

isarIimaLinkFeTxUnusableSec OBJECT-TYPE
    SYNTAX  INTEGER
    ACCESS  read-only
    STATUS  mandatory
    DESCRIPTION
           "Tx Unusable seconds at far-end: count of seconds with 
            Unusable indications from the far-end Tx LSM."
    ::= { isarIimaLinkEntry  21 }

isarIimaLinkFeRxUnusableSec OBJECT-TYPE
    SYNTAX  INTEGER
    ACCESS  read-only
    STATUS  mandatory
    DESCRIPTION
           "Rx Unusable seconds at far-end: count of seconds with 
            Unusable indications from the far-end Rx LSM."
    ::= { isarIimaLinkEntry  22 }

isarIimaLinkNeTxNumFailures OBJECT-TYPE
    SYNTAX  INTEGER
    ACCESS  read-only
    STATUS  mandatory
    DESCRIPTION
           "The number of times a near-end transmit failure alarm 
            condition has been entered on this link."
    ::= { isarIimaLinkEntry  23 }

isarIimaLinkNeRxNumFailures OBJECT-TYPE
    SYNTAX  INTEGER
    ACCESS  read-only
    STATUS  mandatory
    DESCRIPTION
           "The number of times a near-end receive failure alarm 
            condition has been entered on this link (i.e., LIF, LODS, 
            Mis-Connected, RDI-IMA)."
    ::= { isarIimaLinkEntry  24 }

isarIimaLinkFeTxNumFailures OBJECT-TYPE
    SYNTAX  INTEGER
    ACCESS  read-only
    STATUS  optional
    DESCRIPTION
           "The number of times a far-end transmit failure alarm 
            condition has been entered on this link. This is an 
            optional attribute."
    ::= { isarIimaLinkEntry  25 }

isarIimaLinkFeRxNumFailures OBJECT-TYPE
    SYNTAX  INTEGER
    ACCESS  read-only
    STATUS  optional
    DESCRIPTION
           "The number of times a far-end receive failure alarm 
            condition has been entered on this link (i.e., LIF, LODS, 
            Mis-Connected, RDI-IMA).
            This is an optional attribute."
    ::= { isarIimaLinkEntry  26 }

isarIimaLinkTxStuffs OBJECT-TYPE
    SYNTAX  INTEGER
    ACCESS  read-only
    STATUS  optional
    DESCRIPTION
           "Counts of stuff events inserted in the transmit direction.
            This is an optional attribute."
    ::= { isarIimaLinkEntry  27 }

isarIimaLinkRxStuffs OBJECT-TYPE
    SYNTAX  INTEGER
    ACCESS  read-only
    STATUS  optional
    DESCRIPTION
           "Counts of stuff events detected in the receive direction.
            This is an optional attribute."
    ::= { isarIimaLinkEntry  28 }


--
-- Test Pattern Procedure control objects. These objects are implemented
-- if the IMA implements the Test Pattern Procedure. In this case all
-- test pattern procedure related objects must be implemented. 
-- Specifically these are
-- 
-- isarIimaGroupTestLinkIfIndex
-- isarIimaGroupTestPattern
-- isarIimaGroupTestProcStatus
-- isarIimaLinkTestProcStatus
-- isarIimaLinkRxTestPattern
--

isarIimaLinkRxTestPattern OBJECT-TYPE
    SYNTAX  INTEGER (0..255)
    ACCESS  read-only
    STATUS  mandatory
    DESCRIPTION
           "This object identifies the test pattern received in the
            ICP Cell (octet 17) on the link during the IMA Test Pattern
            Procedure. This value may then be compared to the 
            transmitted test pattern."
    ::= { isarIimaLinkEntry  29 }

isarIimaLinkTestProcStatus OBJECT-TYPE
    SYNTAX  INTEGER {
                      disabled(1),
                      operating(2),
                      linkFail(3)
            }
    ACCESS  read-only
    STATUS  mandatory
    DESCRIPTION
           "This value indicates the current state of the Test Pattern
            Procedure. If the value is disabled(1), the test is not
            running. A value of operating(2) means the test is running
            and no error has been found on this interface. A value of
            linkFail(3) means an error has been detected on this link
            during the test.

            Once an error occurs, the linkFail(3) value is latched until
            either this object is read or until the 
            isarIimaGroupTestProcStatus is moved to disabled(1). Once 
            read, if the error no longer persists, a subsequent read 
            will report the value operating(2)."
    ::= { isarIimaLinkEntry  30 }

isarIimaLinkTransmitClockSource OBJECT-TYPE
    SYNTAX  INTEGER {
                      loopTiming(1),
                      systemTiming(2)
            }
    ACCESS  read-write
    STATUS  mandatory
    DESCRIPTION
           "The source of Transmit Clock.
            'loopTiming' indicates that the recovered receive 
             clock is used as the transmit clock.

            'systemTiming' indicates that a local clock source is used
             or when an external clock is attached to the box containing
             the interface."
    ::= { isarIimaLinkEntry  31 }






--
-- ISAR specific extensions
--



--  IMA group configuration table

isarIimaGroupConfigTable OBJECT-TYPE
    SYNTAX  SEQUENCE OF IsarIimaGroupConfigEntry
    ACCESS  not-accessible
    STATUS  mandatory
    DESCRIPTION
           "The IMA group configuration table contains group specific
            parameters of one IMA group.
            Rows in this table are created when rows are created in
            isarIimaGroupTable."
    ::= { isarIatmfImaMIBObjects  4 }

isarIimaGroupConfigEntry OBJECT-TYPE
    SYNTAX  IsarIimaGroupConfigEntry
    ACCESS  not-accessible
    STATUS  mandatory
    DESCRIPTION
           "An entry in the IMA group configuration table."
    INDEX   { isarIimaGroupIndex }
    ::= { isarIimaGroupConfigTable  1 }

IsarIimaGroupConfigEntry ::=
    SEQUENCE {
      isarIimaGroupLogicalPort
        INTEGER,

      isarIimaGroupMaxDiffDelay
        INTEGER,

      isarIimaGroupSelectMethod
        INTEGER,

      isarIimaGroupMinActiveLinks
        INTEGER,

      isarIimaGroupCtcMode
        INTEGER,

      isarIimaGroupActTime
        INTEGER,

      isarIimaGroupDeActTime
        INTEGER

    }

isarIimaGroupLogicalPort OBJECT-TYPE
    SYNTAX  INTEGER
    ACCESS  read-write
    STATUS  mandatory
    DESCRIPTION
           "Logical port number of the IMA Group."
    ::= { isarIimaGroupConfigEntry  1 }

isarIimaGroupMaxDiffDelay OBJECT-TYPE
    SYNTAX  INTEGER
    ACCESS  read-write
    STATUS  mandatory
    DESCRIPTION
           "Maximum differential delay in milliseconds."
    ::= { isarIimaGroupConfigEntry  2 }

isarIimaGroupSelectMethod OBJECT-TYPE
    SYNTAX  INTEGER {
                      delayOptimized(1),
                      bandwidthOptimized(2)
            }
    ACCESS  read-write
    STATUS  mandatory
    DESCRIPTION
           "Method for selecting links in group."
    ::= { isarIimaGroupConfigEntry  3 }

isarIimaGroupMinActiveLinks OBJECT-TYPE
    SYNTAX  INTEGER
    ACCESS  read-write
    STATUS  mandatory
    DESCRIPTION
           "Minimum of active links."
    ::= { isarIimaGroupConfigEntry  4 }

isarIimaGroupCtcMode OBJECT-TYPE
    SYNTAX  INTEGER {
                      ctc(1),
                      itc(2)
            }
    ACCESS  read-write
    STATUS  mandatory
    DESCRIPTION
           "CTC or ITC mode."
    ::= { isarIimaGroupConfigEntry  5 }

isarIimaGroupActTime OBJECT-TYPE
    SYNTAX  INTEGER
    ACCESS  read-write
    STATUS  mandatory
    DESCRIPTION
           "Activation time in milliseconds."
    ::= { isarIimaGroupConfigEntry  6 }

isarIimaGroupDeActTime OBJECT-TYPE
    SYNTAX  INTEGER
    ACCESS  read-write
    STATUS  mandatory
    DESCRIPTION
           "DeActivation time in milliseconds."
    ::= { isarIimaGroupConfigEntry  7 }




--
-- ISAR atmfImaMIBObjects : end
--  




-- This file cannot be used to create SNMP agent.
-- The file isarOneFile.my has to be used to create the agent.



-- isarIoamMIBObjects         OBJECT IDENTIFIER ::= { isar  12 }


--
-- ISAR oamMIBObjects : begin
--  
-- enterprise MIB for OAM
-- The MIB is written for SNMPv1.

isarIoamNodeId OBJECT-TYPE
    SYNTAX  OCTET STRING (SIZE (16))
    ACCESS  read-write
    STATUS  mandatory
    DESCRIPTION
           "Value used in the OAM loopback cells to indicate the source
            or the loopback location.
            The default value is 'all ones'."
    ::= { isarIoamMIBObjects  1 }



-- continuity check table
-- This table is optional

isarIoamContCheckTable OBJECT-TYPE
    SYNTAX  SEQUENCE OF IsarIoamContCheckEntry
    ACCESS  not-accessible
    STATUS  mandatory
    DESCRIPTION
           "The continuity check table offers the operator the
            possibility to engage OAM Continuity Check on selected VPC
            (F4 flow) or VCC (F5 flow) connections or connection
            segments.  The operator can determine the flow
            (isarIoamContCheckVci equal to zero means F4 flow, every
            other value means F5 flow), the type (value different from
            none(1) activates the flow) and the direction of the flow.
            Loss of continuity will result in an alarm.
            INDEX : ifIndex is the index of the ATM layer."
    ::= { isarIoamMIBObjects  2 }

isarIoamContCheckEntry OBJECT-TYPE
    SYNTAX  IsarIoamContCheckEntry
    ACCESS  not-accessible
    STATUS  mandatory
    DESCRIPTION
           "One row in the isarIoamContCheckTable."
    INDEX   { ifIndex, isarIoamContCheckVpi, isarIoamContCheckVci }
    ::= { isarIoamContCheckTable  1 }


IsarIoamContCheckEntry ::=
    SEQUENCE { 
      isarIoamContCheckVpi
        INTEGER,
        
      isarIoamContCheckVci
        INTEGER,
        
      isarIoamContCheckType
        INTEGER,
        
      isarIoamContCheckDirection
        INTEGER,
        
      isarIoamContCheckActivProc
        INTEGER,
        
      isarIoamContCheckRowStatus
        INTEGER

    }


isarIoamContCheckVpi OBJECT-TYPE
    SYNTAX  INTEGER (0..4095)
    ACCESS  read-only
    STATUS  mandatory
    DESCRIPTION
           "Vpi has to be specified in case of VC or VP end-to-end
            or segment continuity check."
    ::= { isarIoamContCheckEntry  1 }

isarIoamContCheckVci OBJECT-TYPE
    SYNTAX  INTEGER (0..65535)
    ACCESS  read-only
    STATUS  mandatory
    DESCRIPTION
           "This object has the value zero in case of VP end-to-end or
            segment continuity check (not in IAD4700 v1.0/v1.1/v2.0).
            It is the Vci in case of VC end-to-end or segment
            continuity check."
    ::= { isarIoamContCheckEntry  2 }

isarIoamContCheckType OBJECT-TYPE
    SYNTAX  INTEGER {
                      none(1),
                      activeSegment(2),
                      activeEnd2End(3),
                      activeBoth(4)
                    }
    ACCESS  read-write
    STATUS  mandatory
    DESCRIPTION
           "The type of the continuity check."
    ::= { isarIoamContCheckEntry  3 }

isarIoamContCheckDirection OBJECT-TYPE
    SYNTAX  INTEGER {
                      directionBA(1),
                      directionAB(2),
                      directionBoth(3)
                    }
    ACCESS  read-write
    STATUS  mandatory
    DESCRIPTION
           "The B-A direction means that the endpoint B is commanded
            to activate the source-process of the continuity check
            function and the endpoint A is commanded to activate the
            sink-process of the continuity check function.
            The A-B direction means that the endpoint A is commanded
            to activate the source-process of the continuity check
            function and the endpoint B is commanded to activate the
            sink-process of the continuity check function."
    ::= { isarIoamContCheckEntry  4 }

isarIoamContCheckActivProc OBJECT-TYPE
    SYNTAX  INTEGER {
                      disabled(1),
                      enabled(2)
                    }
    ACCESS  read-write
    STATUS  mandatory
    DESCRIPTION
           "Continuity check activation procedure.
            disabled : the operator has to configure both endpoints
            enabled : the operator has to configure this endpoint, the
                      other endpoint is configured via OAM activation
                      cells.  Traps are generated for success or 
                      failure."
    ::= { isarIoamContCheckEntry  5 }


isarIoamContCheckRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
                    }
    ACCESS  read-write
    STATUS  mandatory
    DESCRIPTION
           "This object is used to create and delete rows in the 
            isarIoamContCheckTable.
            The SNMPv2 MAX-ACCESS is read-create."
    ::= { isarIoamContCheckEntry  6 }



-- loopback table
-- This table is optional

isarIoamLoopbackTable OBJECT-TYPE
    SYNTAX  SEQUENCE OF IsarIoamLoopbackEntry
    ACCESS  not-accessible
    STATUS  mandatory
    DESCRIPTION
           "The loopback table offers the operator the possibility to
            engage OAM Loopback on selected VPC (F4 flow) or VCC (F5
            flow) connections or connection segments.  The operator
            can determine the flow (isarIoamLoopbackVci equal to zero
            means F4 flow, every other value means F5 flow), the type
            (value different from none(1) activate the flow) and
            optional the loopback location.  No loopback location 
            specified means the next connection end-point or segment
            end-point.
           
            INDEX : ifIndex is the index of the ATM layer."
    ::= { isarIoamMIBObjects  3 }

isarIoamLoopbackEntry OBJECT-TYPE
    SYNTAX  IsarIoamLoopbackEntry
    ACCESS  not-accessible
    STATUS  mandatory
    DESCRIPTION
           "One row in the isarIoamLoopbackTable."
    INDEX   { ifIndex, isarIoamLoopbackVpi, isarIoamLoopbackVci }
    ::= { isarIoamLoopbackTable  1 }


IsarIoamLoopbackEntry ::=
    SEQUENCE { 
      isarIoamLoopbackVpi
        INTEGER,
        
      isarIoamLoopbackVci
        INTEGER,
        
      isarIoamLoopbackType
        INTEGER,
        
      isarIoamLoopbackLocationId
        OCTET STRING,
        
      isarIoamLoopbackStatus
        INTEGER,

      isarIoamLoopbackRowStatus
        INTEGER
    }
    
isarIoamLoopbackVpi OBJECT-TYPE
    SYNTAX  INTEGER (0..4095)
    ACCESS  read-only
    STATUS  mandatory
    DESCRIPTION
           "The Vpi has to be specified in case of VC or VP end-to-end
            or segment loopback."
    ::= { isarIoamLoopbackEntry  1 }

isarIoamLoopbackVci OBJECT-TYPE
    SYNTAX  INTEGER (0..65535)
    ACCESS  read-only
    STATUS  mandatory
    DESCRIPTION
           "This object has the value zero in case of VP end-to-end or
            segment loopback.  
            It is the Vci in case of VC end-to-end or segment loopback."
    ::= { isarIoamLoopbackEntry  2 }

isarIoamLoopbackType OBJECT-TYPE
    SYNTAX  INTEGER {
                      none(1),
                      segmentOam(2),
                      end2EndOam(3)
                    }
    ACCESS  read-write
    STATUS  mandatory
    DESCRIPTION
           "The type of the loopback.
            Loopback is activated when type is changed into segmentOam
            or end2EndOam.
            Changes are not allowed when isarIoamLoopbackStatus = 
            initiated."
    ::= { isarIoamLoopbackEntry  3 }

isarIoamLoopbackLocationId OBJECT-TYPE
    SYNTAX  OCTET STRING (SIZE (16))
    ACCESS  read-write
    STATUS  optional
    DESCRIPTION
           "Identifies the connection point along the virtual
            connection or connection segment where the loopback is to
            occur.
            The default value is 'all ones'. (Not done via DEFVAL because
            EMANATE generates the wrong code)."
    ::= { isarIoamLoopbackEntry  4 }

isarIoamLoopbackStatus OBJECT-TYPE
    SYNTAX  INTEGER {
                      none(1),
                      initiated(2),
                      success(3),
                      failed(4)
            }
    ACCESS  read-only
    STATUS  optional
    DESCRIPTION
           "Status of loopback.
              none : row created and loopback not started
              initiated : loopback cell has been sent
              success : loopback cell received
              failed : loopback cell not received within x seconds."
    DEFVAL { none }
    ::= { isarIoamLoopbackEntry  5 }

isarIoamLoopbackRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
                    }
    ACCESS  read-write
    STATUS  mandatory
    DESCRIPTION
           "This object is used to create and delete rows in the 
            isarIoamLoopbackTable.
            The SNMPv2 MAX-ACCESS is read-create."
    ::= { isarIoamLoopbackEntry  6 }



isarIoamTraps OBJECT IDENTIFIER     ::= { isarIoamMIBObjects 4 }
                                    
isarIoamCCActivationConfirmed TRAP-TYPE
    ENTERPRISE  isarIoamTraps
    VARIABLES   { ifIndex, 
                  isarIoamContCheckVpi, 
                  isarIoamContCheckVci 
                 }
    DESCRIPTION
           "isarIoamContCheckActivProc = enabled and continuity check
            is activated."
    ::= 1

isarIoamCCActivationDenied TRAP-TYPE
    ENTERPRISE  isarIoamTraps
    VARIABLES   { ifIndex, 
                  isarIoamContCheckVpi, 
                  isarIoamContCheckVci 
                 }
    DESCRIPTION
           "isarIoamContCheckActivProc = enabled and continuity check
            is denied."
    ::= 2

isarIoamLoopbackSuccess TRAP-TYPE
    ENTERPRISE  isarIoamTraps
    VARIABLES   { ifIndex,
                  isarIoamLoopbackVpi, 
                  isarIoamLoopbackVci 
                 }
    DESCRIPTION
           "isarIoamLoopbackStatus = success."
    ::= 3

isarIoamLoopbackFailed TRAP-TYPE
    ENTERPRISE  isarIoamTraps
    VARIABLES   { ifIndex,
                  isarIoamLoopbackVpi, 
                  isarIoamLoopbackVci 
                 }
    DESCRIPTION
           "isarIoamLoopbackStatus = failed."
    ::= 4



--
-- ISAR oamMIBObjects : end
--  




-- This file cannot be used to create SNMP agent.
-- The file isarOneFile.my has to be used to create the agent.


--
-- RFC 1643 : begin
--  

-- This MIB module uses the extended OBJECT-TYPE macro as
-- defined in RFC-1212.

dot3    OBJECT IDENTIFIER ::= { transmission 7 }

-- the Ethernet-like Statistics group

dot3StatsTable  OBJECT-TYPE
    SYNTAX     SEQUENCE OF Dot3StatsEntry
    ACCESS     not-accessible
    STATUS     mandatory
    DESCRIPTION
           "Statistics for a collection of ethernet-like
            interfaces attached to a particular system."
    ::= { dot3 2 }


dot3StatsEntry   OBJECT-TYPE
    SYNTAX      Dot3StatsEntry
    ACCESS      not-accessible
    STATUS      mandatory
    DESCRIPTION
           "Statistics for a particular interface to an
            ethernet-like medium."
    INDEX     { dot3StatsIndex }
    ::= { dot3StatsTable 1 }


Dot3StatsEntry ::= 
    SEQUENCE {
      dot3StatsIndex
        INTEGER,

      dot3StatsAlignmentErrors
        Counter,

      dot3StatsFCSErrors
        Counter,

      dot3StatsSingleCollisionFrames
        Counter,

      dot3StatsMultipleCollisionFrames
        Counter,

      dot3StatsSQETestErrors
        Counter,

      dot3StatsDeferredTransmissions
        Counter,

      dot3StatsLateCollisions
        Counter,

      dot3StatsExcessiveCollisions
        Counter,

      dot3StatsInternalMacTransmitErrors
        Counter,

      dot3StatsCarrierSenseErrors
        Counter,

      dot3StatsFrameTooLongs
        Counter,

      dot3StatsInternalMacReceiveErrors
        Counter,

      dot3StatsEtherChipSet
        OBJECT IDENTIFIER

    }

dot3StatsIndex   OBJECT-TYPE
    SYNTAX      INTEGER
    ACCESS      read-only
    STATUS      mandatory
    DESCRIPTION
           "An index value that uniquely identifies an
            interface to an ethernet-like medium.  The
            interface identified by a particular value of
            this index is the same interface as identified
            by the same value of ifIndex."
    ::= { dot3StatsEntry 1 }

dot3StatsAlignmentErrors   OBJECT-TYPE
    SYNTAX     Counter
    ACCESS     read-only
    STATUS     mandatory
    DESCRIPTION
           "A count of frames received on a particular
            interface that are not an integral number of
            octets in length and do not pass the FCS check.
            The count represented by an instance of this
            object is incremented when the alignmentError
            status is returned by the MAC service to the
            LLC (or other MAC user). Received frames for
            which multiple error conditions obtain are,
            according to the conventions of IEEE 802.3
            Layer Management, counted exclusively according
            to the error status presented to the LLC."
    REFERENCE
           "IEEE 802.3 Layer Management"
    ::= { dot3StatsEntry 2 }

dot3StatsFCSErrors   OBJECT-TYPE
    SYNTAX      Counter
    ACCESS      read-only
    STATUS      mandatory
    DESCRIPTION
           "A count of frames received on a particular
           interface that are an integral number of octets
           in length but do not pass the FCS check.

           The count represented by an instance of this
           object is incremented when the frameCheckError
           status is returned by the MAC service to the
           LLC (or other MAC user). Received frames for
           which multiple error conditions obtain are,
           according to the conventions of IEEE 802.3
           Layer Management, counted exclusively according
           to the error status presented to the LLC."
   REFERENCE
          "IEEE 802.3 Layer Management"
   ::= { dot3StatsEntry 3 }

dot3StatsSingleCollisionFrames   OBJECT-TYPE
    SYNTAX      Counter
    ACCESS      read-only
    STATUS      mandatory
    DESCRIPTION
           "A count of successfully transmitted frames on
            a particular interface for which transmission
            is inhibited by exactly one collision.

            A frame that is counted by an instance of this
            object is also counted by the corresponding
            instance of either the ifOutUcastPkts,
            ifOutMulticastPkts, or ifOutBroadcastPkts,
            and is not counted by the corresponding
            instance of the dot3StatsMultipleCollisionFrames
            object."
   REFERENCE
          "IEEE 802.3 Layer Management"
   ::= { dot3StatsEntry 4 }

dot3StatsMultipleCollisionFrames   OBJECT-TYPE
    SYNTAX      Counter
    ACCESS      read-only
    STATUS      mandatory
    DESCRIPTION
           "A count of successfully transmitted frames on
            a particular interface for which transmission
            is inhibited by more than one collision.

            A frame that is counted by an instance of this
            object is also counted by the corresponding
            instance of either the ifOutUcastPkts,
            ifOutMulticastPkts, or ifOutBroadcastPkts,
            and is not counted by the corresponding
            instance of the dot3StatsSingleCollisionFrames
            object."
    REFERENCE
           "IEEE 802.3 Layer Management"
            ::= { dot3StatsEntry 5 }

dot3StatsSQETestErrors   OBJECT-TYPE
    SYNTAX     Counter
    ACCESS     read-only
    STATUS     mandatory
    DESCRIPTION
           "A count of times that the SQE TEST ERROR
            message is generated by the PLS sublayer for a
            particular interface. The SQE TEST ERROR
            message is defined in section 7.2.2.2.4 of
            ANSI/IEEE 802.3-1985 and its generation is
            described in section 7.2.4.6 of the same
            document."
    REFERENCE
           "ANSI/IEEE Std 802.3-1985 Carrier Sense
            Multiple Access with Collision Detection Access
            Method and Physical Layer Specifications"
    ::= { dot3StatsEntry 6 }

dot3StatsDeferredTransmissions   OBJECT-TYPE
    SYNTAX      Counter
    ACCESS      read-only
    STATUS      mandatory
    DESCRIPTION
           "A count of frames for which the first
            transmission attempt on a particular interface
            is delayed because the medium is busy.

            The count represented by an instance of this
            object does not include frames involved in
            collisions."
    REFERENCE
           "IEEE 802.3 Layer Management"
    ::= { dot3StatsEntry 7 }


dot3StatsLateCollisions   OBJECT-TYPE
    SYNTAX      Counter
    ACCESS      read-only
    STATUS      mandatory
    DESCRIPTION
           "The number of times that a collision is
            detected on a particular interface later than
            512 bit-times into the transmission of a
            packet.

            Five hundred and twelve bit-times corresponds
            to 51.2 microseconds on a 10 Mbit/s system. A
            (late) collision included in a count
            represented by an instance of this object is
            also considered as a (generic) collision for
            purposes of other collision-related
            statistics."
    REFERENCE
           "IEEE 802.3 Layer Management"
    ::= { dot3StatsEntry 8 }

dot3StatsExcessiveCollisions   OBJECT-TYPE
    SYNTAX    Counter
    ACCESS    read-only
    STATUS    mandatory
    DESCRIPTION
           "A count of frames for which transmission on a
            particular interface fails due to excessive
            collisions."
    REFERENCE
           "IEEE 802.3 Layer Management"
    ::= { dot3StatsEntry 9 }


dot3StatsInternalMacTransmitErrors   OBJECT-TYPE
    SYNTAX    Counter
    ACCESS    read-only
    STATUS    mandatory
    DESCRIPTION
           "A count of frames for which transmission on a
            particular interface fails due to an internal
            MAC sublayer transmit error. A frame is only
            counted by an instance of this object if it is
            not counted by the corresponding instance of
            either the dot3StatsLateCollisions object, the
            dot3StatsExcessiveCollisions object, or the
            dot3StatsCarrierSenseErrors object.
            The precise meaning of the count represented by
            an instance of this object is implementation-
            specific.  In particular, an instance of this
            object may represent a count of transmission
            errors on a particular interface that are not
            otherwise counted."
    REFERENCE
           "IEEE 802.3 Layer Management"
    ::= { dot3StatsEntry 10 }

dot3StatsCarrierSenseErrors   OBJECT-TYPE
    SYNTAX    Counter
    ACCESS    read-only
    STATUS    mandatory
    DESCRIPTION
           "The number of times that the carrier sense
            condition was lost or never asserted when
            attempting to transmit a frame on a particular
            interface.

            The count represented by an instance of this
            object is incremented at most once per
            transmission attempt, even if the carrier sense
            condition fluctuates during a transmission
            attempt."
    REFERENCE
           "IEEE 802.3 Layer Management"
    ::= { dot3StatsEntry 11 }

-- { dot3StatsEntry 12 } is not assigned

dot3StatsFrameTooLongs   OBJECT-TYPE
    SYNTAX    Counter
    ACCESS    read-only
    STATUS    mandatory
    DESCRIPTION
           "A count of frames received on a particular
            interface that exceed the maximum permitted
            frame size.

            The count represented by an instance of this
            object is incremented when the frameTooLong
            status is returned by the MAC service to the
            LLC (or other MAC user). Received frames for
            which multiple error conditions obtain are,
            according to the conventions of IEEE 802.3
            Layer Management, counted exclusively according
            to the error status presented to the LLC."
    REFERENCE
           "IEEE 802.3 Layer Management"
    ::= { dot3StatsEntry 13 }

-- { dot3StatsEntry 14 } is not assigned

-- { dot3StatsEntry 15 } is not assigned

dot3StatsInternalMacReceiveErrors   OBJECT-TYPE
    SYNTAX    Counter
    ACCESS    read-only
    STATUS    mandatory
    DESCRIPTION
           "A count of frames for which reception on a
            particular interface fails due to an internal
            MAC sublayer receive error. A frame is only
            counted by an instance of this object if it is
            not counted by the corresponding instance of
            either the dot3StatsFrameTooLongs object, the
            dot3StatsAlignmentErrors object, or the
            dot3StatsFCSErrors object.

            The precise meaning of the count represented by
            an instance of this object is implementation-
            specific.  In particular, an instance of this
            object may represent a count of receive errors
            on a particular interface that are not
            otherwise counted."
    REFERENCE
           "IEEE 802.3 Layer Management"
    ::= { dot3StatsEntry 16 }

dot3StatsEtherChipSet   OBJECT-TYPE
    SYNTAX        OBJECT IDENTIFIER
    ACCESS        read-only
    STATUS        mandatory
    DESCRIPTION
           "This object contains an OBJECT IDENTIFIER
            which identifies the chipset used to
            realize the interface. Ethernet-like
            interfaces are typically built out of
            several different chips. The MIB implementor
            is presented with a decision of which chip
            to identify via this object. The implementor
            should identify the chip which is usually
            called the Medium Access Control chip.
            If no such chip is easily identifiable,
            the implementor should identify the chip
            which actually gathers the transmit
            and receive statistics and error
            indications. This would allow a
            manager station to correlate the
            statistics and the chip generating
            them, giving it the ability to take
            into account any known anomalies
            in the chip."
    ::= { dot3StatsEntry 17 }

-- the Ethernet-like Collision Statistics group

-- Implementation of this group is optional; it is appropriate
-- for all systems which have the necessary metering



-- RFC1573 does away with the interface chipset object.
-- The following OBJECT IDENTIFIER definitions are
-- retained for purposes of backwards compatibility
-- with pre-RFC1573 systems.
--  802.3 Hardware Chipsets

-- The object ifExtnsChipSet is provided in RFC1229 to
-- identify the MAC hardware used to communcate on an
-- interface.  The following hardware chipsets are
-- provided for 802.3:

dot3ChipSets          OBJECT IDENTIFIER ::= { dot3 8 }
dot3ChipSetAMD        OBJECT IDENTIFIER ::= { dot3ChipSets 1 }
dot3ChipSetAMD7990    OBJECT IDENTIFIER ::= { dot3ChipSetAMD 1 }
dot3ChipSetAMD79900   OBJECT IDENTIFIER ::= { dot3ChipSetAMD 2 }
dot3ChipSetAMD79C940  OBJECT IDENTIFIER ::= { dot3ChipSetAMD 3 }

dot3ChipSetIntel      OBJECT IDENTIFIER ::= { dot3ChipSets 2 }
dot3ChipSetIntel82586 OBJECT IDENTIFIER ::= { dot3ChipSetIntel 1 }
dot3ChipSetIntel82596 OBJECT IDENTIFIER ::= { dot3ChipSetIntel 2 }

dot3ChipSetSeeq       OBJECT IDENTIFIER ::= { dot3ChipSets 3 }
dot3ChipSetSeeq8003   OBJECT IDENTIFIER ::= { dot3ChipSetSeeq 1 }

dot3ChipSetNational      OBJECT IDENTIFIER ::= { dot3ChipSets 4 }
dot3ChipSetNational8390  OBJECT IDENTIFIER ::= { dot3ChipSetNational 1 }
dot3ChipSetNationalSonic OBJECT IDENTIFIER ::= { dot3ChipSetNational 2 }

dot3ChipSetFujitsu       OBJECT IDENTIFIER ::= { dot3ChipSets 5 }
dot3ChipSetFujitsu86950  OBJECT IDENTIFIER ::= { dot3ChipSetFujitsu 1 }

dot3ChipSetDigital       OBJECT IDENTIFIER ::= { dot3ChipSets 6 }
dot3ChipSetDigitalDC21040  OBJECT IDENTIFIER ::= { dot3ChipSetDigital 1 }

-- For those chipsets not represented above, OBJECT IDENTIFIER
-- assignment is required in other documentation, e.g., assignment
-- within that part of the registration tree delegated to
-- individual enterprises (see RFC1155).


--
-- RFC 1643 : end
--  



-- This file cannot be used to create SNMP agent.
-- The file isarOneFile.my has to be used to create the agent.


-- isarIdot1dBridgeMIBObjects  OBJECT IDENTIFIER ::= { isar  14 }


--
-- ISAR isarIdot1dBridgeMIBObjects : begin
--
-- This MIB is based on one of the MIBs described in IETF RFC 1493
-- The MIB is written for SNMPv1.
-- The textual conventions have been replaced by their base types
-- (because the 45020 does not know these textual conventions).
--

-- Replaced textual conventions

-- All representations of MAC addresses in this MIB Module
-- use, as a textual convention (i.e. this convention does
-- not affect their encoding), the data type:

-- MacAddress ::= OCTET STRING (SIZE (6))
-- is replaced by OCTET STRING (SIZE (6))
-- originally used in : dot1dBaseBridgeAddress dot1dTpFdbAddress
--                      dot1dStaticAddress

-- a 6 octet address in the "canonical" order
-- defined by IEEE 802.1a, i.e., as if it were transmitted
-- least significant bit first, even though 802.5 (in
-- contrast to other n802.x protocols) requires MAC
-- addresses to be transmitted most significant bit first.
--
-- 16-bit addresses, if needed, are represented by setting
-- their upper 4 octets to all 0's, i.e., AAFF would be
-- represented as 00000000AAFF.


-- Similarly, all representations of Bridge-Id in this MIB
-- Module use, as a textual convention (i.e. this
-- convention does not affect their encoding), the data
-- type:

-- BridgeId ::= OCTET STRING (SIZE (8))
-- is replaced by OCTET STRING (SIZE (8))
-- originally used in : dot1dStpDesignatedRoot dot1dStpPortDesignatedRoot
--                      dot1dStpPortDesignatedBridge

-- the Bridge-Identifier as used in the Spanning Tree
-- Protocol to uniquely identify a bridge.  Its first two
-- octets (in network byte order) contain a priority
-- value and its last 6 octets contain the MAC address
-- used to refer to a bridge in a unique fashion
-- (typically, the numerically smallest MAC address
-- of all ports on the bridge).
-- Several objects in this MIB module represent values of
-- timers used by the Spanning Tree Protocol.  In this
-- MIB, these timers have values in units of hundreths of
-- a second (i.e. 1/100 secs).
-- These timers, when stored in a Spanning Tree Protocol's
-- BPDU, are in units of 1/256 seconds.  Note, however,
-- that 802.1D-1990 specifies a settable granularity of
-- no more than 1 second for these timers.  To avoid
-- ambiguity, a data type is defined here as a textual
-- convention and all representation of these timers
-- in this MIB module are defined using this data type.  An
-- algorithm is also defined for converting between the
-- different units, to ensure a timer's value is not
-- distorted by multiple conversions.
-- The data type is:


-- Timeout ::= INTEGER 
-- is replaced by INTEGER
-- originally used in : dot1dStpMaxAge dot1dStpHelloTime 
--                      dot1dStpForwardDelay dot1dStpBridgeMaxAge 
--                      dot1dStpBridgeHelloTime dot1dStpBridgeForwardDelay

-- a STP timer in units of 1/100 seconds
-- To convert a Timeout value into a value in units of
-- 1/256 seconds, the following algorithm should be used:
--
--      b  = floor( (n * 256) / 100)
--
-- where:
--      floor   =  quotient [ignore remainder]
--      n is the value in 1/100 second units
--      b is the value in 1/256 second units
--
-- To convert the value from 1/256 second units back to
-- 1/100 seconds, the following algorithm should be used:
--
--      n = ceiling( (b * 100) / 256)
--
-- where:
--      ceiling =  quotient [if remainder is 0], or
--                 quotient + 1 [if remainder is non-zero]
--      n is the value in 1/100 second units
--      b is the value in 1/256 second units
--
-- Note: it is important that the arithmetic operations are
-- done in the order specified (i.e., multiply first, divide
-- second).






-- groups in the Bridge MIB

isarIdot1dBase     OBJECT IDENTIFIER ::= { isarIdot1dBridgeMIBObjects 1 }

isarIdot1dStp      OBJECT IDENTIFIER ::= { isarIdot1dBridgeMIBObjects 2 }

isarIdot1dSr       OBJECT IDENTIFIER ::= { isarIdot1dBridgeMIBObjects 3 }

-- separately documented

isarIdot1dTp       OBJECT IDENTIFIER ::= { isarIdot1dBridgeMIBObjects 4 }

isarIdot1dStatic   OBJECT IDENTIFIER ::= { isarIdot1dBridgeMIBObjects 5 }


-- the isarIdot1dBase group

-- Implementation of the isarIdot1dBase group is mandatory for all
-- bridges.


-- isarIdot1dBaseTable

isarIdot1dBaseTable OBJECT-TYPE
    SYNTAX  SEQUENCE OF IsarIdot1dBaseEntry
    ACCESS  not-accessible
    STATUS  mandatory
    DESCRIPTION
           "A table that contains generic information about
            every bridge.  A bridge is identified by a service index."
    ::= { isarIdot1dBase 1 }

isarIdot1dBaseEntry OBJECT-TYPE
    SYNTAX  IsarIdot1dBaseEntry
    ACCESS  not-accessible
    STATUS  mandatory
    DESCRIPTION
           "A list of information for each bridge."
    INDEX  { isarIdot1dBaseServiceIndex }
    ::= { isarIdot1dBaseTable 1 }


IsarIdot1dBaseEntry ::=
    SEQUENCE {
      isarIdot1dBaseServiceIndex
        INTEGER,

      isarIdot1dBaseBridgeAddress
        OCTET STRING,

      isarIdot1dBaseNumPorts
        INTEGER,

      isarIdot1dBaseNextPortNumber
        INTEGER,

      isarIdot1dBaseType
        INTEGER

    }

isarIdot1dBaseServiceIndex OBJECT-TYPE
    SYNTAX  INTEGER
    ACCESS  read-only
    STATUS  mandatory
    DESCRIPTION
           "The service to which the folowing columnars apply.
            This is the same index as serviceIndex of isarIserviceTable."
    ::= { isarIdot1dBaseEntry 1 }

isarIdot1dBaseBridgeAddress OBJECT-TYPE
    SYNTAX  OCTET STRING (SIZE (6))
    ACCESS  read-only
    STATUS  mandatory
    DESCRIPTION
           "The MAC address used by this bridge when it must
            be referred to in a unique fashion.   It is
            recommended that this be the numerically smallest
            MAC address of all ports that belong to this
            bridge.  However it is only required to be unique.
            When concatenated with isarIdot1dStpPriority a unique
            BridgeIdentifier is formed which is used in the
            Spanning Tree Protocol."
    REFERENCE
           "IEEE 802.1D-1990: Sections 6.4.1.1.3 and 3.12.5"
    ::= { isarIdot1dBaseEntry 2 }

isarIdot1dBaseNumPorts OBJECT-TYPE
    SYNTAX  INTEGER
    ACCESS  read-only
    STATUS  mandatory
    DESCRIPTION
           "The number of ports controlled by this bridging
            entity."
    REFERENCE
           "IEEE 802.1D-1990: Section 6.4.1.1.3"
    ::= { isarIdot1dBaseEntry 3 }

isarIdot1dBaseNextPortNumber OBJECT-TYPE
    SYNTAX  INTEGER (1..64)
    ACCESS  read-only
    STATUS  mandatory
    DESCRIPTION
           "The next available port number that has to be used
            when a new logical port is created on this bridge.
            It is not automatically equal to isarIdot1dBaseNumPorts+1.
            This number is determined by the SNMP agent by way of a 
            get-function."
    ::= { isarIdot1dBaseEntry 4 }

isarIdot1dBaseType OBJECT-TYPE
    SYNTAX  INTEGER {
                      unknown(1),
                      transparent-only(2),
                      sourceroute-only(3),
                      srt(4)
            }
    ACCESS  read-only
    STATUS  mandatory
    DESCRIPTION
           "Indicates what type of bridging this bridge can
            perform.  If a bridge is actually performing a
            certain type of bridging this will be indicated by
            entries in the port table for the given type."
    ::= { isarIdot1dBaseEntry 5 }


-- The Bridge Port Table

isarIdot1dBasePortTable OBJECT-TYPE
    SYNTAX  SEQUENCE OF IsarIdot1dBasePortEntry
    ACCESS  not-accessible
    STATUS  mandatory
    DESCRIPTION
           "A table that contains generic information about
            every port that is associated with this bridge (identified
            by the serviceIndex).
            Transparent, source-route, and srt ports are
            included.
            Entries added here (or deleted) should automatically be
            added to (or deleted from) the table isarIdot1dTpPortTable.

            Entries are created by IAD4700."
    ::= { isarIdot1dBase 4 }

isarIdot1dBasePortEntry OBJECT-TYPE
    SYNTAX  IsarIdot1dBasePortEntry
    ACCESS  not-accessible
    STATUS  mandatory
    DESCRIPTION
           "A list of information for each port of the
            bridge."
    REFERENCE
           "IEEE 802.1D-1990: Section 6.4.2, 6.6.1"
    INDEX  { isarIdot1dBasePortServiceIndex, isarIdot1dBasePort }
    ::= { isarIdot1dBasePortTable 1 }


IsarIdot1dBasePortEntry ::=
    SEQUENCE {
      isarIdot1dBasePort
        INTEGER,

      isarIdot1dBasePortDelayExceededDiscards
        Counter,

      isarIdot1dBasePortMtuExceededDiscards
        Counter,
 
      isarIdot1dBasePortServiceIndex
        INTEGER
    }


isarIdot1dBasePort OBJECT-TYPE
    SYNTAX  INTEGER (1..64)
    ACCESS  read-only
    STATUS  mandatory
    DESCRIPTION
           "The port number of the port for which this entry
            contains bridge management information.  It is equal to
            isarIdot1dBaseNextPortNumber of isarIdot1dBaseEntry."
    ::= { isarIdot1dBasePortEntry 1 }

isarIdot1dBasePortDelayExceededDiscards OBJECT-TYPE
    SYNTAX  Counter
    ACCESS  read-only
    STATUS  mandatory
    DESCRIPTION
           "The number of frames discarded by this port due
            to excessive transit delay through the bridge.  It
            is incremented by both transparent and source
            route bridges."
    REFERENCE
           "IEEE 802.1D-1990: Section 6.6.1.1.3"
    ::= { isarIdot1dBasePortEntry 2 }

isarIdot1dBasePortMtuExceededDiscards OBJECT-TYPE
    SYNTAX  Counter
    ACCESS  read-only
    STATUS  mandatory
    DESCRIPTION
           "The number of frames discarded by this port due
            to an excessive size.  It is incremented by both
            transparent and source route bridges."
    REFERENCE
           "IEEE 802.1D-1990: Section 6.6.1.1.3"
    ::= { isarIdot1dBasePortEntry 3 }

isarIdot1dBasePortServiceIndex OBJECT-TYPE
    SYNTAX  INTEGER
    ACCESS  read-only
    STATUS  mandatory
    DESCRIPTION
           "The service index to which this port belongs.
            This is the same index as serviceIndex of isarIserviceTable."
    ::= { isarIdot1dBasePortEntry 4 }



-- the isarIdot1dStp group

-- Implementation of the dot1dStp group is optional.  It is
-- implemented by those bridges that support the Spanning Tree
-- Protocol.

-- no changes for IAD4700

isarIdot1dStpProtocolSpecification OBJECT-TYPE
    SYNTAX  INTEGER {
                      unknown(1),
                      decLb100(2),
                      ieee8021d(3)
            }
    ACCESS  read-only
    STATUS  mandatory
    DESCRIPTION
           "An indication of what version of the Spanning
            Tree Protocol is being run.  The value
            'decLb100(2)' indicates the DEC LANbridge 100
            Spanning Tree protocol.  IEEE 802.1d
            implementations will return 'ieee8021d(3)'.  If
            future versions of the IEEE Spanning Tree Protocol
            are released that are incompatible with the
            current version a new value will be defined."
    ::= { isarIdot1dStp 1 }

isarIdot1dStpPriority OBJECT-TYPE
    SYNTAX  INTEGER (0..65535)
    ACCESS  read-write
    STATUS  mandatory
    DESCRIPTION
           "The value of the write-able portion of the Bridge
            ID, i.e., the first two octets of the (8 octet
            long) Bridge ID.  The other (last) 6 octets of the
            Bridge ID are given by the value of
            dot1dBaseBridgeAddress."
    REFERENCE
           "IEEE 802.1D-1990: Section 4.5.3.7"
    ::= { isarIdot1dStp 2 }

isarIdot1dStpTimeSinceTopologyChange OBJECT-TYPE
    SYNTAX  TimeTicks
    ACCESS  read-only
    STATUS  mandatory
    DESCRIPTION
           "The time (in hundredths of a second) since the
            last time a topology change was detected by the
            bridge entity."
    REFERENCE
           "IEEE 802.1D-1990: Section 6.8.1.1.3"
    ::= { isarIdot1dStp 3 }

isarIdot1dStpTopChanges OBJECT-TYPE
    SYNTAX  Counter
    ACCESS  read-only
    STATUS  mandatory
    DESCRIPTION
           "The total number of topology changes detected by
            this bridge since the management entity was last
            reset or initialized."
    REFERENCE
           "IEEE 802.1D-1990: Section 6.8.1.1.3"
    ::= { isarIdot1dStp 4 }

isarIdot1dStpDesignatedRoot OBJECT-TYPE
    SYNTAX  OCTET STRING (SIZE (8))
    ACCESS  read-only
    STATUS  mandatory
    DESCRIPTION
           "The bridge identifier of the root of the spanning
            tree as determined by the Spanning Tree Protocol
            as executed by this node.  This value is used as
            the Root Identifier parameter in all Configuration
            Bridge PDUs originated by this node."
    REFERENCE
           "IEEE 802.1D-1990: Section 4.5.3.1"
    ::= { isarIdot1dStp 5 }

isarIdot1dStpRootCost OBJECT-TYPE
    SYNTAX  INTEGER
    ACCESS  read-only
    STATUS  mandatory
    DESCRIPTION
           "The cost of the path to the root as seen from
            this bridge."
    REFERENCE
           "IEEE 802.1D-1990: Section 4.5.3.2"
    ::= { isarIdot1dStp 6 }

isarIdot1dStpRootPort OBJECT-TYPE
    SYNTAX  INTEGER
    ACCESS  read-only
    STATUS  mandatory
    DESCRIPTION
           "The port number of the port which offers the
            lowest cost path from this bridge to the root
            bridge."
    REFERENCE
           "IEEE 802.1D-1990: Section 4.5.3.3"
    ::= { isarIdot1dStp 7 }

isarIdot1dStpMaxAge OBJECT-TYPE
    SYNTAX  INTEGER
    ACCESS  read-only
    STATUS  mandatory
    DESCRIPTION
           "The maximum age of Spanning Tree Protocol
            information learned from the network on any port
            before it is discarded, in units of hundredths of
            a second.  This is the actual value that this
            bridge is currently using."
    REFERENCE
           "IEEE 802.1D-1990: Section 4.5.3.4"
    ::= { isarIdot1dStp 8 }

isarIdot1dStpHelloTime OBJECT-TYPE
    SYNTAX  INTEGER
    ACCESS  read-only
    STATUS  mandatory
    DESCRIPTION
           "The amount of time between the transmission of
            Configuration bridge PDUs by this node on any port
            when it is the root of the spanning tree or trying
            to become so, in units of hundredths of a second.
            This is the actual value that this bridge is
            currently using."
    REFERENCE
           "IEEE 802.1D-1990: Section 4.5.3.5"
    ::= { isarIdot1dStp 9 }

isarIdot1dStpHoldTime OBJECT-TYPE
    SYNTAX  INTEGER
    ACCESS  read-only
    STATUS  mandatory
    DESCRIPTION
           "This time value determines the interval length
            during which no more than two Configuration bridge
            PDUs shall be transmitted by this node, in units
            of hundredths of a second."
    REFERENCE
           "IEEE 802.1D-1990: Section 4.5.3.14"
    ::= { isarIdot1dStp 10 }

isarIdot1dStpForwardDelay OBJECT-TYPE
    SYNTAX  INTEGER
    ACCESS  read-only
    STATUS  mandatory
    DESCRIPTION
           "This time value, measured in units of hundredths
            of a second, controls how fast a port changes its
            spanning state when moving towards the Forwarding
            state.  The value determines how long the port
            stays in each of the Listening and Learning
            states, which precede the Forwarding state.  This
            value is also used, when a topology change has
            been detected and is underway, to age all dynamic
            entries in the Forwarding Database.  [Note that
            this value is the one that this bridge is
            currently using, in contrast to
            dot1dStpBridgeForwardDelay which is the value that
            this bridge and all others would start using
            if/when this bridge were to become the root.]"
    REFERENCE
           "IEEE 802.1D-1990: Section 4.5.3.6"
    ::= { isarIdot1dStp 11 }

isarIdot1dStpBridgeMaxAge OBJECT-TYPE
    SYNTAX  INTEGER (600..4000)
    ACCESS  read-write
    STATUS  mandatory
    DESCRIPTION
           "The value that all bridges use for MaxAge when
            this bridge is acting as the root.  Note that
            802.1D-1990 specifies that the range for this
            parameter is related to the value of
            dot1dStpBridgeHelloTime. The granularity of this
            timer is specified by 802.1D-1990 to be 1 second.
            An agent may return a badValue error if a set is
            attempted to a value which is not a whole number
            of seconds."
    REFERENCE
           "IEEE 802.1D-1990: Section 4.5.3.8"
    ::= { isarIdot1dStp 12 }

isarIdot1dStpBridgeHelloTime OBJECT-TYPE
    SYNTAX  INTEGER (100..1000)
    ACCESS  read-write
    STATUS  mandatory
    DESCRIPTION
           "The value that all bridges use for HelloTime when
            this bridge is acting as the root.  The
            granularity of this timer is specified by 802.1D-
            1990 to be 1 second.  An agent may return a
            badValue error if a set is attempted to a value
            which is not a whole number of seconds."
    REFERENCE
           "IEEE 802.1D-1990: Section 4.5.3.9"
    ::= { isarIdot1dStp 13 }

isarIdot1dStpBridgeForwardDelay OBJECT-TYPE
    SYNTAX  INTEGER (400..3000)
    ACCESS  read-write
    STATUS  mandatory
    DESCRIPTION
           "The value that all bridges use for ForwardDelay
            when this bridge is acting as the root.  Note that
            802.1D-1990 specifies that the range for this
            parameter is related to the value of
            dot1dStpBridgeMaxAge.  The granularity of this
            timer is specified by 802.1D-1990 to be 1 second.
            An agent may return a badValue error if a set is
            attempted to a value which is not a whole number
            of seconds."
    REFERENCE
           "IEEE 802.1D-1990: Section 4.5.3.10"
    ::= { isarIdot1dStp 14 }



-- The Spanning Tree Port Table

isarIdot1dStpPortTable OBJECT-TYPE
    SYNTAX  SEQUENCE OF IsarIdot1dStpPortEntry
    ACCESS  not-accessible
    STATUS  mandatory
    DESCRIPTION
           "A table that contains port-specific information
            for the Spanning Tree Protocol."
    ::= { isarIdot1dStp 15 }

isarIdot1dStpPortEntry OBJECT-TYPE
    SYNTAX  IsarIdot1dStpPortEntry
    ACCESS  not-accessible
    STATUS  mandatory
    DESCRIPTION
           "A list of information maintained by every port
            about the Spanning Tree Protocol state for that
            port."
    INDEX   { isarIdot1dStpPort }
    ::= { isarIdot1dStpPortTable 1 }

IsarIdot1dStpPortEntry ::=
    SEQUENCE {
       isarIdot1dStpPort
         INTEGER,

       isarIdot1dStpPortPriority
         INTEGER,

       isarIdot1dStpPortState
         INTEGER,

       isarIdot1dStpPortEnable
         INTEGER,

       isarIdot1dStpPortPathCost
         INTEGER,

       isarIdot1dStpPortDesignatedRoot
         OCTET STRING,

       isarIdot1dStpPortDesignatedCost
         INTEGER,

       isarIdot1dStpPortDesignatedBridge
         OCTET STRING,

       isarIdot1dStpPortDesignatedPort
         OCTET STRING,

       isarIdot1dStpPortForwardTransitions
         Counter

    }

isarIdot1dStpPort OBJECT-TYPE
    SYNTAX  INTEGER (1..65535)
    ACCESS  read-only
    STATUS  mandatory
    DESCRIPTION
           "The port number of the port for which this entry
            contains Spanning Tree Protocol management
            information."
    REFERENCE
           "IEEE 802.1D-1990: Section 6.8.2.1.2"
    ::= { isarIdot1dStpPortEntry 1 }

isarIdot1dStpPortPriority OBJECT-TYPE
    SYNTAX  INTEGER (0..255)
    ACCESS  read-write
    STATUS  mandatory
    DESCRIPTION
           "The value of the priority field which is
            contained in the first (in network byte order)
            octet of the (2 octet long) Port ID.  The other
            octet of the Port ID is given by the value of
            dot1dStpPort."
    REFERENCE
           "IEEE 802.1D-1990: Section 4.5.5.1"
    ::= { isarIdot1dStpPortEntry 2 }

isarIdot1dStpPortState OBJECT-TYPE
    SYNTAX  INTEGER {
                      disabled(1),
                      blocking(2),
                      listening(3),
                      learning(4),
                      forwarding(5),
                      broken(6)
            }
    ACCESS  read-only
    STATUS  mandatory
    DESCRIPTION
           "The port's current state as defined by
            application of the Spanning Tree Protocol.  This
            state controls what action a port takes on
            reception of a frame.  If the bridge has detected
            a port that is malfunctioning it will place that
            port into the broken(6) state.  For ports which
            are disabled (see dot1dStpPortEnable), this object
            will have a value of disabled(1)."
    REFERENCE
           "IEEE 802.1D-1990: Section 4.5.5.2"
    ::= { isarIdot1dStpPortEntry 3 }


isarIdot1dStpPortEnable OBJECT-TYPE
    SYNTAX  INTEGER {
                      enabled(1),
                      disabled(2)
            }
    ACCESS  read-write
    STATUS  mandatory
    DESCRIPTION
           "The enabled/disabled status of the port."
    REFERENCE
           "IEEE 802.1D-1990: Section 4.5.5.2"
    ::= { isarIdot1dStpPortEntry 4 }

isarIdot1dStpPortPathCost OBJECT-TYPE
    SYNTAX  INTEGER (1..65535)
    ACCESS  read-write
    STATUS  mandatory
    DESCRIPTION
           "The contribution of this port to the path cost of
            paths towards the spanning tree root which include
            this port.  802.1D-1990 recommends that the
            default value of this parameter be in inverse
            proportion to the speed of the attached LAN."
    REFERENCE
           "IEEE 802.1D-1990: Section 4.5.5.3"
    ::= { isarIdot1dStpPortEntry 5 }

isarIdot1dStpPortDesignatedRoot OBJECT-TYPE
    SYNTAX  OCTET STRING (SIZE (8))
    ACCESS  read-only
    STATUS  mandatory
    DESCRIPTION
           "The unique Bridge Identifier of the Bridge
            recorded as the Root in the Configuration BPDUs
            transmitted by the Designated Bridge for the
            segment to which the port is attached."
    REFERENCE
           "IEEE 802.1D-1990: Section 4.5.5.4"
    ::= { isarIdot1dStpPortEntry 6 }

isarIdot1dStpPortDesignatedCost OBJECT-TYPE
    SYNTAX  INTEGER
    ACCESS  read-only
    STATUS  mandatory
    DESCRIPTION
           "The path cost of the Designated Port of the
            segment connected to this port.  This value is
            compared to the Root Path Cost field in received
            bridge PDUs."
    REFERENCE
           "IEEE 802.1D-1990: Section 4.5.5.5"
    ::= { isarIdot1dStpPortEntry 7 }

isarIdot1dStpPortDesignatedBridge OBJECT-TYPE
    SYNTAX  OCTET STRING (SIZE (8))
    ACCESS  read-only
    STATUS  mandatory
    DESCRIPTION
           "The Bridge Identifier of the bridge which this
            port considers to be the Designated Bridge for
            this port's segment."
    REFERENCE
           "IEEE 802.1D-1990: Section 4.5.5.6"
    ::= { isarIdot1dStpPortEntry 8 }

isarIdot1dStpPortDesignatedPort OBJECT-TYPE
    SYNTAX  OCTET STRING (SIZE (2))
    ACCESS  read-only
    STATUS  mandatory
    DESCRIPTION
           "The Port Identifier of the port on the Designated
            Bridge for this port's segment."
    REFERENCE
           "IEEE 802.1D-1990: Section 4.5.5.7"
    ::= { isarIdot1dStpPortEntry 9 }

isarIdot1dStpPortForwardTransitions OBJECT-TYPE
    SYNTAX  Counter
    ACCESS  read-only
    STATUS  mandatory
    DESCRIPTION
           "The number of times this port has transitioned
            from the Learning state to the Forwarding state."
    ::= { isarIdot1dStpPortEntry 10 }




-- the isarIdot1dTp group

-- Implementation of the isarIdot1dTp group is optional.  It is
-- implemented by those bridges that support the transparent
-- bridging mode.  A transparent or SRT bridge will implement
-- this group.



-- ISAR specific

-- isarIdot1dTpTable

isarIdot1dTpTable OBJECT-TYPE
    SYNTAX  SEQUENCE OF IsarIdot1dTpEntry
    ACCESS  not-accessible
    STATUS  mandatory
    DESCRIPTION
           "A table that contains generic information per bridge."
    ::= { isarIdot1dTp 1 }

isarIdot1dTpEntry OBJECT-TYPE
    SYNTAX  IsarIdot1dTpEntry
    ACCESS  not-accessible
    STATUS  mandatory
    DESCRIPTION
           "A list of information for each bridge."
    INDEX  { isarIdot1dTpServiceIndex }
    ::= { isarIdot1dTpTable 1 }


IsarIdot1dTpEntry ::=
    SEQUENCE {
      isarIdot1dTpServiceIndex
        INTEGER,

      isarIdot1dTpLearnedEntryDiscards
        Counter,

      isarIdot1dTpAgingTime
        INTEGER,

      isarIdot1dTpFunctionType
        INTEGER

    }

isarIdot1dTpServiceIndex OBJECT-TYPE
    SYNTAX  INTEGER
    ACCESS  read-only
    STATUS  mandatory
    DESCRIPTION
           "The service to which this information belongs.
            This is the same index as serviceIndex of isarIserviceTable."
    ::= { isarIdot1dTpEntry 1 }

isarIdot1dTpLearnedEntryDiscards OBJECT-TYPE
    SYNTAX  Counter
    ACCESS  read-only
    STATUS  mandatory
    DESCRIPTION
           "The total number of Forwarding Database entries,
            which have been or would have been learnt, but
            have been discarded due to a lack of space to
            store them in the Forwarding Database.  If this
            counter is increasing, it indicates that the
            Forwarding Database is regularly becoming full (a
            condition which has unpleasant performance effects
            on the subnetwork).  If this counter has a
            significant value but is not presently increasing,
            it indicates that the problem has been occurring
            but is not persistent."
    REFERENCE
           "IEEE 802.1D-1990: Section 6.7.1.1.3"
    ::= { isarIdot1dTpEntry 2 }

isarIdot1dTpAgingTime OBJECT-TYPE
    SYNTAX   INTEGER (10..1000000)
    ACCESS   read-write
    STATUS   mandatory
    DESCRIPTION
           "The timeout period in seconds for aging out
            dynamically learned forwarding information.
            802.1D-1990 recommends a default of 300 seconds."
    REFERENCE
           "IEEE 802.1D-1990: Section 6.7.1.1.3"
    DEFVAL { 300 }
    ::= { isarIdot1dTpEntry 3 }

isarIdot1dTpFunctionType OBJECT-TYPE
    SYNTAX   INTEGER {
                       ipRelay(1),
                       lanInterworking(2)
             }
    ACCESS   read-write
    STATUS   mandatory
    DESCRIPTION
           "The value indicates for which purpose the LANIS is going
            to be used.
            Modification of this value is only allowed when no 
            connections are created for this service."
    DEFVAL { lanInterworking }
    ::= { isarIdot1dTpEntry 4 }



--  The Forwarding Database for Transparent Bridges

isarIdot1dTpFdbTable OBJECT-TYPE
    SYNTAX  SEQUENCE OF IsarIdot1dTpFdbEntry
    ACCESS  not-accessible
    STATUS  mandatory
    DESCRIPTION
           "A table that contains information about unicast
            entries for which the bridge has forwarding and/or
            filtering information.  This information is used
            by the transparent bridging function in
            determining how to propagate a received frame."
    ::= { isarIdot1dTp 3 }

isarIdot1dTpFdbEntry OBJECT-TYPE
    SYNTAX  IsarIdot1dTpFdbEntry
    ACCESS  not-accessible
    STATUS  mandatory
    DESCRIPTION
           "Information about a specific unicast MAC address
            for which the bridge has some forwarding and/or
            filtering information."
    INDEX   { isarIdot1dTpFdbServiceIndex, isarIdot1dTpFdbAddress }
    ::= { isarIdot1dTpFdbTable 1 }

IsarIdot1dTpFdbEntry ::=
    SEQUENCE {
      isarIdot1dTpFdbAddress
        OCTET STRING,

      isarIdot1dTpFdbPort
        INTEGER,

      isarIdot1dTpFdbServiceIndex
        INTEGER
    }

isarIdot1dTpFdbAddress OBJECT-TYPE
    SYNTAX  OCTET STRING (SIZE (6))
    ACCESS  read-only
    STATUS  mandatory
    DESCRIPTION
           "A unicast MAC address for which the bridge has
            forwarding and/or filtering information."
    REFERENCE
           "IEEE 802.1D-1990: Section 3.9.1, 3.9.2"
    ::= { isarIdot1dTpFdbEntry 1 }

isarIdot1dTpFdbPort OBJECT-TYPE
    SYNTAX  INTEGER
    ACCESS  read-only
    STATUS  mandatory
    DESCRIPTION
           "Either the value '0', or the port number of the
            port on which a frame having a source address
            equal to the value of the corresponding instance
            of dot1dTpFdbAddress has been seen.  A value of
            '0' indicates that the port number has not been
            learned but that the bridge does have some
            forwarding/filtering information about this
            address (e.g. in the dot1dStaticTable).
            Implementors are encouraged to assign the port
            value to this object whenever it is learned even
            for addresses for which the corresponding value of
            dot1dTpFdbStatus is not learned(3)."
    ::= { isarIdot1dTpFdbEntry 2 }


-- isarIdot1dTpFdbStatus OBJECT-TYPE ::= { isarIdot1dTpFdbEntry 3 }
-- not needed for IAD4700

isarIdot1dTpFdbServiceIndex OBJECT-TYPE
    SYNTAX  INTEGER
    ACCESS  read-only
    STATUS  mandatory
    DESCRIPTION
           "The service to which this information belongs.
            This is the same index as serviceIndex of isarIserviceTable."
    ::= { isarIdot1dTpFdbEntry 4 }


--  Port Table for Transparent Bridges

isarIdot1dTpPortTable OBJECT-TYPE
    SYNTAX  SEQUENCE OF IsarIdot1dTpPortEntry
    ACCESS  not-accessible
    STATUS  mandatory
    DESCRIPTION
           "A table that contains information about every
            port that is associated with this transparent
            bridge.
            One entry in this table corresponds with one entry in the
            isarIdot1dBasePortTable."
    ::= { isarIdot1dTp 4 }

isarIdot1dTpPortEntry OBJECT-TYPE
    SYNTAX  IsarIdot1dTpPortEntry
    ACCESS  not-accessible
    STATUS  mandatory
    DESCRIPTION
           "A list of information for each port of a
            transparent bridge."
    INDEX   { isarIdot1dTpPortServiceIndex, isarIdot1dTpPort }
    ::= { isarIdot1dTpPortTable 1 }

IsarIdot1dTpPortEntry ::=
    SEQUENCE {
      isarIdot1dTpPort
        INTEGER,

      isarIdot1dTpPortInFrames
        Counter,

      isarIdot1dTpPortOutFrames
        Counter,

      isarIdot1dTpPortInDiscards
        Counter,

      isarIdot1dTpPortServiceIndex
        INTEGER,

      isarIdot1dTpPortOutDiscards
        Counter

    }

isarIdot1dTpPort OBJECT-TYPE
    SYNTAX  INTEGER (1..64)
    ACCESS  read-only
    STATUS  mandatory
    DESCRIPTION
           "The port number of the port for which this entry
            contains Transparent bridging management
            information."
    ::= { isarIdot1dTpPortEntry 1 }


isarIdot1dTpPortInFrames OBJECT-TYPE
    SYNTAX  Counter
    ACCESS  read-only
    STATUS  mandatory
    DESCRIPTION
           "The number of frames that have been received by
            this port from its segment. Note that a frame
            received on the interface corresponding to this
            port is only counted by this object if and only if
            it is for a protocol being processed by the local
            bridging function, including bridge management
            frames."
    REFERENCE
           "IEEE 802.1D-1990: Section 6.6.1.1.3"
    ::= { isarIdot1dTpPortEntry 3 }

isarIdot1dTpPortOutFrames OBJECT-TYPE
    SYNTAX  Counter
    ACCESS  read-only
    STATUS  mandatory
    DESCRIPTION
           "The number of frames that have been transmitted
            by this port to its segment.  Note that a frame
            transmitted on the interface corresponding to this
            port is only counted by this object if and only if
            it is for a protocol being processed by the local
            bridging function, including bridge management
            frames."
    REFERENCE
           "IEEE 802.1D-1990: Section 6.6.1.1.3"
    ::= { isarIdot1dTpPortEntry 4 }

isarIdot1dTpPortInDiscards OBJECT-TYPE
    SYNTAX   Counter
    ACCESS   read-only
    STATUS   mandatory
    DESCRIPTION
           "Count of all received frames which were
            discarded by the LANIS."
    REFERENCE
           "IEEE 802.1D-1990: Section 6.6.1.1.3"
    ::= { isarIdot1dTpPortEntry 5 }

isarIdot1dTpPortServiceIndex OBJECT-TYPE
    SYNTAX  INTEGER
    ACCESS  read-only
    STATUS  mandatory
    DESCRIPTION
           "The service to which this information belongs.
            This is the same index as serviceIndex of isarIserviceTable."
    ::= { isarIdot1dTpPortEntry 6 }

isarIdot1dTpPortOutDiscards OBJECT-TYPE
    SYNTAX   Counter
    ACCESS   read-only
    STATUS   mandatory
    DESCRIPTION
           "Count of all valid outbound frames which were
            discarded by the LANIS."
    REFERENCE
           "IEEE 802.1D-1990: Section 6.6.1.1.3"
    ::= { isarIdot1dTpPortEntry 7 }




-- The Static (Destination-Address Filtering) Database

-- Implementation of this group is optional.

-- ISAR specific


isarIdot1dStaticTable OBJECT-TYPE
    SYNTAX  SEQUENCE OF IsarIdot1dStaticEntry
    ACCESS  not-accessible
    STATUS  mandatory
    DESCRIPTION
           "A table containing filtering information
            configured into the bridge by (local or network)
            management specifying the set of ports to which
            frames received from specific ports and containing
            specific destination addresses are allowed to be
            forwarded.  The value of zero in this table as the
            port number from which frames with a specific
            destination address are received, is used to
            specify all ports for which there is no specific
            entry in this table for that particular
            destination address.  Entries are valid for
            unicast and for group/broadcast addresses."
    REFERENCE
           "IEEE 802.1D-1990: Section 6.7.2"
    ::= { isarIdot1dStatic 1 }

isarIdot1dStaticEntry OBJECT-TYPE
    SYNTAX  IsarIdot1dStaticEntry
    ACCESS  not-accessible
    STATUS  mandatory
    DESCRIPTION
           "Filtering information configured into the bridge
            by (local or network) management specifying the
            set of ports to which frames received from a
            specific port and containing a specific
            destination address are allowed to be forwarded."
    REFERENCE
           "IEEE 802.1D-1990: Section 6.7.2"
    INDEX   { isarIdot1dStaticServiceIndex,
              isarIdot1dStaticAddress,
              isarIdot1dStaticReceivePort }
    ::= { isarIdot1dStaticTable 1 }

IsarIdot1dStaticEntry ::=
    SEQUENCE {
      isarIdot1dStaticAddress
        OCTET STRING,

      isarIdot1dStaticReceivePort
        INTEGER,

      isarIdot1dStaticAllowedToGoTo
        OCTET STRING,

      isarIdot1dStaticServiceIndex
        INTEGER,

      isarIdot1dStaticRowStatus
        INTEGER
    }

isarIdot1dStaticAddress OBJECT-TYPE
    SYNTAX  OCTET STRING (SIZE (6))
    ACCESS  read-only
    STATUS  mandatory
    DESCRIPTION
           "The destination MAC address in a frame to which
            this entry's filtering information applies.  This
            object can take the value of a unicast address, a
            group address or the broadcast address."
    REFERENCE
           "IEEE 802.1D-1990: Section 3.9.1, 3.9.2"
    ::= { isarIdot1dStaticEntry 1 }

isarIdot1dStaticReceivePort OBJECT-TYPE
    SYNTAX  INTEGER
    ACCESS  read-only
    STATUS  mandatory
    DESCRIPTION
           "Either the value '0', or the port number of the
            port from which a frame must be received in order
            for this entry's filtering information to apply.
            A value of zero indicates that this entry applies
            on all ports of the bridge for which there is no
            other applicable entry."
    ::= { isarIdot1dStaticEntry 2 }

isarIdot1dStaticAllowedToGoTo OBJECT-TYPE
    SYNTAX  OCTET STRING (SIZE (8))
    ACCESS  read-write
    STATUS  mandatory
    DESCRIPTION
           "The set of ports to which frames received from a
            specific port and destined for a specific MAC
            address, are allowed to be forwarded.  Each octet
            within the value of this object specifies a set of
            eight ports, with the first octet specifying ports
            1 through 8, the second octet specifying ports 9
            through 16, etc.  Within each octet, the most
            significant bit represents the lowest numbered
            port, and the least significant bit represents the
            highest numbered port.  Thus, each port of the
            bridge is represented by a single bit within the
            value of this object.  If that bit has a value of
            '1' then that port is included in the set of
            ports; the port is not included if its bit has a
            value of '0'.  (Note that the setting of the bit
            corresponding to the port from which a frame is
            received is irrelevant.)  The default value of
            this object is a string of ones of appropriate
            length."
    ::= { isarIdot1dStaticEntry 3 }

isarIdot1dStaticServiceIndex OBJECT-TYPE
    SYNTAX  INTEGER
    ACCESS  read-only
    STATUS  mandatory
    DESCRIPTION
           "The service index to which this port belongs.
            This is the same index as serviceIndex of isarIserviceTable."
    ::= { isarIdot1dStaticEntry 4 }

isarIdot1dStaticRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIdot1dStaticEntry  5 }



-- Traps for use by Bridges

-- Traps for the Spanning Tree Protocol

isarInewRoot TRAP-TYPE
    ENTERPRISE  isarIdot1dBridgeMIBObjects
    DESCRIPTION
           "The newRoot trap indicates that the sending agent
            has become the new root of the Spanning Tree; the
            trap is sent by a bridge soon after its election
            as the new root, e.g., upon expiration of the
            Topology Change Timer immediately subsequent to
            its election.  Implementation of this trap is
            optional."
    ::= 1

isarItopologyChange TRAP-TYPE
    ENTERPRISE  isarIdot1dBridgeMIBObjects
    DESCRIPTION
           "A topologyChange trap is sent by a bridge when
            any of its configured ports transitions from the
            Learning state to the Forwarding state, or from
            the Forwarding state to the Blocking state.  The
            trap is not sent if a newRoot trap is sent for the
            same transition.  Implementation of this trap is
            optional."
    ::= 2



--
-- ISAR isarIdot1dBridgeMIBObjects : end
--  





-- This file cannot be used to create SNMP agent.
-- The file isarOneFile.my has to be used to create the agent.



-- isarIatmMIBObjects OBJECT IDENTIFIER ::= { isar  13 }

--
-- ISAR atmMIBObjects : begin
--  


-- This is the MIB Module for ATM and AAL5-related
-- objects for managing ATM interfaces, ATM virtual
-- links, ATM cross-connects, AAL5 entities, and
-- and AAL5 connections."


-- This ISAR ATM MIB Module consists of the following groups:
-- (1) ATM Interface configuration group
-- (2) ATM Traffic Descriptor Parameter group
-- (3) ATM Interface VCL configuration group
-- (4) ATM Interface AAL5 VCC performance statistics group

-- this enterprise MIB is based on rfc1695


-- The textual conventions have been replaced by their base types
-- (because the 45020 does not know these textual conventions).

-- Not replaced textual convention (because it generates different code
-- in EMANATE
-- IpAddress : Represents a 32-bit internet address.
--             More information : see RFC1902, rfc1155
-- used in : atmInterfaceMyNeighborIpAddress



isarIatmTrafficDescriptorTypes  OBJECT IDENTIFIER 
  ::= { isarIatmMIBObjects  1 }

-- The following values are defined for use as
-- possible values of the ATM traffic descriptor type.
-- ATM Forum specified seven types of ATM traffic
-- descriptors.

isarIatmNoTrafficDescriptor  OBJECT IDENTIFIER 
                               ::= { isarIatmTrafficDescriptorTypes  1 }
  -- This identifies the no ATM traffic descriptor
  -- type. None of the parameters are used.
  -- This traffic descriptor type can be used for
  -- best effort traffic.

-- unused traffic types
isarIatmNoClpNoScr  OBJECT IDENTIFIER
                      ::= { isarIatmTrafficDescriptorTypes  2 }

isarIatmClpNoTaggingNoScr  OBJECT IDENTIFIER
                             ::= { isarIatmTrafficDescriptorTypes  3 }

isarIatmClpTaggingNoScr  OBJECT IDENTIFIER
                           ::= { isarIatmTrafficDescriptorTypes  4 }

isarIatmNoClpScr  OBJECT IDENTIFIER
                    ::= { isarIatmTrafficDescriptorTypes  5 }

isarIatmClpNoTaggingScr  OBJECT IDENTIFIER
                           ::= { isarIatmTrafficDescriptorTypes  6 }
                      
isarIatmClpTaggingScr  OBJECT IDENTIFIER
                         ::= { isarIatmTrafficDescriptorTypes  7 }



-- ISAR specific traffic types
-- not used as object identifier but as enumeration

-- isarIatmUBR
                               
  -- This traffic descriptor is for UBR
  -- The use of the parameter vector for this type:
  -- PeakCellRate    : not used
  -- SustCellRate    : not used
  -- MaxBurstSize    : not used
  -- InitRate        : not used
  -- MinRate         : not used
  -- RateIncFactor   : not used
  -- RateDecFactor   : not used
  -- CellDelayVarTol : not used.

-- isarIatmUBRplus
                               
  -- This traffic descriptor is for UBR+
  -- The use of the parameter vector for this type:
  -- PeakCellRate    : not used
  -- SustCellRate    : not used
  -- MaxBurstSize    : not used
  -- InitRate        : not used
  -- MinRate         : to be supplied
  -- RateIncFactor   : not used
  -- RateDecFactor   : not used
  -- CellDelayVarTol : not used.

-- isarIatmCBR
                               
  -- This traffic descriptor is for CBR
  -- The use of the parameter vector for this type:
  -- PeakCellRate    : to be supplied
  -- SustCellRate    : not used
  -- MaxBurstSize    : not used
  -- InitRate        : not used
  -- MinRate         : not used
  -- RateIncFactor   : not used
  -- RateDecFactor   : not used
  -- CellDelayVarTol : to be supplied.

-- isarIatmRtVBR
                               
  -- This traffic descriptor is for real time VBR
  -- The use of the parameter vector for this type:
  -- PeakCellRate    : to be supplied
  -- SustCellRate    : to be supplied
  -- MaxBurstSize    : to be supplied
  -- InitRate        : not used
  -- MinRate         : not used
  -- RateIncFactor   : not used
  -- RateDecFactor   : not used
  -- CellDelayVarTol : to be supplied.

-- isarIatmNrtVBR
                               
  -- This traffic descriptor is for non-real time VBR
  -- The use of the parameter vector for this type:
  -- PeakCellRate    : to be supplied
  -- SustCellRate    : to be supplied
  -- MaxBurstSize    : to be supplied
  -- InitRate        : not used
  -- MinRate         : not used
  -- RateIncFactor   : not used
  -- RateDecFactor   : not used
  -- CellDelayVarTol : to be supplied.

-- isarIatmABR
                               
  -- This traffic descriptor is for ABR
  -- The use of the parameter vector for this type:
  -- PeakCellRate    : to be supplied
  -- SustCellRate    : not used
  -- MaxBurstSize    : not used
  -- InitRate        : to be supplied
  -- MinRate         : to be supplied
  -- RateIncFactor   : to be supplied
  -- RateDecFactor   : to be supplied
  -- CellDelayVarTol : not used.



  
  
--    ATM Interface Configuration Parameters Group

-- This group contains ATM specific
-- configuration information associated with
-- an ATM interface beyond those
-- supported using the ifTable.


-- isarIatmInterfaceConfTable OBJECT-TYPE    ::= { isarIatmMIBObjects  2 }
-- Not used by ISAR


-- ATM interface index table

isarIatmInterfaceTable OBJECT-TYPE
    SYNTAX  SEQUENCE OF IsarIatmInterfaceEntry
    ACCESS  not-accessible
    STATUS  mandatory
    DESCRIPTION
           "This table contains ATM local interface
            ifIndex information."
    ::= { isarIatmMIBObjects  17 }

isarIatmInterfaceEntry OBJECT-TYPE
    SYNTAX  IsarIatmInterfaceEntry
    ACCESS  not-accessible
    STATUS  mandatory
    DESCRIPTION
           "Rows are created by IAD4700."
    INDEX   { isarIphysStackNo }
    ::= { isarIatmInterfaceTable  1 }

IsarIatmInterfaceEntry ::=
    SEQUENCE {
      isarIatmInterfaceIfIndex
        INTEGER,

      isarIatmInterfaceLowerLayerIfIndex
        INTEGER
    }

isarIatmInterfaceIfIndex OBJECT-TYPE
    SYNTAX  INTEGER (1..2147483647)
    ACCESS  read-only
    STATUS  mandatory
    DESCRIPTION
           "IfIndex of the ATM interface (= ATM layer)."
    ::= { isarIatmInterfaceEntry  1 }

isarIatmInterfaceLowerLayerIfIndex OBJECT-TYPE
    SYNTAX  INTEGER (0..2147483647)
    ACCESS  read-only
    STATUS  mandatory
    DESCRIPTION
           "The ifIndex of the layer on which this ATM interface
            is defined."
    ::= { isarIatmInterfaceEntry  2 }




--  ATM Traffic Descriptor Parameter Group

-- This group contains a set of self-consistent
-- ATM traffic parameters including the
-- ATM traffic QoS Class.

-- The ATM virtual link tables (i.e., VPL and VCL tables)
-- will use this ATM Traffic Descriptor table
-- to assign traffic parameters and QoS Class
-- to the receive and transmit directions of
-- the ATM virtual links (i.e., VPLs and VCLs).
-- The ATM VPL or VCL table will indicate a row
-- in the atmTrafficDescrParamTable
-- using its atmTrafficDescrParamIndex value.
-- The management application can then compare a set of
-- ATM traffic parameters with a single value.

-- If no suitable row(s) in the atmTrafficDescrParamTable
-- exists, the manager must create a new row(s) in this
-- table. If such a row is created, agent checks the
-- sanity of that set of ATM traffic parameter values.

-- When creating a new row, the parameter values
-- will be checked for self-consistency.
-- Predefined/template rows may be supported.

-- A row in the atmTrafficDescrParamTable is deleted
-- by setting the atmTrafficDescrRowStatus to destroy(6).
-- The agent will check whether this row is still in use
-- by any entry of the isarIatmVplTable or isarIatmVclTable.
-- The agent denies the request if the row is still in
-- use.



--  The ISAR specific ATM Traffic Descriptor Parameter Table

-- !!!!!!!!!!!!!!!!!!!!!!!!!!!!!!!!!!!!!!!!!!!!!!!!!!!!!!!!!!!
-- The existing table is modified into an ISAR specific table
-- The name has not been changed, the number in the tree is
-- replaced.
-- !!!!!!!!!!!!!!!!!!!!!!!!!!!!!!!!!!!!!!!!!!!!!!!!!!!!!!!!!!!

-- isarIatmTrafficDescrParamTable 
--       OBJECT-IDENTIFIER ::= { isarIatmMIBObjects  5 } : replaced


-- next traffic descriptor index value
-- must be the only scalar in tree

isarIatmNextMIBObjects  OBJECT IDENTIFIER 
  ::= { isarIatmMIBObjects  16 }


isarItrafficDescrNextIndex OBJECT-TYPE
    SYNTAX  INTEGER (0..2147483647)
    ACCESS  read-only
    STATUS  mandatory
    DESCRIPTION
           "This object is used to assist the manager in
            selecting a value for isarIatmTrafficDescrParamIndex."
    ::= { isarIatmNextMIBObjects  1 }


isarIatmTrafficDescrParamTable OBJECT-TYPE
    SYNTAX  SEQUENCE OF IsarIatmTrafficDescrParamEntry
    ACCESS  not-accessible
    STATUS  mandatory
    DESCRIPTION
           "This table contains information on ATM traffic
            descriptor type and the associated parameters."
    ::= { isarIatmMIBObjects  13 }

isarIatmTrafficDescrParamEntry OBJECT-TYPE
    SYNTAX  IsarIatmTrafficDescrParamEntry
    ACCESS  not-accessible
    STATUS  mandatory
    DESCRIPTION
           "This list contains ATM traffic descriptor
            type and the associated parameters."
    INDEX   { isarIatmTrafficDescrParamIndex }
    ::= { isarIatmTrafficDescrParamTable  1 }

IsarIatmTrafficDescrParamEntry ::=
    SEQUENCE {
      isarIatmTrafficDescrParamIndex
        INTEGER,

      isarIatmTrafficDescrType
        INTEGER,

      isarIatmTrafficPeakCellRate
        INTEGER,

      isarIatmTrafficSustCellRate
        INTEGER,

      isarIatmTrafficMaxBurstSize
        INTEGER,

      isarIatmTrafficInitRate
        INTEGER,

      isarIatmTrafficMinRate
        INTEGER,

      isarIatmTrafficRateIncFactor
        INTEGER,

      isarIatmTrafficRateDecFactor
        INTEGER,

      isarIatmTrafficCellDelayVarTol
        INTEGER,

      isarIatmTrafficQoSClass
        INTEGER,

      isarIatmTrafficDescrRowStatus
        INTEGER
    }

isarIatmTrafficDescrParamIndex OBJECT-TYPE
    SYNTAX  INTEGER
    ACCESS  not-accessible
    STATUS  mandatory
    DESCRIPTION
           "This object is used by the virtual link
            table (i.e., VPL or VCL table)
            to identify the row of this table."
    ::= { isarIatmTrafficDescrParamEntry  1 }

isarIatmTrafficDescrType OBJECT-TYPE
    SYNTAX  INTEGER {
                      noTrafficType(1),
                      cbr(2),
                      rtVbr(3),
                      nrtVbr(4),
                      abr(5),
                      ubr(6),
                      ubrPlus(7)
            }
    ACCESS  read-write
    STATUS  mandatory
    DESCRIPTION
           "The value of this object identifies the type
            of ATM traffic descriptor.
            The type may indicate no traffic descriptor or
            traffic descriptor with one or more parameters.
            These parameters are specified as a parameter
            vector, in the corresponding instances of the
            objects:
                isarIatmTrafficPeakCellRate
                isarIatmTrafficSustCellRate
                isarIatmTrafficMaxBurstSize
                isarIatmTrafficInitRate
                isarIatmTrafficMinRate
                isarIatmTrafficRateIncFactor
                isarIatmTrafficRateDecFactor
            The SNMPv2 MAX-ACCESS is read-create."
    DEFVAL  { noTrafficType }
    ::= { isarIatmTrafficDescrParamEntry  2 }

isarIatmTrafficPeakCellRate OBJECT-TYPE
    SYNTAX  INTEGER
    ACCESS  read-write
    STATUS  mandatory
    DESCRIPTION
           "Peak rate in cps.
            The SNMPv2 MAX-ACCESS is read-create."
    DEFVAL  { 0 }
    ::= { isarIatmTrafficDescrParamEntry  3 }

isarIatmTrafficSustCellRate OBJECT-TYPE
    SYNTAX  INTEGER
    ACCESS  read-write
    STATUS  mandatory
    DESCRIPTION
           "Sustainalbe cell rate in cps.
            The SNMPv2 MAX-ACCESS is read-create."
    DEFVAL  { 0 }
    ::= { isarIatmTrafficDescrParamEntry  4 }

isarIatmTrafficMaxBurstSize OBJECT-TYPE
    SYNTAX  INTEGER
    ACCESS  read-write
    STATUS  mandatory
    DESCRIPTION
           "Maximum burst size in cells.
            The SNMPv2 MAX-ACCESS is read-create."
    DEFVAL  { 0 }
    ::= { isarIatmTrafficDescrParamEntry  5 }

isarIatmTrafficInitRate OBJECT-TYPE
    SYNTAX  INTEGER
    ACCESS  read-write
    STATUS  mandatory
    DESCRIPTION
           "Initial rate in cps.
            The SNMPv2 MAX-ACCESS is read-create."
    DEFVAL  { 0 }
    ::= { isarIatmTrafficDescrParamEntry  6 }

isarIatmTrafficMinRate OBJECT-TYPE
    SYNTAX  INTEGER
    ACCESS  read-write
    STATUS  mandatory
    DESCRIPTION
           "Minimum rate in cps.
            The SNMPv2 MAX-ACCESS is read-create."
    DEFVAL  { 0 }
    ::= { isarIatmTrafficDescrParamEntry  7 }

isarIatmTrafficRateIncFactor OBJECT-TYPE
    SYNTAX  INTEGER
    ACCESS  read-write
    STATUS  mandatory
    DESCRIPTION
           "Rate increase factor = 1 / 2power(isarIatmTrafficRateIncFactor).
            The SNMPv2 MAX-ACCESS is read-create."
    DEFVAL  { 0 }
    ::= { isarIatmTrafficDescrParamEntry  8 }

isarIatmTrafficRateDecFactor OBJECT-TYPE
    SYNTAX  INTEGER
    ACCESS  read-write
    STATUS  mandatory
    DESCRIPTION
           "Rate decrease factor = 1 / 2power(isarIatmTrafficRateDecFactor).
            The SNMPv2 MAX-ACCESS is read-create."
    DEFVAL  { 15 }
    ::= { isarIatmTrafficDescrParamEntry  9 }

isarIatmTrafficCellDelayVarTol OBJECT-TYPE
    SYNTAX  INTEGER
    ACCESS  read-write
    STATUS  mandatory
    DESCRIPTION
           "Cell delay variation time in micro-seconds.
            The SNMPv2 MAX-ACCESS is read-create."
    DEFVAL  { 0 }
    ::= { isarIatmTrafficDescrParamEntry  10 }

isarIatmTrafficQoSClass OBJECT-TYPE
    SYNTAX  INTEGER (0..255)
    ACCESS  read-write
    STATUS  mandatory
    DESCRIPTION
           "The value of this object identifies the QoS Class.
            Four Service classes have been
            specified in the ATM Forum UNI Specification:
            Service Class A: Constant bit rate video and
                             Circuit emulation
            Service Class B: Variable bit rate video/audio
            Service Class C: Connection-oriented data
            Service Class D: Connectionless data
            Four QoS classes numbered 1, 2, 3, and 4 have
            been specified with the aim to support service
            classes A, B, C, and D respectively.
            An unspecified QoS Class numbered `0' is used
            for best effort traffic.
            The SNMPv2 MAX-ACCESS is read-create."
    DEFVAL  { 0 }
    ::= { isarIatmTrafficDescrParamEntry  11 }

isarIatmTrafficDescrRowStatus OBJECT-TYPE
    SYNTAX  INTEGER {
                -- the following two values are states:
                -- these values may be read or written
                active(1),
                notInService(2),

                -- the following value is a state:
                -- this value may be read, but not written
                notReady(3),

                -- the following three values are
                -- actions: these values may be written,
                --   but are never read
                createAndGo(4),
                createAndWait(5),
                destroy(6)
             }
    ACCESS  read-write
    STATUS  mandatory
    DESCRIPTION
           "This object is used to create
            a new row or modify or delete an
            existing row in this table.
            The SNMPv2 MAX-ACCESS is read-create."
    DEFVAL  { active }
    ::= { isarIatmTrafficDescrParamEntry  12 }




--  ATM Interface Virtual Path Link (VPL) Group

-- This group contains configuration and state
-- information of a bi-directional Virtual Path Link
-- (VPL)

-- This table can be used to create, delete or modify
-- a VPL that is terminated in an ATM host or switch.
-- This table can also be used to create, delete or
-- modify a VPL which is cross-connected to another
-- VPL.

-- In the example below, the traffic flows on the receive
-- and transmit directions of the VPLs are characterized
-- by isarIatmVplReceiveTrafficDescrIndex and
-- isarIatmVplTransmitTrafficDescrIndex respectively.
-- The cross-connected VPLs are identified by
-- atmVplCrossConnectIdentifier.



--           ________________________________
--           |                              |
--  VPL      | ATM Host, Switch, or Network |   VPL
-- receive   |                              |  receive
-- ========> X                              X <=======
-- <======== X                              X ========>
-- transmit  |                              |  transmit
--           |______________________________|



--  The ATM Interface VPL Table


isarIatmVplTable OBJECT-TYPE
    SYNTAX  SEQUENCE OF IsarIatmVplEntry
    ACCESS  not-accessible
    STATUS  mandatory
    DESCRIPTION
           "The Virtual Path Link (VPL) table.  A
            bi-directional VPL is modeled as one entry
            in this table."
    ::= { isarIatmMIBObjects  6 }

isarIatmVplEntry OBJECT-TYPE
    SYNTAX  IsarIatmVplEntry
    ACCESS  not-accessible
    STATUS  mandatory
    DESCRIPTION
           "An entry in the VPL table.  This entry is
            used to model a bi-directional VPL.
            To create a VPL at an ATM interface,
            either of the following procedures are used:
            Negotiated VPL establishment

             (1) The management application creates
                 a VPL entry in the atmVplTable
                 by setting atmVplRowStatus to createAndWait(5).
                 This may fail for the following reasons:
                 - The selected VPI value is unavailable,
                 - The selected VPI value is in use.
                 Otherwise, the agent creates a row and
                 reserves the VPI value on that port.

             (2) The manager selects an existing row(s) in the
                 isarIatmTrafficDescrParamTable,
                 thereby, selecting a set of self-consistent
                 ATM traffic parameters and the QoS Class
                 for receive and transmit directions of the VPL.

            (2a) If no suitable row(s) in the
                 isarIatmTrafficDescrParamTable exists,
                 the manager must create a new row(s)
                 in that table.

            (2b) The manager characterizes the VPL's traffic
                 parameters through setting the
                 isarIatmVplReceiveTrafficDescrIndex and the
                 isarIatmVplTransmitTrafficDescrIndex values
                 in the VPL table, which point to the rows
                 containing desired ATM traffic parameter values
                 in the isarIatmTrafficDescrParamTable.  The agent
                 will check the availability of resources and
                 may refuse the request.

             (3) The manager activates the VPL by setting the
                 the isarIatmVplRowStatus to active(1).
                 If this set is successful, the agent has
                 reserved the resources to satisfy the requested
                 traffic parameter values and the QoS Class
                 for that VPL.
             (4) If the VPL terminates a VPC in the ATM host
                 or switch, the manager turns on the
                 isarIatmVplAdminStatus to up(1) to turn the VPL
                 traffic flow on.  Otherwise, the
                 atmVpCrossConnectTable  must be used
                 to cross-connect the VPL to another VPL(s)
                 in an ATM switch or network.

            One-Shot VPL Establishment
            A VPL may also be established in one step by a
            set-request with all necessary VPL parameter
            values and isarIatmVplRowStatus set to createAndGo(4).

            In contrast to the negotiated VPL establishment
            which allows for detailed error checking
            (i.e., set errors are explicitly linked to
            particular resource acquisition failures),
            the one-shot VPL establishment
            performs the setup on one operation but
            does not have the advantage of step-wise
            error checking.

            VPL Retirement

            A VPL is released by setting isarIatmVplRowStatus to
            destroy(6), and the agent may release all
            associated resources.
            
            INDEX : ifIndex is the index of the ATM layer."
    INDEX   { ifIndex,  isarIatmVplVpi }
    ::= { isarIatmVplTable  1 }

IsarIatmVplEntry ::=
    SEQUENCE {
      isarIatmVplVpi
        INTEGER,

      isarIatmVplAdminStatus
        INTEGER,

      isarIatmVplOperStatus
        INTEGER,

      isarIatmVplLastChange
        TimeTicks,

      isarIatmVplReceiveTrafficDescrIndex
        INTEGER,

      isarIatmVplTransmitTrafficDescrIndex
        INTEGER,

      isarIatmVplCrossConnectIdentifier
        INTEGER,

      isarIatmVplRowStatus
        INTEGER,

      isarIatmVplState
        INTEGER,
        
      isarIatmVplSegmentEndpt
        INTEGER
    }

isarIatmVplVpi OBJECT-TYPE
    SYNTAX  INTEGER (1..255)
    ACCESS  not-accessible
    STATUS  mandatory
    DESCRIPTION
           "The VPI value of the VPL.
            Note that the VPI=0 is not used
            for a VPL not associated with a VCL.
            The maximum VPI value cannot
            exceed the value allowable by the
            isarIatmInterfaceMaxVpiBits."
    ::= { isarIatmVplEntry  1 }

isarIatmVplAdminStatus OBJECT-TYPE
    SYNTAX  INTEGER {
                      up(1),
                      down(2)
            }
    ACCESS  read-write
    STATUS  mandatory
    DESCRIPTION
           "This object is implemented only for a VPL which
            terminates a VPC (i.e.,
            one which is NOT cross-connected to other VPLs).
            Its value specifies the desired administrative
            state of the VPL.  The up and down states indicate
            that the traffic flow is enabled and disabled
            respectively for this VPL.
            The SNMPv2 MAX-ACCESS is read-create."
    DEFVAL  { down }
    ::= { isarIatmVplEntry  2 }

isarIatmVplOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "This object indicates the current operational
            status of the VPL.  The up and down states
            indicate that the VPL is currently
            operational, or not operational, respectively.
            The unknown state indicates that the status of
            this VPL cannot be determined.
            Refer to RFC 2233 for description of other values."
    ::= { isarIatmVplEntry  3 }

isarIatmVplLastChange OBJECT-TYPE
    SYNTAX  TimeTicks
    ACCESS  read-only
    STATUS  mandatory
    DESCRIPTION
           "The value of MIB II's sysUpTime object
            at the time this VPL entered its current
            operational state.  If the current state was
            entered prior to the last re-initialization of the
            agent, then this object contains a zero value."
    ::= { isarIatmVplEntry  4 }

isarIatmVplReceiveTrafficDescrIndex OBJECT-TYPE
    SYNTAX  INTEGER
    ACCESS  read-write
    STATUS  mandatory
    DESCRIPTION
           "The value of this object identifies the row
            in the atmTrafficDescrParamTable which
            applies to the receive direction of the VPL.
            The SNMPv2 MAX-ACCESS is read-create."
    ::= { isarIatmVplEntry  5 }

isarIatmVplTransmitTrafficDescrIndex OBJECT-TYPE
    SYNTAX  INTEGER
    ACCESS  read-write
    STATUS  mandatory
    DESCRIPTION
           "The value of this object identifies the row
            in the atmTrafficDescrParamTable which
            applies to the transmit direction of the VPL.
            The SNMPv2 MAX-ACCESS is read-create."
    ::= { isarIatmVplEntry  6 }

isarIatmVplCrossConnectIdentifier OBJECT-TYPE
    SYNTAX  INTEGER (0..2147483647)
    ACCESS  read-only
    STATUS  mandatory
    DESCRIPTION
           "This object is implemented only for a VPL
            which is cross-connected to other VPLs
            that belong to the same VPC.  All such
            associated VPLs have the same value of this
            object, and all their cross-connections are
            identified by entries in the
            atmVpCrossConnectTable for which
            atmVpCrossConnectIndex has the same value.
            The value of this object is initialized by the
            agent after the associated entries in the
            atmVpCrossConnectTable have been created."
    ::= { isarIatmVplEntry  7 }

isarIatmVplRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create, delete
            or modify a row in this table.
            To create a new VCL, this object is
            initially set to 'createAndWait' or
            'createAndGo'.  This object must not be
            set to 'active' unless the following columnar
            objects exist in this row:
            isarIatmVplReceiveTrafficDescrIndex and
            atmVplTransmitTrafficDescrIndex.
            The SNMPv2 MAX-ACCESS is read-create."
    DEFVAL  { active }
    ::= { isarIatmVplEntry  8 }

isarIatmVplState OBJECT-TYPE
    SYNTAX  INTEGER (1 | 2 | 4 | 8 | 16 | 32)
    ACCESS  read-only
    STATUS  mandatory
    DESCRIPTION
           "This bit mask represents the Oam state of the Vcl.
              value   :    meaning
                1     :    NoAlarm  
                2     :    XmtAIS  = transmitting AIS state
                4     :    RcRDI   = receiving RDI state
                8     :    XmtRDI  = transmitting RDI state
               16     :    RcAIS   = receiving AIS state
               32     :    LOC     = Loss of continuity check
             ."
    DEFVAL  { 1 }
    ::= { isarIatmVplEntry  9 }

isarIatmVplSegmentEndpt OBJECT-TYPE
    SYNTAX  INTEGER {
                      yes(1),
                      no(2)
            }
    ACCESS  read-only
    STATUS  mandatory
    DESCRIPTION
           "Vpl segment endpoint."
    DEFVAL  { yes }
    ::= { isarIatmVplEntry  10 }







--  ATM Interface Virtual Channel Link (VCL) Group

-- This group contains configuration and state
-- information of a bi-directional Virtual Channel
-- Link (VCL) at an ATM interface.

-- This table can be used to create, delete or modify
-- a VCL that is terminated in an ATM host or switch.
-- This table can also be used to create, delete or modify
-- a VCL that is cross-connected to another VCL.


--  The ATM Interface VCL Table

isarIatmVclTable OBJECT-TYPE
    SYNTAX  SEQUENCE OF IsarIatmVclEntry
    ACCESS  not-accessible
    STATUS  mandatory
    DESCRIPTION
           "The Virtual Channel Link (VCL) table.  A
            bi-directional VCL is modeled as one entry
            in this table."
    ::= { isarIatmMIBObjects  7 }

isarIatmVclEntry OBJECT-TYPE
    SYNTAX  IsarIatmVclEntry
    ACCESS  not-accessible
    STATUS  mandatory
    DESCRIPTION
           "An entry in the VCL table.  This entry is
            used to model a bi-directional VCL.
            
            To create a VCL at an ATM interface,
            either of the following procedures are used:

            Negotiated VCL establishment

            (1) The management application creates
                a VCL entry in the isarIatmVclTable by setting 
                isarIatmVclRowStatus to createAndWait(5).
                This may fail for the following reasons:
                - The selected VPI/VCI values are unavailable,
                - The selected VPI/VCI values are in use.
                Otherwise, the agent creates a row and
                reserves the VPI/VCI values on that port.

            (2) The manager selects an existing row(s) in the
                isarIatmTrafficDescrParamTable,
                thereby, selecting a set of self-consistent
                ATM traffic parameters and the QoS Class
                for receive and transmit directions of the VCL.

           (2a) If no suitable row(s) in the
                isarIatmTrafficDescrParamTable exists,
                the manager must create a new row(s)
                in that table.

           (2b) The manager characterizes the VCL's traffic
                parameters through setting the
                isarIatmVclReceiveTrafficDescrIndex and the
                isarIatmVclTransmitTrafficDescrIndex values
                in the VCL table, which point to the rows
                containing desired ATM traffic parameter values
                in the isarIatmTrafficDescrParamTable.  The agent
                will check the availability of resources and
                may refuse the request.

            (3) The manager activates the VCL by setting the
                the isarIatmVclRowStatus to active(1).
                If this set is successful, the agent has
                reserved the resources to satisfy the requested
                traffic parameter values and the QoS Class
                for that VCL.
                
            (4) If the VCL terminates a VCC in the ATM host
                or switch, the manager turns on the
                isarIatmVclAdminStatus to up(1) to turn the VCL
                traffic flow on.  (Otherwise, the
                atmVcCrossConnectTable must be used
                to cross-connect the VCL to another VCL(s)
                in an ATM switch or network.)

            One-Shot VCL Establishment

            A VCL may also be established in one step by a
            set-request with all necessary VCL parameter
            values and isarIatmVclRowStatus set to createAndGo(4).

            In contrast to the negotiated VCL establishment
            which allows for detailed error checking
            (i.e., set errors are explicitly linked to
            particular resource acquisition failures),
            the one-shot VCL establishment
            performs the setup on one operation but
            does not have the advantage of step-wise
            error checking.

            VCL Retirement

            A VCL is released by setting isarIatmVclRowStatus to
            destroy(6), and the agent may release all
            associated resources.
            
            INDEX : ifIndex is the index of the ATM layer."
    INDEX   { ifIndex, isarIatmVclVpi, isarIatmVclVci }
    ::= { isarIatmVclTable  1 }

IsarIatmVclEntry ::=
    SEQUENCE {
      isarIatmVclVpi
        INTEGER,

      isarIatmVclVci
        INTEGER,

      isarIatmVclAdminStatus
        INTEGER,

      isarIatmVclOperStatus
        INTEGER,

      isarIatmVclLastChange
        TimeTicks,

      isarIatmVclReceiveTrafficDescrIndex
        INTEGER,

      isarIatmVclTransmitTrafficDescrIndex
        INTEGER,

      isarIatmVccAalType
        INTEGER,

      isarIatmVccAal5CpcsTransmitSduSize
        INTEGER,

      isarIatmVccAal5CpcsReceiveSduSize
        INTEGER,

      isarIatmVccAal5EncapsType
        INTEGER,

      isarIatmVclCrossConnectIdentifier
        INTEGER,

      isarIatmVclRowStatus
        INTEGER,
        
      isarIatmVclState
        INTEGER,
        
      isarIatmVclServiceType
        INTEGER,
        
      isarIatmVclSegmentEndpt
        INTEGER
    }

isarIatmVclVpi OBJECT-TYPE
    SYNTAX  INTEGER (0..255)
    ACCESS  not-accessible
    STATUS  mandatory
    DESCRIPTION
           "The VPI value of the VCL.
            The maximum VPI value cannot
            exceed the value allowable by the
            isarIatmInterfaceMaxVpiBits."
    ::= { isarIatmVclEntry  1 }

isarIatmVclVci OBJECT-TYPE
    SYNTAX  INTEGER (32..65535)
    ACCESS  not-accessible
    STATUS  mandatory
    DESCRIPTION
           "The VCI value of the VCL.
            The maximum VCI value cannot
            exceed the value allowable by the
            isarIatmInterfaceMaxVciBits."
    ::= { isarIatmVclEntry  2 }

isarIatmVclAdminStatus OBJECT-TYPE
    SYNTAX  INTEGER {
                 up(1),
                 down(2)
               }
    ACCESS  read-write
    STATUS  mandatory
    DESCRIPTION
           "This object is implemented only for a VCL which
            terminates a VCC (i.e.,
            one which is NOT cross-connected to other VCLs).
            Its value specifies the desired administrative
            state of the VCL.  The up and down states indicate
            that the traffic flow is enabled and disabled
            respectively for this VCL.
            The SNMPv2 MAX-ACCESS is read-create."
    ::= { isarIatmVclEntry  3 }

isarIatmVclOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
               }
    ACCESS  read-only
    STATUS  mandatory
    DESCRIPTION
           "This object indicates the current operational
            status of the VCL.  The up and down states
            indicate that the VCL is currently
            operational, or not operational, respectively.
            The unknown state indicates that the status of
            this VCL cannot be determined.
            Refer to RFC 2233 for description of other values."
    ::= { isarIatmVclEntry  4 }

isarIatmVclLastChange OBJECT-TYPE
    SYNTAX  TimeTicks
    ACCESS  read-only
    STATUS  mandatory
    DESCRIPTION
           "The value of MIB II's sysUpTime object
            at the time this VCL entered its current
            operational state.  If the current state was
            entered prior to the last re-initialization of the
            agent, then this object contains a zero value."
    ::= { isarIatmVclEntry  5 }

isarIatmVclReceiveTrafficDescrIndex OBJECT-TYPE
    SYNTAX  INTEGER
    ACCESS  read-write
    STATUS  mandatory
    DESCRIPTION
           "The value of this object identifies the row
            in the ATM Traffic Descriptor Table which
            applies to the receive direction of this VCL.
            The SNMPv2 MAX-ACCESS is read-create."
    ::= { isarIatmVclEntry  6 }

isarIatmVclTransmitTrafficDescrIndex OBJECT-TYPE
    SYNTAX  INTEGER
    ACCESS  read-write
    STATUS  mandatory
    DESCRIPTION
           "The value of this object identifies the row
            of the ATM Traffic Descriptor Table which applies
            to the transmit direction of this VCL.
            The SNMPv2 MAX-ACCESS is read-create."
    ::= { isarIatmVclEntry  7 }

isarIatmVccAalType OBJECT-TYPE
    SYNTAX  INTEGER {
                 aal1(1),
                 aal34(2),
                 aal5(3),
                 other(4),
                 unknown(5)
               }
    ACCESS  read-only
    STATUS  mandatory
    DESCRIPTION
           "An instance of this object only exists when the
            local VCL end-point is also the VCC end-point,
            and AAL is in use.
            The type of AAL used on this VCC.
            The AAL type includes AAL1, AAL3/4,
            and AAL5. The other(4) may be user-defined
            AAL type.  The unknown type indicates that
            the AAL type cannot be determined.
            
            IAD4700 : the AAL type is filled in at the moment
            that the VCL is used by an IWF.
            The value = unknown when the VCL is not in use."
    ::= { isarIatmVclEntry  8 }

isarIatmVccAal5CpcsTransmitSduSize OBJECT-TYPE
    SYNTAX  INTEGER (1..65535)
    ACCESS  read-write
    STATUS  mandatory
    DESCRIPTION
           "An instance of this object only exists when the
            local VCL end-point is also the VCC end-point,
            and AAL5 is in use.
            The maximum AAL5 CPCS SDU size in octets that is
            supported on the transmit direction of this VCC.
            The SNMPv2 MAX-ACCESS is read-create."
    DEFVAL  { 9188 }
    ::= { isarIatmVclEntry  9 }

isarIatmVccAal5CpcsReceiveSduSize OBJECT-TYPE
    SYNTAX  INTEGER (1..65535)
    ACCESS  read-write
    STATUS  mandatory
    DESCRIPTION
           "An instance of this object only exists when the
            local VCL end-point is also the VCC end-point,
            and AAL5 is in use.
            The maximum AAL5 CPCS SDU size in octets that is
            supported on the receive direction of this VCC.
            The SNMPv2 MAX-ACCESS is read-create."
    DEFVAL  { 9188 }
    ::= { isarIatmVclEntry  10 }

isarIatmVccAal5EncapsType OBJECT-TYPE
    SYNTAX  INTEGER {
                 vcMultiplexRoutedProtocol(1),
                 vcMultiplexBridgedProtocol8023(2),
                 vcMultiplexBridgedProtocol8025(3),
                 vcMultiplexBridgedProtocol8026(4),
                 vcMultiplexLANemulation8023(5),
                 vcMultiplexLANemulation8025(6),
                 llcEncapsulation(7),
                 multiprotocolFrameRelaySscs(8),
                 other(9),
                 unknown(10)
               }
    ACCESS  read-only
    STATUS  mandatory
    DESCRIPTION
           "An instance of this object only exists when the
            local VCL end-point is also the VCC end-point,
            and AAL5 is in use.
            The type of data encapsulation used over
            the AAL5 SSCS layer. The definitions reference
            RFC 1483 Multiprotocol Encapsulation
            over ATM AAL5 and to the ATM Forum
            LAN Emulation specification."
    DEFVAL  { unknown }
    ::= { isarIatmVclEntry  11 }

isarIatmVclCrossConnectIdentifier OBJECT-TYPE
    SYNTAX  INTEGER (0..2147483647)
    ACCESS  read-only
    STATUS  mandatory
    DESCRIPTION
           "IAD4700 : This object is not used as a link to the 
            atmVcCrossConnectTable but as a link to an interworking
            function table.
            The value of this object, together with 
            isarIatmVclServiceType, is initialized by the agent 
            after the associated entries in the
            isarI<serviceType>IwfTable have been created."
    ::= { isarIatmVclEntry  12 }

isarIatmVclRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create, delete or
            modify a row in this table.  To create
            a new VCL, this object is initially set
            to 'createAndWait' or 'createAndGo'.
            This object must not be set to 'active'
            unless the following columnar objects exist
            in this row:
              isarIatmVclReceiveTrafficDescrIndex,
              isarIatmVclTransmitTrafficDescrIndex.
            In addition, if the local VCL end-point
            is also the VCC end-point:
              isarIatmVccAalType.
            In addition, for AAL5 connections only:
              isarIatmVccAal5CpcsTransmitSduSize,
              isarIatmVccAal5CpcsReceiveSduSize, and
              isarIatmVccAal5EncapsType.
            The SNMPv2 MAX-ACCESS is read-create."
    DEFVAL  { active }
    ::= { isarIatmVclEntry  13 }

isarIatmVclState OBJECT-TYPE
    SYNTAX  INTEGER (1 | 2 | 4 | 8| 16 | 32)
    ACCESS  read-only
    STATUS  mandatory
    DESCRIPTION
           "This bit mask represents the Oam state of the Vcl.
              value   :    meaning
                1     :    NoAlarm  
                2     :    XmtAIS  = transmitting AIS state
                4     :    RcRDI   = receiving RDI state
                8     :    XmtRDI  = transmitting RDI state
               16     :    RcAIS   = receiving AIS state
               32     :    LOC     = Loss of continuity check
             ."
    DEFVAL  { 1 }
    ::= { isarIatmVclEntry  14 }

isarIatmVclServiceType OBJECT-TYPE
    SYNTAX  INTEGER {
                      ces(1),
                      frs(2),
                      thdlcs(3),
                      vcs(4),
                      lanis(5),
                      signalling(6),
                      none(10)
            }
    ACCESS  read-only
    STATUS  mandatory
    DESCRIPTION
           "Type of service is set when an entry in an IWF table is 
            created.  The type of service has to be set to 'none'
            when an entry in an IWF table is deleted.
            This field is necessary to find out which IWF table is 
            linked with the service corresponding to this entry.
               service type          IWF table
                  ces            isarIatmfCESConfTable  
                  frs            isarIfrAtm<Si/Ni>IwfConnectionTable
                  thdlcs         isarIthdlcsIwfTable   
                  vcs            isarIvcsIwfTable
                  lanis          isarIlanisIwfTable
            In order to access these IWF tables one must first determine
            the correct index via mapping tables.  The mapping tables 
            use the IWF-index as index.
                IWF table                          Mapping table
            isarIatmfCESConfTable             isarIatmfCESIwfMappingTable
            isarIfrAtmSiIwfConnectionTable    isarIfrAtmSiIwfMappingTable
            isarIfrAtmNiIwfConnectionTable    isarIfrAtmNiIwfMappingTable
            isarIthdlcsIwfTable               isarIthdlcsIwfMappingTable 
            isarIvcsIwfTable                  isarIvcsIwfMappingTable
            isarIlanisIwfTable                isarIlanisIwfMappingTable
            "
    DEFVAL  { none }
    ::= { isarIatmVclEntry  15 }

isarIatmVclSegmentEndpt OBJECT-TYPE
    SYNTAX  INTEGER {
                      yes(1),
                      no(2)
            }
    ACCESS  read-only
    STATUS  mandatory
    DESCRIPTION
           "Vcl segment endpoint."
    DEFVAL  { yes }
    ::= { isarIatmVclEntry  16 }



-- AAL5 Virtual Channel Connection Performance Statistics Group

-- This group contains the AAL5 performance statistics
-- of a VCC at the interface associated with an AAL5 entity
-- in an ATM host or ATM switch.

isarIaal5VccTable OBJECT-TYPE
    SYNTAX  SEQUENCE OF IsarIaal5VccEntry
    ACCESS  not-accessible
    STATUS  mandatory
    DESCRIPTION
           "This table contains AAL5 VCC performance
            parameters."
    ::= { isarIatmMIBObjects  12 }

isarIaal5VccEntry OBJECT-TYPE
    SYNTAX  IsarIaal5VccEntry
    ACCESS  not-accessible
    STATUS  mandatory
    DESCRIPTION
           "This list contains the AAL5 VCC
            performance parameters.
            
            INDEX : ifIndex is the index of the ATM layer."
    INDEX   { ifIndex, isarIaal5VccVpi, isarIaal5VccVci }
    ::= { isarIaal5VccTable  1 }

IsarIaal5VccEntry ::=
    SEQUENCE {
      isarIaal5VccVpi
        INTEGER,

      isarIaal5VccVci
        INTEGER,

      isarIaal5VccCrcErrors
        Counter,

      isarIaal5VccSarTimeOuts
        Counter,

      isarIaal5VccOverSizedSDUs
        Counter,
        
      isarIaal5VccReceivedSDUs
        Counter
    }

isarIaal5VccVpi OBJECT-TYPE
    SYNTAX  INTEGER (0..4095)
    ACCESS  not-accessible
    STATUS  mandatory
    DESCRIPTION
           "The VPI value of the AAL5 VCC at the
            interface identified by the ifIndex."
    ::= { isarIaal5VccEntry  1 }

isarIaal5VccVci OBJECT-TYPE
    SYNTAX  INTEGER (0..65535)
    ACCESS  not-accessible
    STATUS  mandatory
    DESCRIPTION
           "The VCI value of the AAL5 VCC at the
            interface identified by the ifIndex."
    ::= { isarIaal5VccEntry  2 }

isarIaal5VccCrcErrors OBJECT-TYPE
    SYNTAX  Counter
    ACCESS  read-only
    STATUS  mandatory
    DESCRIPTION
           "The number of AAL5 CPCS PDUs received with
            CRC-32 errors on this AAL5 VCC at the
            interface associated with an AAL5 entity."
    ::= { isarIaal5VccEntry  3 }

isarIaal5VccSarTimeOuts OBJECT-TYPE
    SYNTAX  Counter
    ACCESS  read-only
    STATUS  mandatory
    DESCRIPTION
           "The number of partially re-assembled AAL5
            CPCS PDUs which were discarded
            on this AAL5 VCC at the interface associated
            with an AAL5 entity because they
            were not fully re-assembled within the
            required time period.  If the re-assembly
            timer is not supported, then this object
            contains a zero value."
    ::= { isarIaal5VccEntry  4 }

isarIaal5VccOverSizedSDUs OBJECT-TYPE
    SYNTAX  Counter
    ACCESS  read-only
    STATUS  mandatory
    DESCRIPTION
           "The number of AAL5 CPCS PDUs discarded
            on this AAL5 VCC at the interface
            associated with an AAL5 entity because the
            AAL5 SDUs were too large."
    ::= { isarIaal5VccEntry  5 }

isarIaal5VccReceivedSDUs OBJECT-TYPE
    SYNTAX  Counter
    ACCESS  read-only
    STATUS  mandatory
    DESCRIPTION
           "The number of AAL5 CPCS PDUs received
            on this AAL5 VCC at the interface
            associated with an AAL5 entity. (IAD4700 specific)"
    ::= { isarIaal5VccEntry  6 }




--
-- ISAR specific extension
--

-- Connection priority table 
-- This table is linked with the isarIatmVclTable.
-- Rows in this table are created when rows in the isarIatmVclTable
-- are created.  Idem for deletion.

isarIatmConnectionPriorityTable OBJECT-TYPE
    SYNTAX  SEQUENCE OF IsarIatmConnectionPriorityEntry
    ACCESS  not-accessible
    STATUS  obsolete
    DESCRIPTION
           "This table contains the priority of a connection
            identified by a VCL or VPL."
    ::= { isarIatmMIBObjects  14 }

isarIatmConnectionPriorityEntry OBJECT-TYPE
    SYNTAX  IsarIatmConnectionPriorityEntry
    ACCESS  not-accessible
    STATUS  obsolete
    DESCRIPTION
           "One row in the Connection priority table.
            A row in the table is identified by ifIndex,
            isarIatmConnectionVpi and isarIatmConnectionVci
            (isarIatmConnectionVci = 0 in case of VPL).
            
            INDEX : ifIndex is the index of the ATM layer."
    INDEX   { ifIndex,
              isarIatmConnectionVpi, 
              isarIatmConnectionVci 
            }
    ::= { isarIatmConnectionPriorityTable  1 }

IsarIatmConnectionPriorityEntry ::=
    SEQUENCE {
      isarIatmConnectionVpi
        INTEGER,

      isarIatmConnectionVci
        INTEGER,

      isarIatmConnectionPriority
        INTEGER

    }


isarIatmConnectionVpi OBJECT-TYPE
    SYNTAX  INTEGER (0..4095)
    ACCESS  read-only
    STATUS  obsolete
    DESCRIPTION
           "This is the same as isarIatmVclVpi in isarIatmVclTable
            when the connection is identified by VCL, or
            isarIatmVplVpi in isarIatmVplTable."
    ::= { isarIatmConnectionPriorityEntry  1 }

isarIatmConnectionVci OBJECT-TYPE
    SYNTAX  INTEGER (0..65535)
    ACCESS  read-only
    STATUS  obsolete
    DESCRIPTION
           "This is the same as isarIatmVclVci in isarIatmVclTable
            when the connection is identified by VCL, otherwise 0."
    ::= { isarIatmConnectionPriorityEntry  2 }

isarIatmConnectionPriority OBJECT-TYPE
    SYNTAX  INTEGER {
                      high(1),
                      medium(2),
                      low(3)
            }
    ACCESS  read-write
    STATUS  obsolete
    DESCRIPTION
           "The connection priority levels are IAD4700 defined priority
            levels. In case part of the ATM interface fails (e.g. an 
            E1T1 port fails in case of an IMA) all active connections 
            have to be re-routed over the interface. The available 
            bandwidth decreases and some connections may have to be set 
            to operstatusdown. This priority level helps choosing which 
            connections to break down."
    ::= { isarIatmConnectionPriorityEntry  3 }





isarIcellScrambling OBJECT-TYPE
    SYNTAX  INTEGER {
                      true(1),
                      false(2)
            }
    ACCESS  read-write
    STATUS  mandatory
    DESCRIPTION
           "Scrambling the bits in the payload of the ATM cells by
            the IWE-8."
    DEFVAL { true }
    ::= { isarIatmMIBObjects  15 }



-- Call and connection control information


isarIatmInterfaceCcConfTable OBJECT-TYPE
    SYNTAX  SEQUENCE OF IsarIatmInterfaceCcConfEntry
    ACCESS  not-accessible
    STATUS  mandatory
    DESCRIPTION
           "These objects are not used by the IAD4700 software.
            They are needed for path management via the 46020.  Path management
            of the 46020 selects the VPI, VCI itself.  The information in this
            table will be used to tell the 46020 not to choose a value within 
            the indicated range because they are reserved for CCC SVCs.
            The information of this table is not visible in the LCT.
            Rows are created at startup of the IAD4700.
            Values can be changed at any time."
    ::= { isarIatmMIBObjects  18 }

isarIatmInterfaceCcConfEntry OBJECT-TYPE
    SYNTAX  IsarIatmInterfaceCcConfEntry
    ACCESS  not-accessible
    STATUS  mandatory
    DESCRIPTION
           "One row in the isarIatmInterfaceCcConfTable.
            
            INDEX : ifIndex is the index of the ATM layer."
    INDEX   { ifIndex }
    ::= { isarIatmInterfaceCcConfTable  1 }

IsarIatmInterfaceCcConfEntry ::=
    SEQUENCE {
      isarIatmInterfaceCcResBw
        INTEGER,

      isarIatmInterfaceCcResVpiVciRange
        DisplayString
    }

isarIatmInterfaceCcResBw OBJECT-TYPE
    SYNTAX  INTEGER
    ACCESS  read-write
    STATUS  mandatory
    DESCRIPTION
           "Reserved bandwidth at the associated ATM interface.
            UNITS = kBits/sec"
    DEFVAL { 0 }
    ::= { isarIatmInterfaceCcConfEntry  1 }


isarIatmInterfaceCcResVpiVciRange OBJECT-TYPE
    SYNTAX  DisplayString (SIZE (0..255))
    ACCESS  read-write
    STATUS  mandatory
    DESCRIPTION
           "Reserved VPI/VCI range for CCC SVCs. 
            The VPI/VCI range is a string with one or more 'VPI/VCI 
            ranges' separated by a ';'.
            A VPI/VCI range is a VPI range and a VCI range separated by 
            a ':'.
            The maximum number of VPI/VCI ranges is 4. 
            There can be no overlap of VPI ranges for multiple VPI/VCI 
            ranges. 
            The VCIs have to be between 32 and 1024.
            E.g. 10-15:100-200;20:32-40.  Thsi means: for VPIs 10 to 15
                 the VCIs 100 to 200 are reserved and for VPI = 20 the 
                 VCIs 32 to 40 are reserved."
    DEFVAL { "" }
    ::= { isarIatmInterfaceCcConfEntry  3 }



--  The ATM Interface VCL read-only Table

isarIatmVclRoTable OBJECT-TYPE
    SYNTAX  SEQUENCE OF IsarIatmVclRoEntry
    ACCESS  not-accessible
    STATUS  mandatory
    DESCRIPTION
           "The Virtual Channel Link (VCL) read-only table.  A
            bi-directional VCL is modeled as one entry in this
            table.
            This table is a duplicate of the isarIatmVclTable with all
            fields, except row status, set to read-only.  The operator
            is not allowed to modify entries in this table, only delete
            is permitted.  Deletion of a VCL with service type = 
            iwfIwfSignaling or broadbandSignaling is not allowed.
            Duplication is done for Call and connection control because
            this software creates its own VCLs.
            Rows are created/deleted by IAD4700."
    ::= { isarIatmMIBObjects  19 }

isarIatmVclRoEntry OBJECT-TYPE
    SYNTAX  IsarIatmVclRoEntry
    ACCESS  not-accessible
    STATUS  mandatory
    DESCRIPTION
           "An entry in the VCL table.  This entry is
            used to model a bi-directional VCL.
            
            INDEX : ifIndex is the index of the ATM layer."
    INDEX   { ifIndex, isarIatmVclRoVpi, isarIatmVclRoVci }
    ::= { isarIatmVclRoTable  1 }

IsarIatmVclRoEntry ::=
    SEQUENCE {
      isarIatmVclRoVpi
        INTEGER,

      isarIatmVclRoVci
        INTEGER,

      isarIatmVclRoOperStatus
        INTEGER,

      isarIatmVclRoLastChange
        TimeTicks,

      isarIatmVclRoReceiveTrafficDescrIndex
        INTEGER,

      isarIatmVclRoTransmitTrafficDescrIndex
        INTEGER,

      isarIatmVccRoAalType
        INTEGER,

      isarIatmVccRoAal5CpcsTransmitSduSize
        INTEGER,

      isarIatmVccRoAal5CpcsReceiveSduSize
        INTEGER,

      isarIatmVccRoAal5EncapsType
        INTEGER,

      isarIatmVclRoCrossConnectIdentifier
        INTEGER,

      isarIatmVclRoRowStatus
        INTEGER,
        
      isarIatmVclRoState
        INTEGER,
        
      isarIatmVclRoServiceType
        INTEGER,
        
      isarIatmVclRoSegmentEndpt
        INTEGER
    }

isarIatmVclRoVpi OBJECT-TYPE
    SYNTAX  INTEGER (0..255)
    ACCESS  not-accessible
    STATUS  mandatory
    DESCRIPTION
           "The VPI value of the VCL.
            The maximum VPI value cannot
            exceed the value allowable by the
            isarIatmInterfaceMaxVpiBits."
    ::= { isarIatmVclRoEntry  1 }

isarIatmVclRoVci OBJECT-TYPE
    SYNTAX  INTEGER (32..65535)
    ACCESS  not-accessible
    STATUS  mandatory
    DESCRIPTION
           "The VCI value of the VCL.
            The maximum VCI value cannot
            exceed the value allowable by the
            isarIatmInterfaceMaxVciBits."
    ::= { isarIatmVclRoEntry  2 }

isarIatmVclRoOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
               }
    ACCESS  read-only
    STATUS  mandatory
    DESCRIPTION
           "This object indicates the current operational
            status of the VCL.  The up and down states
            indicate that the VCL is currently
            operational, or not operational, respectively.
            The unknown state indicates that the status of
            this VCL cannot be determined.
            Refer to RFC 2233 for description of other values."
    ::= { isarIatmVclRoEntry  4 }

isarIatmVclRoLastChange OBJECT-TYPE
    SYNTAX  TimeTicks
    ACCESS  read-only
    STATUS  mandatory
    DESCRIPTION
           "The value of MIB II's sysUpTime object
            at the time this VCL entered its current
            operational state.  If the current state was
            entered prior to the last re-initialization of the
            agent, then this object contains a zero value."
    ::= { isarIatmVclRoEntry  5 }

isarIatmVclRoReceiveTrafficDescrIndex OBJECT-TYPE
    SYNTAX  INTEGER
    ACCESS  read-only
    STATUS  mandatory
    DESCRIPTION
           "The value of this object identifies the row
            in the ATM Traffic Descriptor Table which
            applies to the receive direction of this VCL."
    ::= { isarIatmVclRoEntry  6 }

isarIatmVclRoTransmitTrafficDescrIndex OBJECT-TYPE
    SYNTAX  INTEGER
    ACCESS  read-only
    STATUS  mandatory
    DESCRIPTION
           "The value of this object identifies the row
            of the ATM Traffic Descriptor Table which applies
            to the transmit direction of this VCL."
    ::= { isarIatmVclRoEntry  7 }

isarIatmVccRoAalType OBJECT-TYPE
    SYNTAX  INTEGER {
                 aal1(1),
                 aal34(2),
                 aal5(3),
                 other(4),
                 unknown(5)
               }
    ACCESS  read-only
    STATUS  mandatory
    DESCRIPTION
           "An instance of this object only exists when the
            local VCL end-point is also the VCC end-point,
            and AAL is in use.
            The type of AAL used on this VCC.
            The AAL type includes AAL1, AAL3/4,
            and AAL5. The other(4) may be user-defined
            AAL type.  The unknown type indicates that
            the AAL type cannot be determined.
            
            IAD4700 : the AAL type is filled in at the moment
            that the VCL is used by an IWF.
            The value = unknown when the VCL is not in use."
    ::= { isarIatmVclRoEntry  8 }

isarIatmVccRoAal5CpcsTransmitSduSize OBJECT-TYPE
    SYNTAX  INTEGER (1..65535)
    ACCESS  read-only
    STATUS  mandatory
    DESCRIPTION
           "An instance of this object only exists when the
            local VCL end-point is also the VCC end-point,
            and AAL5 is in use.
            The maximum AAL5 CPCS SDU size in octets that is
            supported on the transmit direction of this VCC."
    DEFVAL  { 9188 }
    ::= { isarIatmVclRoEntry  9 }

isarIatmVccRoAal5CpcsReceiveSduSize OBJECT-TYPE
    SYNTAX  INTEGER (1..65535)
    ACCESS  read-only
    STATUS  mandatory
    DESCRIPTION
           "An instance of this object only exists when the
            local VCL end-point is also the VCC end-point,
            and AAL5 is in use.
            The maximum AAL5 CPCS SDU size in octets that is
            supported on the receive direction of this VCC."
    DEFVAL  { 9188 }
    ::= { isarIatmVclRoEntry  10 }

isarIatmVccRoAal5EncapsType OBJECT-TYPE
    SYNTAX  INTEGER {
                 vcMultiplexRoutedProtocol(1),
                 vcMultiplexBridgedProtocol8023(2),
                 vcMultiplexBridgedProtocol8025(3),
                 vcMultiplexBridgedProtocol8026(4),
                 vcMultiplexLANemulation8023(5),
                 vcMultiplexLANemulation8025(6),
                 llcEncapsulation(7),
                 multiprotocolFrameRelaySscs(8),
                 other(9),
                 unknown(10)
               }
    ACCESS  read-only
    STATUS  mandatory
    DESCRIPTION
           "An instance of this object only exists when the
            local VCL end-point is also the VCC end-point,
            and AAL5 is in use.
            The type of data encapsulation used over
            the AAL5 SSCS layer. The definitions reference
            RFC 1483 Multiprotocol Encapsulation
            over ATM AAL5 and to the ATM Forum
            LAN Emulation specification."
    DEFVAL  { unknown }
    ::= { isarIatmVclRoEntry  11 }

isarIatmVclRoCrossConnectIdentifier OBJECT-TYPE
    SYNTAX  INTEGER (0..2147483647)
    ACCESS  read-only
    STATUS  mandatory
    DESCRIPTION
           "IAD4700 : This object is not used as a link to the 
            atmVcCrossConnectTable but as a link to an interworking
            function table.
            The value of this object, together with 
            isarIatmVclRoServiceType, is initialized by the agent 
            after the associated entries in the
            isarI<serviceType>IwfTable have been created.
            The value of this object is equal to a remote node index (CCC)
            when isarIatmVclRoServiceType=iwfIwfSignalling and equal to 1
            when isarIatmVclRoServiceType=broadbandSignalling."
    ::= { isarIatmVclRoEntry  12 }

isarIatmVclRoRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create, delete or
            modify a row in this table.  To create
            a new VCL, this object is initially set
            to 'createAndWait' or 'createAndGo'.
            This object must not be set to 'active'
            unless the following columnar objects exist
            in this row:
              isarIatmVclReceiveTrafficDescrIndex,
              isarIatmVclTransmitTrafficDescrIndex.
            In addition, if the local VCL end-point
            is also the VCC end-point:
              isarIatmVccAalType.
            In addition, for AAL5 connections only:
              isarIatmVccAal5CpcsTransmitSduSize,
              isarIatmVccAal5CpcsReceiveSduSize, and
              isarIatmVccAal5EncapsType.
            
            The operator is not allowed to delete an entry with
            service type = iwfIwfSignalling or broadbandSignalling."
    DEFVAL  { active }
    ::= { isarIatmVclRoEntry  13 }

isarIatmVclRoState OBJECT-TYPE
    SYNTAX  INTEGER (1 | 2 | 4 | 8| 16 | 32)
    ACCESS  read-only
    STATUS  mandatory
    DESCRIPTION
           "This bit mask represents the Oam state of the Vcl.
              value   :    meaning
                1     :    NoAlarm  
                2     :    XmtAIS  = transmitting AIS state
                4     :    RcRDI   = receiving RDI state
                8     :    XmtRDI  = transmitting RDI state
               16     :    RcAIS   = receiving AIS state
               32     :    LOC     = Loss of continuity check
             ."
    DEFVAL  { 1 }
    ::= { isarIatmVclRoEntry  14 }

isarIatmVclRoServiceType OBJECT-TYPE
    SYNTAX  INTEGER {
                      ces(1),
                      frs(2),
                      thdlcs(3),
                      vcs(4),
                      lanis(5),
                      signalling(6),
                      iwfIwfSignalling(7),
                      broadbandSignalling(8),
                      none(10)
            }
    ACCESS  read-only
    STATUS  mandatory
    DESCRIPTION
           "Type of service is set when an entry in an IWF table is 
            created.  The type of service has to be set to 'none'
            when an entry in an IWF table is deleted.
            This field is necessary to find out which IWF table is 
            linked with the service corresponding to this entry.
               service type             IWF table
                  ces                 isarIatmfCESConfTable  
                  frs                 isarIfrAtm<Si/Ni>IwfConnectionTable
                  thdlcs              isarIthdlcsIwfTable   
                  vcs                 isarIvcsIwfTable
                  lanis               isarIlanisIwfTable
                  signalling          isarIsignallingIwfTable
                  iwfIwfSignalling    -
                  broadbandSignalling -
            In order to access these IWF tables one must first determine
            the correct index via mapping tables.  The mapping tables 
            use the IWF-index as index.
                IWF table                          Mapping table
            isarIatmfCESConfTable            isarIatmfCESIwfMappingTable
            isarIfrAtmSiIwfConnectionTable   isarIfrAtmSiIwfMappingTable
            isarIfrAtmNiIwfConnectionTable   isarIfrAtmNiIwfMappingTable
            isarIthdlcsIwfTable              isarIthdlcsIwfMappingTable 
            isarIvcsIwfTable                 isarIvcsIwfMappingTable
            isarIlanisIwfTable               isarIlanisIwfMappingTable
            isarIsignallingIwfTable          isarIsignallingIwfMappingTable
            "
    DEFVAL  { none }
    ::= { isarIatmVclRoEntry  15 }

isarIatmVclRoSegmentEndpt OBJECT-TYPE
    SYNTAX  INTEGER {
                      yes(1),
                      no(2)
            }
    ACCESS  read-only
    STATUS  mandatory
    DESCRIPTION
           "Vcl segment endpoint."
    DEFVAL  { yes }
    ::= { isarIatmVclRoEntry  16 }



-- traps
isarIatmVclStatusChange TRAP-TYPE
    ENTERPRISE  isarIatmMIBObjects
    VARIABLES   { ifIndex,
                  isarIatmVclVpi,
                  isarIatmVclVci,
                  isarIatmVclAdminStatus,
                  isarIatmVclAdminStatus,
                  isarIatmVclOperStatus,
                  isarIatmVclOperStatus
                 }
    DESCRIPTION
           "An indication that the operation status of this ATM VCL
            has changed.
            A status change is given when :
            1. isarIatmVclAdminStatus is 'up' and 
               isarIatmVclOperStatus is going 'down' (set alarm)
            2. when isarIatmVclOperStatus is leaving the 'down' 
               state (clear alarm)
            3. isarIatmVclAdminStatus is set to 'up' and 
               isarIatmVclOperStatus is not changed to 'up' (set alarm)
            4. isarIatmVclAdminStatus is set to 'down' and 
               isarIatmVclOperStatus is not 'up' (clear alarm)
            The first isarIatmVclAdminStatus is the previous state,
            the second isarIatmVclAdminStatus is the new state.
            The first isarIatmVclOperStatus is the previous state,
            the second isarIatmVclOperStatus is the new state."
    ::= 1

isarIatmVplStatusChange TRAP-TYPE
    ENTERPRISE  isarIatmMIBObjects
    VARIABLES   { ifIndex,
                  isarIatmVplVpi,
                  isarIatmVplAdminStatus,
                  isarIatmVplAdminStatus,
                  isarIatmVplOperStatus,
                  isarIatmVplOperStatus
                 }
    DESCRIPTION
           "An indication that the operation status of this ATM VPL
            has changed.
            A status change is given when :
            1. isarIatmVplAdminStatus is 'up' and 
               isarIatmVplOperStatus is going 'down' (set alarm)
            2. when isarIatmVplOperStatus is leaving the 'down' 
               state (clear alarm)
            3. isarIatmVplAdminStatus is set to 'up' and 
               isarIatmVplOperStatus is not changed to 'up' (set alarm)
            4. isarIatmVplAdminStatus is set to 'down' and 
               isarIatmVplOperStatus is not 'up' (clear alarm)
            The first isarIatmVplAdminStatus is the previous state,
            the second isarIatmVplAdminStatus is the new state.
            The first isarIatmVplOperStatus is the previous state,
            the second isarIatmVplOperStatus is the new state."
    ::= 2

isarIatmVplOamStateChange TRAP-TYPE
    ENTERPRISE  isarIatmMIBObjects
    VARIABLES   { ifIndex,
                  isarIatmVplVpi,
                  isarIatmVplState
                 }
    DESCRIPTION
           "Indicates that the OAM failure state of the VPL has
            changed."
    ::= 3

isarIatmVclOamStateChange TRAP-TYPE
    ENTERPRISE  isarIatmMIBObjects
    VARIABLES   { ifIndex,
                  isarIatmVclVpi,
                  isarIatmVclVci,
                  isarIatmVclState
                 }
    DESCRIPTION
           "Indicates that the OAM failure state of the VCL has
            changed."
    ::= 4


--
-- ISAR atmMIBObjects : end
--  




-- This file cannot be used to create SNMP agent.
-- The file isarOneFile.my has to be used to create the agent.


-- isarIserviceMIBObjects      OBJECT IDENTIFIER ::= { isar  15 }


--
-- ISAR serviceMIBObjects : begin
--
-- enterprise MIB for ISAR
-- The MIB is written for SNMPv1.

--
-- ISAR service
--



-- ISAR service table


isarIserviceTable OBJECT-TYPE
    SYNTAX  SEQUENCE OF IsarIserviceEntry
    ACCESS  not-accessible
    STATUS  mandatory
    DESCRIPTION
           "This table contains all services that are present in IAD4700.
            When a row in this table is created (by IAD4700), an entry in the
            isarIserviceMappingTable is made by IAD4700 (inverse mapping
            of index)."
    ::= { isarIserviceMIBObjects  1 }

isarIserviceEntry OBJECT-TYPE
    SYNTAX  IsarIserviceEntry
    ACCESS  not-accessible
    STATUS  mandatory
    DESCRIPTION
           "One row in the isarIserviceTable."
    INDEX   { isarIserviceIndex }
    ::= { isarIserviceTable  1 }


IsarIserviceEntry ::=
    SEQUENCE { 
      isarIserviceIndex
        INTEGER,
        
      isarIserviceName
        DisplayString,
        
      isarIserviceType
        INTEGER,
        
      isarIserviceStackNumber
        INTEGER,
        
      isarIserviceSlotNumber
        INTEGER,

      isarIserviceBufferNum
        INTEGER,

      isarIserviceBufferLength
        INTEGER,        

      isarIserviceAdminStatus
        INTEGER,

      isarIserviceOperStatus
        INTEGER

    }
    
isarIserviceIndex OBJECT-TYPE
    SYNTAX  INTEGER
    ACCESS  read-only
    STATUS  mandatory
    DESCRIPTION
           "The index of the service."
    ::= { isarIserviceEntry  1 }

isarIserviceName OBJECT-TYPE
    SYNTAX  DisplayString (SIZE (0..255))
    ACCESS  read-write
    STATUS  mandatory
    DESCRIPTION
           "The operator given name of the service."
    ::= { isarIserviceEntry  2 }

isarIserviceType OBJECT-TYPE
    SYNTAX  INTEGER {
                      ces(1),
                      frs(2),
                      thdlcs(3),
                      vcs(4),
                      lanis(5),
                      signalling(6)
                --    iwfIwfSignalling(7)   for CCC: will be used in VCLs
                --    broadbandSignalling(8)   for CCC: will be used in VCLs
            }
    ACCESS  read-only
    STATUS  mandatory
    DESCRIPTION
           "The name of the service."
    ::= { isarIserviceEntry  3 }

isarIserviceStackNumber OBJECT-TYPE
    SYNTAX  INTEGER (0..63)
    ACCESS  read-only
    STATUS  mandatory
    DESCRIPTION
           "The number of the IAD4700 in which the service physically
            resides (when IAD4700s are stacked)."
    ::= { isarIserviceEntry  4 }

isarIserviceSlotNumber OBJECT-TYPE
    SYNTAX  INTEGER (0..3)
    ACCESS  read-only
    STATUS  mandatory
    DESCRIPTION
           "The number of the slot in which the service physically
            resides.  The slot number corresponds to isarIphysSlotId
            of isarIslotTable."
    ::= { isarIserviceEntry  5 }

isarIserviceBufferNum OBJECT-TYPE
    SYNTAX  INTEGER
    ACCESS  read-only
    STATUS  mandatory
    DESCRIPTION
           "The number of buffers for store and forward that are
            dedicated to this service. (will probably be defined
            in a .INI-file)"
    ::= { isarIserviceEntry  6 }

isarIserviceBufferLength OBJECT-TYPE
    SYNTAX  INTEGER
    ACCESS  read-only
    STATUS  mandatory
    DESCRIPTION
           "The lentgh of the buffers."
    ::= { isarIserviceEntry  7 }

isarIserviceAdminStatus OBJECT-TYPE
    SYNTAX  INTEGER {
                      up(1),
                      down(2)
            }
    ACCESS  read-write
    STATUS  mandatory
    DESCRIPTION
           "The administrative status of this service. It allows the
            operator to disable/enable the data flow for a service."
    ::= { isarIserviceEntry  8 }

isarIserviceOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "The operational status of this service. It allows the
            operator to determine the availability of the module
            where this service task runs on.
            Refer to RFC 2233 for the different states."
    ::= { isarIserviceEntry  9 }



-- ISAR service mapping table


isarIserviceMappingTable OBJECT-TYPE
    SYNTAX  SEQUENCE OF IsarIserviceMappingEntry
    ACCESS  not-accessible
    STATUS  mandatory
    DESCRIPTION
           "This table contains all services that are present in IAD4700."
    ::= { isarIserviceMIBObjects  3 }

isarIserviceMappingEntry OBJECT-TYPE
    SYNTAX  IsarIserviceMappingEntry
    ACCESS  not-accessible
    STATUS  mandatory
    DESCRIPTION
           "One row in the isarIserviceMappingTable."
    INDEX   { isarIserviceStackNumber, isarIserviceSlotNumber, isarIserviceType }
    ::= { isarIserviceMappingTable  1 }


IsarIserviceMappingEntry ::=
    SEQUENCE { 
      isarIserviceMappingIndex
        INTEGER
    }
    
isarIserviceMappingIndex OBJECT-TYPE
    SYNTAX  INTEGER
    ACCESS  read-only
    STATUS  mandatory
    DESCRIPTION
           "The index of the service."
    ::= { isarIserviceMappingEntry  1 }
        


-- trap
isarIserviceTraps OBJECT IDENTIFIER     ::= { isarIserviceMIBObjects 2 }

isarIserviceStatusChange TRAP-TYPE
    ENTERPRISE  isarIserviceTraps
    VARIABLES   { isarIserviceIndex, 
                  isarIserviceAdminStatus,
                  isarIserviceOperStatus,
                  isarIserviceOperStatus
                }
    DESCRIPTION
           "An indication that the operation status of this interworking
            function has changed.
            A status change is given when :
            1. isarIserviceAdminStatus is 'up' and 
               isarIserviceOperStatus is going 'down'
            2. when isarIserviceOperStatus is leaving the 'down' 
               state.
            The first isarIserviceOperStatus is the previous state,
            the second isarIserviceOperStatus is the new state."
    ::= 1

isarIserviceAal5ProcessorUnavailable TRAP-TYPE
    ENTERPRISE  isarIserviceTraps
    VARIABLES   { isarIserviceIndex }
    DESCRIPTION
           "An indication that there is no AAL5 processor available."
    ::= 2



--
-- ISAR serviceMIBObjects : end
--



-- This file cannot be used to create SNMP agent.
-- The file isarOneFile.my has to be used to create the agent.


-- isarIlanisMIBObjects      OBJECT IDENTIFIER ::= { isar  16 }


--
-- ISAR lanisMIBObjects : begin
--
-- enterprise MIB for ISAR
-- The MIB is written for SNMPv1.


-- LANIS static source filtering table
-- table is optional


isarIlanisStatSrcFilterTable OBJECT-TYPE
    SYNTAX  SEQUENCE OF IsarIlanisStatSrcFilterEntry
    ACCESS  not-accessible
    STATUS  mandatory
    DESCRIPTION
           "This table contains the MAC addresses for which bridging
            is disabled at the LAN side."
    ::= { isarIlanisMIBObjects  1 }

isarIlanisStatSrcFilterEntry OBJECT-TYPE
    SYNTAX  IsarIlanisStatSrcFilterEntry
    ACCESS  not-accessible
    STATUS  mandatory
    DESCRIPTION
           "One row in the isarIlanisStatSrcFilterTable."
    INDEX   { isarIlanisStatSrcFilterServiceIndex,
              isarIlanisStatSrcFilterAddress
            }
    ::= { isarIlanisStatSrcFilterTable  1 }


IsarIlanisStatSrcFilterEntry ::=
    SEQUENCE { 
      isarIlanisStatSrcFilterServiceIndex
        INTEGER,
        
      isarIlanisStatSrcFilterAddress
        OCTET STRING,
        
      isarIlanisStatSrcFilterRowStatus
        INTEGER

    }
    
isarIlanisStatSrcFilterServiceIndex OBJECT-TYPE
    SYNTAX  INTEGER
    ACCESS  read-only
    STATUS  mandatory
    DESCRIPTION
           "The index of the service to which this address belongs.
            This is the same index as serviceIndex of isarIserviceTable."
    ::= { isarIlanisStatSrcFilterEntry  1 }

isarIlanisStatSrcFilterAddress OBJECT-TYPE
    SYNTAX  OCTET STRING (SIZE (6))
    ACCESS  read-write
    STATUS  mandatory
    DESCRIPTION
           "The MAC address for which bridging is disabled
            at the LANside.
            It is allowed to modify the address.
            The SNMPv2 MAX-ACCESS is read-create."
    ::= { isarIlanisStatSrcFilterEntry 2 }

isarIlanisStatSrcFilterRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIlanisStatSrcFilterEntry  3 }



-- LANIS protocol filtering table
-- table is optional


isarIlanisProtocolFilterTable OBJECT-TYPE
    SYNTAX  SEQUENCE OF IsarIlanisProtocolFilterEntry
    ACCESS  not-accessible
    STATUS  mandatory
    DESCRIPTION
           "This table contains the protocols for which bridging
            is disabled ."
    ::= { isarIlanisMIBObjects  2 }

isarIlanisProtocolFilterEntry OBJECT-TYPE
    SYNTAX  IsarIlanisProtocolFilterEntry
    ACCESS  not-accessible
    STATUS  mandatory
    DESCRIPTION
           "One row in the isarIlanisProtocolFilterTable."
    INDEX   { isarIlanisProtocolFilterServiceIndex,
              isarIlanisProtocolFilterProtocol
            }
    ::= { isarIlanisProtocolFilterTable  1 }


IsarIlanisProtocolFilterEntry ::=
    SEQUENCE { 
      isarIlanisProtocolFilterServiceIndex
        INTEGER,
        
      isarIlanisProtocolFilterProtocol
        INTEGER,
        
      isarIlanisProtocolFilterRowStatus
        INTEGER

    }
    
isarIlanisProtocolFilterServiceIndex OBJECT-TYPE
    SYNTAX  INTEGER
    ACCESS  read-only
    STATUS  mandatory
    DESCRIPTION
           "The index of the service to which this protocol belongs.
            This is the same index as serviceIndex of isarIserviceTable."
    ::= { isarIlanisProtocolFilterEntry  1 }

isarIlanisProtocolFilterProtocol OBJECT-TYPE
    SYNTAX  INTEGER {
                      ip(2048),
                      arp(2054),
                      rarp(32821)
            }
    ACCESS  read-only
    STATUS  mandatory
    DESCRIPTION
           "The protocol for which bridging is disabled.
            Possible protocols : IP (= 0800H), ARP (= 0806H),
            RARP (= 8035H).
            The SNMPv2 MAX-ACCESS is read-create."
    ::= { isarIlanisProtocolFilterEntry 2 }

isarIlanisProtocolFilterRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIlanisProtocolFilterEntry  3 }


-- LANIS interworking function table
-- table is optional


isarIlanisIwfTable OBJECT-TYPE
    SYNTAX  SEQUENCE OF IsarIlanisIwfEntry
    ACCESS  not-accessible
    STATUS  mandatory
    DESCRIPTION
           "This table contains the LANIS interworking.
            When a row in this table is created, an entry in the
            isarIlanisIwfMappingTable is made by IAD4700 (inverse mapping
            of index).
            
            At the same time another table must be updated :
             - set field isarIatmVclCrossConnectIdentifier of the 
               corresponding entry in IsarIatmVclEntry with the
               value of isarIlanisIwfConnIndex and
             - set field isarIatmVclServiceType of the 
               corresponding entry in IsarIatmVclEntry to 'lanis'."
    ::= { isarIlanisMIBObjects  3 }

isarIlanisIwfEntry OBJECT-TYPE
    SYNTAX  IsarIlanisIwfEntry
    ACCESS  not-accessible
    STATUS  mandatory
    DESCRIPTION
           "One row in the isarIlanisIwfTable."
    INDEX   { isarIlanisIwfServiceIndex,
              isarIlanisIwfPortNumber
            }
    ::= { isarIlanisIwfTable  1 }


IsarIlanisIwfEntry ::=
    SEQUENCE { 
      isarIlanisIwfServiceIndex
        INTEGER,

      isarIlanisIwfConnIndex
        INTEGER,        

      isarIlanisIwfPortNumber
        INTEGER,

      isarIlanisIwfAtmIfIndex
        INTEGER,

      isarIlanisIwfAtmVpi
        INTEGER,

      isarIlanisIwfAtmVci
        INTEGER,

      isarIlanisIwfAdminStatus
        INTEGER,

      isarIlanisIwfOperStatus
        INTEGER,

      isarIlanisIwfRowStatus
        INTEGER

    }
    
isarIlanisIwfServiceIndex OBJECT-TYPE
    SYNTAX  INTEGER
    ACCESS  read-only
    STATUS  mandatory
    DESCRIPTION
           "The index of the service to which this interworking function
            belongs.
            This is the same index as serviceIndex of isarIserviceTable."
    ::= { isarIlanisIwfEntry  1 }

isarIlanisIwfConnIndex OBJECT-TYPE
    SYNTAX  INTEGER
    ACCESS  read-only
    STATUS  mandatory
    DESCRIPTION
           "The value of this object is equal to the 
            isarIiwfNextConnIndex obtained (by IAD4700) to uniqely identify
            this IWF."
    ::= { isarIlanisIwfEntry  2 }

isarIlanisIwfPortNumber OBJECT-TYPE
    SYNTAX  INTEGER (1..64)
    ACCESS  read-only
    STATUS  mandatory
    DESCRIPTION
           "The port number of this ATMport."
    ::= { isarIlanisIwfEntry 3 }

isarIlanisIwfAtmIfIndex OBJECT-TYPE
    SYNTAX  INTEGER
    ACCESS  read-write
    STATUS  mandatory
    DESCRIPTION
           "The ifIndex of the ATM interface of this interworking 
            function.
            (it must be possible to add rows but it must be 
            impossible to modify this index)
            The SNMPv2 MAX-ACCESS is read-create."
    ::= { isarIlanisIwfEntry  4 }

isarIlanisIwfAtmVpi OBJECT-TYPE
    SYNTAX  INTEGER (0..4095)
    ACCESS  read-write
    STATUS  mandatory
    DESCRIPTION
           "The VPI value of the VCL used for this interworking 
            function.
            (it must be possible to add rows but it must be 
            impossible to modify this index)
            The SNMPv2 MAX-ACCESS is read-create."
    ::= { isarIlanisIwfEntry  5 }

isarIlanisIwfAtmVci OBJECT-TYPE
    SYNTAX  INTEGER (0..65535)
    ACCESS  read-write
    STATUS  mandatory
    DESCRIPTION
           "The VCI value of the VCL used for this interworking 
            function.
            (it must be possible to add rows but it must be 
            impossible to modify this index)
            The SNMPv2 MAX-ACCESS is read-create."
    ::= { isarIlanisIwfEntry  6 }

isarIlanisIwfAdminStatus OBJECT-TYPE
    SYNTAX  INTEGER {
                      up(1),
                      down(2)
            }
    ACCESS  read-write
    STATUS  mandatory
    DESCRIPTION
           "The administrative state of the interworking function.
            The SNMPv2 MAX-ACCESS is read-create."
    DEFVAL { down }
    ::= { isarIlanisIwfEntry 7 }

isarIlanisIwfOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "The operational state of the interworking function.
            Refer to RFC 2233 for more info."
    ::= { isarIlanisIwfEntry 8 }


isarIlanisIwfRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIlanisIwfEntry  9 }



-- lanisIwf Mapping

isarIlanisIwfMappingTable OBJECT-TYPE
    SYNTAX  SEQUENCE OF IsarIlanisIwfMappingEntry
    ACCESS  not-accessible
    STATUS  mandatory
    DESCRIPTION
           "The lanisIwf mapping table is used to map the IWF index
            into the index of the corresponding entry in the
            isarIlanisIwfTable."
    ::= { isarIlanisMIBObjects  4 }

isarIlanisIwfMappingEntry OBJECT-TYPE
    SYNTAX  IsarIlanisIwfMappingEntry
    ACCESS  not-accessible
    STATUS  mandatory
    DESCRIPTION
           "An entry in the lanisIwf mapping table."
    INDEX   { isarIlanisIwfConnIndex }
    ::= { isarIlanisIwfMappingTable  1 }

IsarIlanisIwfMappingEntry ::=
    SEQUENCE {
      isarIlanisIwfMapServiceIndex
        INTEGER,

      isarIlanisIwfMapPortNumber
        INTEGER

    }

isarIlanisIwfMapServiceIndex OBJECT-TYPE
    SYNTAX  INTEGER
    ACCESS  read-only
    STATUS  mandatory
    DESCRIPTION
           "Mapped index."
    ::= { isarIlanisIwfMappingEntry  1 }

isarIlanisIwfMapPortNumber OBJECT-TYPE
    SYNTAX  INTEGER (1..64)
    ACCESS  read-only
    STATUS  mandatory
    DESCRIPTION
           "Mapped index."
    ::= { isarIlanisIwfMappingEntry  2 }



-- tables for SDSL

isarIarpDestinationTable OBJECT-TYPE
    SYNTAX  SEQUENCE OF IsarIarpDestinationEntry
    ACCESS  not-accessible
    STATUS  mandatory
    DESCRIPTION
           "This table contains a list of destination IP addresses for which 
            ARP messages may be passed to the aggregate side."
    ::= { isarIlanisMIBObjects  5 }

isarIarpDestinationEntry OBJECT-TYPE
    SYNTAX  IsarIarpDestinationEntry
    ACCESS  not-accessible
    STATUS  mandatory
    DESCRIPTION
           "One row in the isarIarpDestinationTable."
    INDEX   { isarIarpDestinationServiceIndex,
              isarIarpDestinationIpAddress
            }
    ::= { isarIarpDestinationTable  1 }


IsarIarpDestinationEntry ::=
    SEQUENCE { 
      isarIarpDestinationServiceIndex
        INTEGER,
        
      isarIarpDestinationIpAddress
        IpAddress,
        
      isarIarpDestinationRowStatus
        INTEGER

    }
    
isarIarpDestinationServiceIndex OBJECT-TYPE
    SYNTAX  INTEGER
    ACCESS  read-only
    STATUS  mandatory
    DESCRIPTION
           "The index of the service to which this address belongs.
            This is the same index as serviceIndex of isarIserviceTable."
    ::= { isarIarpDestinationEntry  1 }

isarIarpDestinationIpAddress OBJECT-TYPE
    SYNTAX  IpAddress
    ACCESS  read-only
    STATUS  mandatory
    DESCRIPTION
           "The IP address for which ARP messages may be passed to the 
           aggregate side."
    ::= { isarIarpDestinationEntry 2 }

isarIarpDestinationRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIarpDestinationEntry  3 }




isarIipAccessTable OBJECT-TYPE
    SYNTAX  SEQUENCE OF IsarIipAccessEntry
    ACCESS  not-accessible
    STATUS  mandatory
    DESCRIPTION
           "This table contains a list of source IP addresses 
            and a subnet mask.  Entries will be used to forward 
            IP pakages from drop side to aggregate side."
    ::= { isarIlanisMIBObjects  6 }

isarIipAccessEntry OBJECT-TYPE
    SYNTAX  IsarIipAccessEntry
    ACCESS  not-accessible
    STATUS  mandatory
    DESCRIPTION
           "One row in the isarIipAccessTable."
    INDEX   { isarIipAccessServiceIndex,
              isarIipAccessIpAddress
            }
    ::= { isarIipAccessTable  1 }


IsarIipAccessEntry ::=
    SEQUENCE { 
      isarIipAccessServiceIndex
        INTEGER,
        
      isarIipAccessIpAddress
        IpAddress,
        
      isarIipAccessSubnetMask
        IpAddress,
        
      isarIipAccessRowStatus
        INTEGER

    }
    
isarIipAccessServiceIndex OBJECT-TYPE
    SYNTAX  INTEGER
    ACCESS  read-only
    STATUS  mandatory
    DESCRIPTION
           "The index of the service to which this address belongs.
            This is the same index as serviceIndex of isarIserviceTable."
    ::= { isarIipAccessEntry  1 }

isarIipAccessIpAddress OBJECT-TYPE
    SYNTAX  IpAddress
    ACCESS  read-only
    STATUS  mandatory
    DESCRIPTION
           "A subnet or host IP address."
    ::= { isarIipAccessEntry 2 }

isarIipAccessSubnetMask OBJECT-TYPE
    SYNTAX  IpAddress
    ACCESS  read-write
    STATUS  mandatory
    DESCRIPTION
           "The subnet mask.
            Modification of this values is not allowed."
    ::= { isarIipAccessEntry 3 }

isarIipAccessRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIipAccessEntry  4 }




-- trap defined in isarIiwfMIBObjects

--
-- ISAR lanisMIBObjects : end
--




-- This file cannot be used to create SNMP agent.
-- The file isarOneFile.my has to be used to create the agent.


-- isarIthdlcsMIBObjects       OBJECT IDENTIFIER ::= { isar  17 }


--
-- ISAR thdlcsMIBObjects : begin
--
-- enterprise MIB for ISAR
-- The MIB is written for SNMPv1.


-- THDLCS interworking function table
-- table is optional


isarIthdlcsIwfTable OBJECT-TYPE
    SYNTAX  SEQUENCE OF IsarIthdlcsIwfEntry
    ACCESS  not-accessible
    STATUS  mandatory
    DESCRIPTION
           "This table contains the THDLCS interworking functions
            present in the system.
            It must be possible to dynamically add and delete entries.
            Addition (or deletion) of an entry will automatically add
            (or delete) a corresponding entry in the 
            isarIthdlcsIwfStatsTable.

            When a row in this table is created, an entry in the
            isarIthdlcsIwfMappingTable is made by IAD4700 (inverse mapping
            of index).
            
            At the same time another table must be updated :
             - set field isarIatmVclCrossConnectIdentifier of the 
               corresponding entry in IsarIatmVclEntry with the
               value of isarIthdlcsIwfConnIndex and
             - set field isarIatmVclServiceType of the 
               corresponding entry in IsarIatmVclEntry to 'thdlcs'."
    ::= { isarIthdlcsMIBObjects  1 }

isarIthdlcsIwfEntry OBJECT-TYPE
    SYNTAX  IsarIthdlcsIwfEntry
    ACCESS  not-accessible
    STATUS  mandatory
    DESCRIPTION
           "One row in the isarIthdlcsIwfTable."
    INDEX   { isarIthdlcsIwfServiceIndex, isarIthdlcsIwfHdlcIfIndex }
    ::= { isarIthdlcsIwfTable  1 }


IsarIthdlcsIwfEntry ::=
    SEQUENCE { 
      isarIthdlcsIwfServiceIndex
        INTEGER,
        
      isarIthdlcsIwfConnIndex
        INTEGER,
        
      isarIthdlcsIwfHdlcIfIndex
        INTEGER,

      isarIthdlcsIwfAtmIfIndex
        INTEGER,

      isarIthdlcsIwfAtmVpi
        INTEGER,

      isarIthdlcsIwfAtmVci
        INTEGER,

      isarIthdlcsIwfAdminStatus
        INTEGER,

      isarIthdlcsIwfOperStatus
        INTEGER,

      isarIthdlcsIwfRowStatus
        INTEGER

    }
    
isarIthdlcsIwfServiceIndex OBJECT-TYPE
    SYNTAX  INTEGER
    ACCESS  read-only
    STATUS  mandatory
    DESCRIPTION
           "The index of the service to which this interworking function
            belongs.
            This is the same index as serviceIndex of isarIserviceTable."
    ::= { isarIthdlcsIwfEntry  1 }

isarIthdlcsIwfConnIndex OBJECT-TYPE
    SYNTAX  INTEGER
    ACCESS  read-only
    STATUS  mandatory
    DESCRIPTION
           "The value of this object is equal to the 
            isarIiwfNextConnIndex obtained (by IAD4700) to uniqely identify 
            this IWF."
    ::= { isarIthdlcsIwfEntry  2 }

isarIthdlcsIwfHdlcIfIndex OBJECT-TYPE
    SYNTAX  INTEGER
    ACCESS  read-only
    STATUS  mandatory
    DESCRIPTION
           "The ifIndex of the logical HDLC-port of this interworking 
            function (index of isarIhdlcLogPortMappingTable).
            The SNMPv2 MAX-ACCESS is read-create."
    ::= { isarIthdlcsIwfEntry  3 }

isarIthdlcsIwfAtmIfIndex OBJECT-TYPE
    SYNTAX  INTEGER
    ACCESS  read-write
    STATUS  mandatory
    DESCRIPTION
           "The ifIndex of the ATM interface of this interworking 
            function.
            (it must be possible to add rows but it must be 
            impossible to modify this index)
            The SNMPv2 MAX-ACCESS is read-create."
    ::= { isarIthdlcsIwfEntry  4 }

isarIthdlcsIwfAtmVpi OBJECT-TYPE
    SYNTAX  INTEGER (0..4095)
    ACCESS  read-write
    STATUS  mandatory
    DESCRIPTION
           "The VPI value of the VCL used for this interworking 
            function.
            (it must be possible to add rows but it must be 
            impossible to modify this index)
            The SNMPv2 MAX-ACCESS is read-create."
    ::= { isarIthdlcsIwfEntry  5 }

isarIthdlcsIwfAtmVci OBJECT-TYPE
    SYNTAX  INTEGER (0..65535)
    ACCESS  read-write
    STATUS  mandatory
    DESCRIPTION
           "The VCI value of the VCL used for this interworking 
            function.
            (it must be possible to add rows but it must be 
            impossible to modify this index)
            The SNMPv2 MAX-ACCESS is read-create."
    ::= { isarIthdlcsIwfEntry  6 }

isarIthdlcsIwfAdminStatus OBJECT-TYPE
    SYNTAX  INTEGER {
                      up(1),
                      down(2)
            }
    ACCESS  read-write
    STATUS  mandatory
    DESCRIPTION
           "The administrative state of the interworking function.
            The SNMPv2 MAX-ACCESS is read-create."
    DEFVAL { down }
    ::= { isarIthdlcsIwfEntry 7 }

isarIthdlcsIwfOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "The operational state of the interworking function.
            Refer to RFC 2233 for the different states."
    ::= { isarIthdlcsIwfEntry 8 }


isarIthdlcsIwfRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIthdlcsIwfEntry  9 }



-- thdlcs iwf mapping

isarIthdlcsIwfMappingTable OBJECT-TYPE
    SYNTAX  SEQUENCE OF IsarIthdlcsIwfMappingEntry
    ACCESS  not-accessible
    STATUS  mandatory
    DESCRIPTION
           "The thdlcsIwf mapping table is used to map the IWF index
            into the index of the corresponding entry in the
            isarIthdlcsIwfTable."
    ::= { isarIthdlcsMIBObjects  2 }

isarIthdlcsIwfMappingEntry OBJECT-TYPE
    SYNTAX  IsarIthdlcsIwfMappingEntry
    ACCESS  not-accessible
    STATUS  mandatory
    DESCRIPTION
           "An entry in the thdlcsIwf mapping table."
    INDEX   { isarIthdlcsIwfConnIndex }
    ::= { isarIthdlcsIwfMappingTable  1 }

IsarIthdlcsIwfMappingEntry ::=
    SEQUENCE {
      isarIthdlcsIwfMapServiceIndex
        INTEGER,

      isarIthdlcsIwfMapHdlcIfIndex
        INTEGER

    }

isarIthdlcsIwfMapServiceIndex OBJECT-TYPE
    SYNTAX  INTEGER
    ACCESS  read-only
    STATUS  mandatory
    DESCRIPTION
           "Mapped index."
    ::= { isarIthdlcsIwfMappingEntry  1 }

isarIthdlcsIwfMapHdlcIfIndex OBJECT-TYPE
    SYNTAX  INTEGER
    ACCESS  read-only
    STATUS  mandatory
    DESCRIPTION
           "Mapped index."
    ::= { isarIthdlcsIwfMappingEntry  2 }




-- THDLCS interworking function statistics table
-- table is optional


isarIthdlcsIwfStatsTable OBJECT-TYPE
    SYNTAX  SEQUENCE OF IsarIthdlcsIwfStatsEntry
    ACCESS  not-accessible
    STATUS  mandatory
    DESCRIPTION
           "This table contains the statistic about the THDLCS 
            interworking functions.
            Creation and deletion of entries is coupled with the 
            isarIthdlcsIwfTable."
    ::= { isarIthdlcsMIBObjects  3 }

isarIthdlcsIwfStatsEntry OBJECT-TYPE
    SYNTAX  IsarIthdlcsIwfStatsEntry
    ACCESS  not-accessible
    STATUS  mandatory
    DESCRIPTION
           "One row in the isarIthdlcsIwfStatsTable."
    INDEX   { isarIthdlcsIwfStatsServiceIndex,
              isarIthdlcsIwfStatsHdlcIfIndex }
    ::= { isarIthdlcsIwfStatsTable  1 }


IsarIthdlcsIwfStatsEntry ::=
    SEQUENCE { 
      isarIthdlcsIwfStatsServiceIndex
        INTEGER,
        
      isarIthdlcsIwfStatsHdlcIfIndex
        INTEGER,

      isarIthdlcsIwfStatsDsToAsTransmFrames
        Counter,

      isarIthdlcsIwfStatsAsToDsTransmFrames
        Counter,

      isarIthdlcsIwfStatsDsToAsDroppedFrames
        Counter,

      isarIthdlcsIwfStatsAsToDsDroppedFrames
        Counter
    }
    
isarIthdlcsIwfStatsServiceIndex OBJECT-TYPE
    SYNTAX  INTEGER
    ACCESS  read-only
    STATUS  mandatory
    DESCRIPTION
           "The index of the service to which this interworking function
            belongs.
            This is the same index as serviceIndex of isarIserviceTable."
    ::= { isarIthdlcsIwfStatsEntry  1 }

isarIthdlcsIwfStatsHdlcIfIndex OBJECT-TYPE
    SYNTAX  INTEGER
    ACCESS  read-only
    STATUS  mandatory
    DESCRIPTION
           "The ifIndex of the logical HDLC-port of this interworking 
            function."
    ::= { isarIthdlcsIwfStatsEntry  2 }

isarIthdlcsIwfStatsDsToAsTransmFrames OBJECT-TYPE
    SYNTAX  Counter
    ACCESS  read-only
    STATUS  mandatory
    DESCRIPTION
           "The number of frames that have been received from the drop
            side and have been sent to the aggregate side by this
            interworking function."
    ::= { isarIthdlcsIwfStatsEntry  3 }

isarIthdlcsIwfStatsAsToDsTransmFrames OBJECT-TYPE
    SYNTAX  Counter
    ACCESS  read-only
    STATUS  mandatory
    DESCRIPTION
           "The number of frames that have been received from the 
            aggregate side and have been sent to the drop side by this
            interworking function."
    ::= { isarIthdlcsIwfStatsEntry  4 }

isarIthdlcsIwfStatsDsToAsDroppedFrames OBJECT-TYPE
    SYNTAX  Counter
    ACCESS  read-only
    STATUS  mandatory
    DESCRIPTION
           "The number of frames that have been received from the drop
            side and have been dropped by the store and forward function."
    ::= { isarIthdlcsIwfStatsEntry  5 }

isarIthdlcsIwfStatsAsToDsDroppedFrames OBJECT-TYPE
    SYNTAX  Counter
    ACCESS  read-only
    STATUS  mandatory
    DESCRIPTION
           "The number of frames that have been received from the 
            aggregate side and have been dropped by the store and forward
            function."
    ::= { isarIthdlcsIwfStatsEntry  6 }



-- trap defined in isarIiwfMIBObjects

--
-- ISAR thdlcsMIBObjects : end
--




-- This file cannot be used to create SNMP agent.
-- The file isarOneFile.my has to be used to create the agent.


-- isarItraceHandlerMIBObjects      OBJECT IDENTIFIER ::= { isar  18 }


--
-- ISAR traceHandlerMIBObjects : begin
--
-- enterprise MIB for ISAR
-- The MIB is written for SNMPv1.

--
-- ISAR trace handler
--



isarIlockedForRead OBJECT-TYPE
    SYNTAX  INTEGER { 
                      true(1), 
                      false(2) 
            }
    ACCESS  read-write
    STATUS  mandatory
    DESCRIPTION
           "Indicates if the trace buffer is currently locked for 
            reading. If locked, new arriving trace messages are dropped
            (not put into the trace buffer). 
            When the value is set from true to false, a check has to be
            made to verify that the same snmp manager is resetting the
            value. There are three possible ways this variable can be set
            to false.
            a. set to false by the same manager who set it previously to
               true,
            b. automatically when during sequential get, the trace buffer
               is sent completely,
            c. via a time out in order not to block the trace buffer
               indefinite."
    ::= { isarItraceHandlerMIBObjects  1 }

isarIlostTraces OBJECT-TYPE
    SYNTAX  Counter
    ACCESS  read-only
    STATUS  mandatory
    DESCRIPTION
           "Gives the number of trace messages lost during the current
            locked period.  The value should be 0 as long as 
            isarIlockedForRead is false."
    ::= { isarItraceHandlerMIBObjects  2 }

isarIclearTraceBuffer OBJECT-TYPE
    SYNTAX  INTEGER { 
                      true(1), 
                      false(2) 
            }
    ACCESS  read-write
    STATUS  mandatory
    DESCRIPTION
           "Set to true removes current content of the trace buffer.
            'Get' always returns false."
    ::= { isarItraceHandlerMIBObjects  3 }




isarItraceUdpObjects   OBJECT IDENTIFIER 
                             ::= { isarItraceHandlerMIBObjects  5 }

isarItraceUdp OBJECT-TYPE
    SYNTAX  INTEGER { 
                      enabled(1), 
                      disabled(2) 
            }
    ACCESS  read-write
    STATUS  mandatory
    DESCRIPTION
           "When this field is set to 'enabled' then traces are sent 
            via a dedicated connection (e.g. a specific socket 
            connection) configurable via the maintenance interface (IP 
            addrss, port number).  As transport protocol UDP is used to
            minimise additional load.
            isarItraceUdpPortNo and isarItraceUdpIpAddr must be filled
            in when isarItraceUdp is set to 'enabled'."
    ::= { isarItraceUdpObjects  1 }

isarItraceUdpPortNo OBJECT-TYPE
    SYNTAX  INTEGER (1..65535)
    ACCESS  read-write
    STATUS  mandatory
    DESCRIPTION
           "Port number that will be used when isarItraceUdp is set to
            'enabled'."
    ::= { isarItraceUdpObjects  2 }

isarItraceUdpIpAddr OBJECT-TYPE
    SYNTAX  IpAddress
    ACCESS  read-write
    STATUS  mandatory
    DESCRIPTION
           "IP address that will be used when isarItraceUdp is set to
            'enabled'."
    ::= { isarItraceUdpObjects  3 }



isarItraceSelectors   OBJECT IDENTIFIER 
                             ::= { isarItraceHandlerMIBObjects  6 }

-- REMARK : the trace selectors for CCC are incorporated in the CCC MIB


isarItraceAll OBJECT-TYPE
    SYNTAX  INTEGER { 
                      true(1), 
                      false(2) 
            }
    ACCESS  read-write
    STATUS  optional
    DESCRIPTION
           "When this object is set to 'true' then all events (except
            the real-time events) are traced.  From this moment on, the 
            value of the different selectors (except the *Sff selectors)
            are ignored (but not changed).
            Tracing is done again via the different selectors when this
            object is set from 'true' to 'false'."
    DEFVAL { false }
    ::= { isarItraceSelectors  1 }

isarItraceNC OBJECT-TYPE
    SYNTAX  INTEGER { 
                      true(1), 
                      false(2) 
            }
    ACCESS  read-write
    STATUS  optional
    DESCRIPTION
           "Setting this object to 'true' activates the sending of 
            trace events by the NC layer.  It almost has the same effect
            as setting the following trace selectors to 'true':
               isarItraceAal1Processor (FW is also traced)
               isarItraceAal5Processor
               isarItraceCbrProcessor
               isarItraceSpeechProcessor
               isarItraceAtmLayer
               isarItraceE1T1Port
               isarItraceHssiPort
               isarItraceImaGroup
               isarItraceLanPort
               isarItraceQmc
               isarItraceCommon
               isarItraceStm1Port
               isarItraceTss (FW is also traced)
               isarItraceS0
               isarItraceSdsl.
            The value of these selectors is not influenced by the value
            of isarItraceNC.
            Tracing is done again via the different selectors when this
            object is set from 'true' to 'false'."
    DEFVAL { false }
    ::= { isarItraceSelectors  2 }

isarItraceAal1Processor OBJECT-TYPE
    SYNTAX  INTEGER { 
                      true(1), 
                      false(2) 
            }
    ACCESS  read-write
    STATUS  optional
    DESCRIPTION
           "Setting this object to 'true' activates the sending of 
            trace events by the Aal1Processor. Setting it back to 'false'
            de-activates the sending of the events."
    DEFVAL { false }
    ::= { isarItraceSelectors  3 }

isarItraceAal5Processor OBJECT-TYPE
    SYNTAX  INTEGER { 
                      true(1), 
                      false(2) 
            }
    ACCESS  read-write
    STATUS  optional
    DESCRIPTION
           "Setting this object to 'true' activates the sending of 
            trace events by the Aal5Processor. Setting it back to 'false'
            de-activates the sending of the events."
    DEFVAL { false }
    ::= { isarItraceSelectors  4 }

isarItraceCbrProcessor OBJECT-TYPE
    SYNTAX  INTEGER { 
                      true(1), 
                      false(2) 
            }
    ACCESS  read-write
    STATUS  optional
    DESCRIPTION
           "Setting this object to 'true' activates the sending of 
            trace events by the CbrProcessor. Setting it back to 'false'
            de-activates the sending of the events."
    DEFVAL { false }
    ::= { isarItraceSelectors  5 }

isarItraceSpeechProcessor OBJECT-TYPE
    SYNTAX  INTEGER { 
                      true(1), 
                      false(2) 
            }
    ACCESS  read-write
    STATUS  optional
    DESCRIPTION
           "Setting this object to 'true' activates the sending of 
            trace events by the SpeechProcessor.  Setting it back to 
            'false' de-activates the sending of the events."
    DEFVAL { false }
    ::= { isarItraceSelectors  6 }

isarItraceAtmLayer OBJECT-TYPE
    SYNTAX  INTEGER { 
                      true(1), 
                      false(2) 
            }
    ACCESS  read-write
    STATUS  optional
    DESCRIPTION
           "Setting this object to 'true' activates the sending of 
            trace events by the ATM layer.  Setting it back to 'false'
            de-activates the sending of the events."
    DEFVAL { false }
    ::= { isarItraceSelectors  7 }

isarItraceE1T1Port OBJECT-TYPE
    SYNTAX  INTEGER { 
                      true(1), 
                      false(2) 
            }
    ACCESS  read-write
    STATUS  optional
    DESCRIPTION
           "Setting this object to 'true' activates the sending of 
            trace events by the E1/T1 Port.  Setting it back to 'false'
            de-activates the sending of the events."
    DEFVAL { false }
    ::= { isarItraceSelectors  8 }

isarItraceHssiPort OBJECT-TYPE
    SYNTAX  INTEGER { 
                      true(1), 
                      false(2) 
            }
    ACCESS  read-write
    STATUS  optional
    DESCRIPTION
           "Setting this object to 'true' activates the sending of 
            trace events by the HSSI Port.  Setting it back to 'false'
            de-activates the sending of the events."
    DEFVAL { false }
    ::= { isarItraceSelectors  9 }

isarItraceImaGroup OBJECT-TYPE
    SYNTAX  INTEGER { 
                      true(1), 
                      false(2) 
            }
    ACCESS  read-write
    STATUS  optional
    DESCRIPTION
           "Setting this object to 'true' activates the sending of 
            trace events by the IMA Group.  Setting it back to 'false'
            de-activates the sending of the events."
    DEFVAL { false }
    ::= { isarItraceSelectors  10 }

isarItraceLanPort OBJECT-TYPE
    SYNTAX  INTEGER { 
                      true(1), 
                      false(2) 
            }
    ACCESS  read-write
    STATUS  optional
    DESCRIPTION
           "Setting this object to 'true' activates the sending of 
            trace events by the LAN Port.  Setting it back to 'false'
            de-activates the sending of the events."
    DEFVAL { false }
    ::= { isarItraceSelectors  11 }

isarItraceQmc OBJECT-TYPE
    SYNTAX  INTEGER { 
                      true(1), 
                      false(2) 
            }
    ACCESS  read-write
    STATUS  optional
    DESCRIPTION
           "Setting this object to 'true' activates the sending of 
            trace events by the QMC.  Setting it back to 'false'
            de-activates the sending of the events."
    DEFVAL { false }
    ::= { isarItraceSelectors  12 }

isarItraceCommon OBJECT-TYPE
    SYNTAX  INTEGER { 
                      true(1), 
                      false(2) 
            }
    ACCESS  read-write
    STATUS  optional
    DESCRIPTION
           "Setting this object to 'true' activates the sending of 
            trace events by the Common part.  Setting it back to 'false'
            de-activates the sending of the events."
    DEFVAL { false }
    ::= { isarItraceSelectors  13 }

isarItraceTss OBJECT-TYPE
    SYNTAX  INTEGER { 
                      true(1), 
                      false(2) 
            }
    ACCESS  read-write
    STATUS  optional
    DESCRIPTION
           "Setting this object to 'true' activates the sending of 
            trace events by the TSS.  Setting it back to 'false'
            de-activates the sending of the events."
    DEFVAL { false }
    ::= { isarItraceSelectors  14 }

isarItraceOam OBJECT-TYPE
    SYNTAX  INTEGER { 
                      true(1), 
                      false(2) 
            }
    ACCESS  read-write
    STATUS  optional
    DESCRIPTION
           "Setting this object to 'true' activates the sending of 
            trace events by the OAM part.  Setting it back to 'false'
            de-activates the sending of the events."
    DEFVAL { false }
    ::= { isarItraceSelectors  15 }

isarItraceAP OBJECT-TYPE
    SYNTAX  INTEGER { 
                      true(1), 
                      false(2) 
            }
    ACCESS  read-write
    STATUS  optional
    DESCRIPTION
           "Setting this object to 'true' activates the sending of 
            trace events by the AP layer.  It has the same effect as 
            setting the following trace selectors to 'true':
               isarItraceCes
               isarItraceFrs
               isarItraceThdlcs
               isarItraceVcs
               isarItraceLanis
               isarItraceSignalling.
            The value of these selectors is not influenced by the value
            of isarItraceAP.
            Tracing is done again via the different selectors when this
            object is set from 'true' to 'false'."
    DEFVAL { false }
    ::= { isarItraceSelectors  16 }

isarItraceCes OBJECT-TYPE
    SYNTAX  INTEGER { 
                      true(1), 
                      false(2) 
            }
    ACCESS  read-write
    STATUS  optional
    DESCRIPTION
           "Setting this object to 'true' activates the sending of
            trace events concerning a Circuit Emulation Service.
            Setting it back to 'false' de-activates the sending of 
            the events."
    DEFVAL { false }
    ::= { isarItraceSelectors  17 }

isarItraceFrs OBJECT-TYPE
    SYNTAX  INTEGER { 
                      true(1), 
                      false(2) 
            }
    ACCESS  read-write
    STATUS  optional
    DESCRIPTION
           "Setting this object to 'true' activates the sending of
            trace events concerning a Frame Relay Service.
            Setting it back to 'false' de-activates the sending of 
            the events."
    DEFVAL { false }
    ::= { isarItraceSelectors  18 }

isarItraceThdlcs OBJECT-TYPE
    SYNTAX  INTEGER { 
                      true(1), 
                      false(2) 
            }
    ACCESS  read-write
    STATUS  optional
    DESCRIPTION
           "Setting this object to 'true' activates the sending of
            trace events concerning a Transparent HDLC Service.
            Setting it back to 'false' de-activates the sending of 
            the events."
    DEFVAL { false }
    ::= { isarItraceSelectors  19 }

isarItraceVcs OBJECT-TYPE
    SYNTAX  INTEGER { 
                      true(1), 
                      false(2) 
            }
    ACCESS  read-write
    STATUS  optional
    DESCRIPTION
           "Setting this object to 'true' activates the sending of
            trace events concerning a Voice compression service.
            Setting it back to 'false' de-activates the sending of 
            the events."
    DEFVAL { false }
    ::= { isarItraceSelectors  20 }

isarItraceLanis OBJECT-TYPE
    SYNTAX  INTEGER { 
                      true(1), 
                      false(2) 
            }
    ACCESS  read-write
    STATUS  optional
    DESCRIPTION
           "Setting this object to 'true' activates the sending of
            trace events concerning a LAN Interconnection Service.
            Setting it back to 'false' de-activates the sending of 
            the events."
    DEFVAL { false }
    ::= { isarItraceSelectors  21 }

isarItraceSignalling OBJECT-TYPE
    SYNTAX  INTEGER { 
                      true(1), 
                      false(2) 
            }
    ACCESS  read-write
    STATUS  optional
    DESCRIPTION
           "Setting this object to 'true' activates the sending of 
            trace events concerning a Signalling Service.
            Setting it back to 'false' de-activates the sending of 
            the events."
    DEFVAL { false }
    ::= { isarItraceSelectors  22 }

isarItraceFrsSff OBJECT-TYPE
    SYNTAX  INTEGER { 
                      true(1), 
                      false(2) 
            }
    ACCESS  read-write
    STATUS  optional
    DESCRIPTION
           "Setting this object to 'true' activates the sending of
            trace events concerning FR Service SFF.
            Setting it back to 'false' de-activates the sending of 
            the events."
    DEFVAL { false }
    ::= { isarItraceSelectors  23 }

isarItraceThdlcsSff OBJECT-TYPE
    SYNTAX  INTEGER { 
                      true(1), 
                      false(2) 
            }
    ACCESS  read-write
    STATUS  optional
    DESCRIPTION
           "Setting this object to 'true' activates the sending of
            trace events concerning THDLC Service SFF.
            Setting it back to 'false' de-activates the sending of 
            the events."
    DEFVAL { false }
    ::= { isarItraceSelectors  24 }

isarItraceVcsSff OBJECT-TYPE
    SYNTAX  INTEGER { 
                      true(1), 
                      false(2) 
            }
    ACCESS  read-write
    STATUS  optional
    DESCRIPTION
           "Setting this object to 'true' activates the sending of
            trace events concerning VC Service SFF.
            Setting it back to 'false' de-activates the sending of 
            the events."
    DEFVAL { false }
    ::= { isarItraceSelectors  25 }

isarItraceLanisSff OBJECT-TYPE
    SYNTAX  INTEGER { 
                      true(1), 
                      false(2) 
            }
    ACCESS  read-write
    STATUS  optional
    DESCRIPTION
           "Setting this object to 'true' activates the sending of
            trace events concerning LAN Interconnection Service SFF.
            Setting it back to 'false' de-activates the sending of 
            the events."
    DEFVAL { false }
    ::= { isarItraceSelectors  26 }

isarItraceSignallingSff OBJECT-TYPE
    SYNTAX  INTEGER { 
                      true(1), 
                      false(2) 
            }
    ACCESS  read-write
    STATUS  optional
    DESCRIPTION
           "Setting this object to 'true' activates the sending of
            trace events concerning Signalling Service SFF.
            Setting it back to 'false' de-activates the sending of 
            the events."
    DEFVAL { false }
    ::= { isarItraceSelectors  27 }

isarItraceHeap OBJECT-TYPE
    SYNTAX  INTEGER { 
                      true(1), 
                      false(2) 
            }
    ACCESS  read-write
    STATUS  optional
    DESCRIPTION
           "Setting this object to 'true' activates the sending of
            trace events concerning Heap requests.  Events are only
            sent if a memory pool of a certain block size is exhausted.
            Setting it back to 'false' de-activates the sending of 
            the events."
    DEFVAL { false }
    ::= { isarItraceSelectors  28 }

isarItraceFW OBJECT-TYPE
    SYNTAX  INTEGER { 
                      true(1), 
                      false(2) 
            }
    ACCESS  read-write
    STATUS  optional
    DESCRIPTION
           "Setting this object to 'true' activates the sending of 
            trace events by the FW layer.  It almost has the same effect
            as setting the following trace selectors to 'true':
               isarItraceAal1Processor (NC is also traced)
               isarItraceTss (NC is also traced).
            The value of these selectors is not influenced by the value
            of isarItraceFW.
            Tracing is done again via the different selectors when this
            object is set from 'true' to 'false'."
    DEFVAL { false }
    ::= { isarItraceSelectors  29 }


isarItraceInbandMgmt OBJECT-TYPE
    SYNTAX  INTEGER { 
                      true(1), 
                      false(2) 
            }
    ACCESS  read-write
    STATUS  optional
    DESCRIPTION
           "Setting this object to 'true' activates the sending of
            trace events concerning Inband management.
            Setting it back to 'false' de-activates the sending of 
            the events."
    DEFVAL { false }
    ::= { isarItraceSelectors  30 }

isarItraceInbandMgmtCtrl OBJECT-TYPE
    SYNTAX  INTEGER { 
                      true(1), 
                      false(2) 
            }
    ACCESS  read-write
    STATUS  optional
    DESCRIPTION
           "Setting this object to 'true' activates the sending of
            trace events concerning Inband management control.
            Setting it back to 'false' de-activates the sending of 
            the events."
    DEFVAL { false }
    ::= { isarItraceSelectors  31 }

isarItraceStm1Port OBJECT-TYPE
    SYNTAX  INTEGER { 
                      true(1), 
                      false(2) 
            }
    ACCESS  read-write
    STATUS  optional
    DESCRIPTION
           "Setting this object to 'true' activates the sending of
            trace events concerning Stm1 port.
            Setting it back to 'false' de-activates the sending of 
            the events."
    DEFVAL { false }
    ::= { isarItraceSelectors  32 }

isarItraceS0 OBJECT-TYPE
    SYNTAX  INTEGER { 
                      true(1), 
                      false(2) 
            }
    ACCESS  read-write
    STATUS  optional
    DESCRIPTION
           "Setting this object to 'true' activates the sending of
            trace events concerning S0 port.
            Setting it back to 'false' de-activates the sending of 
            the events."
    DEFVAL { false }
    ::= { isarItraceSelectors  33 }

isarItraceCccConfig OBJECT-TYPE
    SYNTAX  INTEGER { 
                      true(1), 
                      false(2) 
            }
    ACCESS  read-write
    STATUS  optional
    DESCRIPTION
           "Setting this object to 'true' activates the sending of
            trace events concerning CCC configurations (= tracing of
            SNMP SET Requests).
            Setting it back to 'false' de-activates the sending of 
            the events."
    DEFVAL { false }
    ::= { isarItraceSelectors  34 }

-- reserved for Rapm    ::= { isarItraceSelectors  35 }
-- reserved for Rapm    ::= { isarItraceSelectors  36 }

isarItraceSdsl OBJECT-TYPE
    SYNTAX  INTEGER { 
                      true(1), 
                      false(2) 
            }
    ACCESS  read-write
    STATUS  optional
    DESCRIPTION
           "Setting this object to 'true' activates the sending of
            trace events concerning SDSL configurations (= tracing of
            SNMP SET Requests).
            Setting it back to 'false' de-activates the sending of 
            the events."
    DEFVAL { false }
    ::= { isarItraceSelectors  37 }

isarItraceSlottedS0Sff OBJECT-TYPE
    SYNTAX  INTEGER { 
                      true(1), 
                      false(2) 
            }
    ACCESS  read-write
    STATUS  optional
    DESCRIPTION
           "Setting this object to 'true' activates the sending of
            trace events concerning slotted S0 (CES) SFF.
            Setting it back to 'false' de-activates the sending of 
            the events."
    DEFVAL { false }
    ::= { isarItraceSelectors  38 }

isarItraceCesS0Sff OBJECT-TYPE
    SYNTAX  INTEGER { 
                      true(1), 
                      false(2) 
            }
    ACCESS  read-write
    STATUS  optional
    DESCRIPTION
           "Setting this object to 'true' activates the sending of
            trace events concerning CES over S0 SFF.
            Setting it back to 'false' de-activates the sending of 
            the events."
    DEFVAL { false }
    ::= { isarItraceSelectors  39 }


-- ISAR trace handler table


isarItraceHandlerTable OBJECT-TYPE
    SYNTAX  SEQUENCE OF IsarItraceHandlerEntry
    ACCESS  not-accessible
    STATUS  mandatory
    DESCRIPTION
           "."
    ::= { isarItraceHandlerMIBObjects  4 }

isarItraceHandlerEntry OBJECT-TYPE
    SYNTAX  IsarItraceHandlerEntry
    ACCESS  not-accessible
    STATUS  mandatory
    DESCRIPTION
           "One row in the isarItraceHandlerTable."
    INDEX   { isarItraceHandlerIndex }
    ::= { isarItraceHandlerTable  1 }


IsarItraceHandlerEntry ::=
    SEQUENCE { 
      isarItraceHandlerIndex
        INTEGER,
        
      isarItraceHandlerMessage
        OCTET STRING

    }
    
isarItraceHandlerIndex OBJECT-TYPE
    SYNTAX  INTEGER
    ACCESS  not-accessible
    STATUS  mandatory
    DESCRIPTION
           "Dummy index not used to access the table.
            The table will always be sequentially read."
    ::= { isarItraceHandlerEntry  1 }

isarItraceHandlerMessage OBJECT-TYPE
    SYNTAX  OCTET STRING (SIZE (0..300))
    ACCESS  read-only
    STATUS  mandatory
    DESCRIPTION
           "During a 'get', the snmp agent will verify whether the 
            calling manager is the same as the one who has set the
            isarIlockedForRead variable. Each 'get' will return the next
            trace message.  If one needs the first message again, one
            should reset and set the isarIlockedForRead variable.  The
            next 'get' of isarItraceHandlerMessage will then return the
            first trace message again."
    ::= { isarItraceHandlerEntry  2 }

--
-- ISAR traceHandlerMIBObjects : end
--




-- This file cannot be used to create SNMP agent.
-- The file isarOneFile.my has to be used to create the agent.


-- isarIalarmLogMIBObjects      OBJECT IDENTIFIER ::= { isar  19 }


--
-- ISAR alarmLogMIBObjects : begin
--
-- enterprise MIB for ISAR
-- The MIB is written for SNMPv1.

--
-- ISAR alarm log
--


-- severity trap threshold

isarIalarmTrapThreshold OBJECT-TYPE
    SYNTAX  INTEGER (0..3)
    ACCESS  read-write
    STATUS  mandatory
    DESCRIPTION
           "Indicates when an alarm results into a trap 
              0 = only critical alarms generate a trap
              1 = critical and major alarms generate a trap
              2 = critical, major and minor alarms generate a trap
              3 = all alarms generate a trap"
    ::= { isarIalarmLogMIBObjects  4 }

-- highest current severity

isarIcurrentAlarmHighestSeverity OBJECT-TYPE
    SYNTAX  INTEGER { 
                      critical(1), 
                      major(2),
                      minor(3),
                      diagnostic(4) ,
                      none(5)
            }
    ACCESS  read-only
    STATUS  mandatory
    DESCRIPTION
           "Indicates the highest severity in the list of current alarms 
              1 = a critical alarm is present
              2 = a major alarm but no critical alarm is present
              3 = a minor alarm but no critical/major alarm is present
              4 = a diagnostic alarm but no critical/major/minor alarm 
                  is present
              5 = there is no current alarm
            This object is used by the 45020 to determine the color state
            of the system."
    ::= { isarIalarmLogMIBObjects  5 }



-- ISAR alarm log limits table


isarIalarmLogLimTable OBJECT-TYPE
    SYNTAX  SEQUENCE OF IsarIalarmLogLimEntry
    ACCESS  not-accessible
    STATUS  mandatory
    DESCRIPTION
           "."
    ::= { isarIalarmLogMIBObjects  1 }

isarIalarmLogLimEntry OBJECT-TYPE
    SYNTAX  IsarIalarmLogLimEntry
    ACCESS  not-accessible
    STATUS  mandatory
    DESCRIPTION
           "One row in the isarIalarmLogLimTable."
    INDEX   { isarIalarmLogSeverity }
    ::= { isarIalarmLogLimTable  1 }


IsarIalarmLogLimEntry ::=
    SEQUENCE { 
      isarIalarmLogLimMaxIndexLength
        INTEGER,
        
      isarIalarmLogLimCurrentIndexLim
        INTEGER,

      isarIalarmLogLimClearLog
        INTEGER

    }
    
isarIalarmLogLimMaxIndexLength OBJECT-TYPE
    SYNTAX  INTEGER (1..4000)
    ACCESS  read-write
    STATUS  mandatory
    DESCRIPTION
           "The maximum number of entries contained in the log."
    ::= { isarIalarmLogLimEntry  1 }

isarIalarmLogLimCurrentIndexLim OBJECT-TYPE
    SYNTAX  INTEGER (0..4000)
    ACCESS  read-only
    STATUS  mandatory
    DESCRIPTION
           "Gives the number of alarms logs currently available in the
            log.
            Range will be between 0 and isarIalarmLogLimMaxIndexLength."
    ::= { isarIalarmLogLimEntry  2 }

isarIalarmLogLimClearLog OBJECT-TYPE
    SYNTAX  INTEGER { 
                      true(1), 
                      false(2) 
            }
    ACCESS  read-write
    STATUS  mandatory
    DESCRIPTION
           "Set to 'true' removes current content of the alarm log.
            'Get' always returns 'false'."
    ::= { isarIalarmLogLimEntry  3 }



-- ISAR alarm log table


isarIalarmLogTable OBJECT-TYPE
    SYNTAX  SEQUENCE OF IsarIalarmLogEntry
    ACCESS  not-accessible
    STATUS  mandatory
    DESCRIPTION
           "."
    ::= { isarIalarmLogMIBObjects  2 }

isarIalarmLogEntry OBJECT-TYPE
    SYNTAX  IsarIalarmLogEntry
    ACCESS  not-accessible
    STATUS  mandatory
    DESCRIPTION
           "One row in the isarIalarmLogTable."
    INDEX   { isarIalarmLogSeverity, isarIalarmLogIndex }
    ::= { isarIalarmLogTable  1 }


IsarIalarmLogEntry ::=
    SEQUENCE { 
      isarIalarmLogSeverity
        INTEGER,
        
      isarIalarmLogIndex
        INTEGER,

      isarIalarmLogLoggedMessage
        OCTET STRING,

      isarIalarmLogSlotId
        INTEGER,

      isarIalarmLogStackNumber
        INTEGER,

      isarIalarmLogPhysPortId
        INTEGER,

      isarIalarmLogTimeStamp
        INTEGER,

      isarIalarmLogAlarmNumber
        INTEGER,

      isarIalarmLogIndex1
        INTEGER,

      isarIalarmLogIndex2
        INTEGER

    }
    
isarIalarmLogSeverity OBJECT-TYPE
    SYNTAX  INTEGER { 
                      critical(1), 
                      major(2),
                      minor(3),
                      diagnostic(4) 
            }
    ACCESS  read-only
    STATUS  mandatory
    DESCRIPTION
           "Severity of the alarm."
    ::= { isarIalarmLogEntry  1 }

isarIalarmLogIndex OBJECT-TYPE
    SYNTAX  INTEGER (1..2147483647)
    ACCESS  read-only
    STATUS  mandatory
    DESCRIPTION
           "Just an index."
    ::= { isarIalarmLogEntry  2 }

isarIalarmLogLoggedMessage OBJECT-TYPE
    SYNTAX  OCTET STRING (SIZE (0..300))
    ACCESS  read-only
    STATUS  mandatory
    DESCRIPTION
           "Readable presentation of the log entry."
    ::= { isarIalarmLogEntry  3 }

isarIalarmLogSlotId OBJECT-TYPE
    SYNTAX  INTEGER (0..3)
    ACCESS  read-only
    STATUS  mandatory
    DESCRIPTION
           "Identification of the slot that generated the alarm."
    ::= { isarIalarmLogEntry  4 }

isarIalarmLogStackNumber OBJECT-TYPE
    SYNTAX  INTEGER (0..63)
    ACCESS  read-only
    STATUS  mandatory
    DESCRIPTION
           "Identification of the IAD4700 that generated the alarm."
    ::= { isarIalarmLogEntry  5 }

isarIalarmLogPhysPortId OBJECT-TYPE
    SYNTAX  INTEGER (0..2147483647)
    ACCESS  read-only
    STATUS  mandatory
    DESCRIPTION
           "Identification of the physical port that generated the
            alarm."
    ::= { isarIalarmLogEntry  6 }

isarIalarmLogTimeStamp OBJECT-TYPE
    SYNTAX  INTEGER (0..2147483647)
    ACCESS  read-only
    STATUS  mandatory
    DESCRIPTION
           "The time when the alarm occured."
    ::= { isarIalarmLogEntry  7 }

isarIalarmLogAlarmNumber OBJECT-TYPE
    SYNTAX  INTEGER (0..2147483647)
    ACCESS  read-only
    STATUS  mandatory
    DESCRIPTION
           "Numerical identification of the alarm."
    ::= { isarIalarmLogEntry  8 }

isarIalarmLogIndex1 OBJECT-TYPE
    SYNTAX  INTEGER (0..2147483647)
    ACCESS  read-only
    STATUS  mandatory
    DESCRIPTION
           "Index for unique identification of the object that
            generated the alarm (can be a VPI, a connection index)."
    ::= { isarIalarmLogEntry  9 }

isarIalarmLogIndex2 OBJECT-TYPE
    SYNTAX  INTEGER (0..2147483647)
    ACCESS  read-only
    STATUS  mandatory
    DESCRIPTION
           "Index for unique identification of the object that
            generated the alarm (can be a VCI)."
    ::= { isarIalarmLogEntry  10 }



-- ISAR current alarms table


isarIcurrentAlarmsTable OBJECT-TYPE
    SYNTAX  SEQUENCE OF IsarIcurrentAlarmsEntry
    ACCESS  not-accessible
    STATUS  mandatory
    DESCRIPTION
           "."
    ::= { isarIalarmLogMIBObjects  3 }

isarIcurrentAlarmsEntry OBJECT-TYPE
    SYNTAX  IsarIcurrentAlarmsEntry
    ACCESS  not-accessible
    STATUS  mandatory
    DESCRIPTION
           "One row in the isarIcurrentAlarmsTable."
    INDEX   { isarIcurrentAlarmsSeverity,
              isarIcurrentAlarmsStackNumber,
              isarIcurrentAlarmsSlotId,
              isarIcurrentAlarmsPhysPortId,
              isarIcurrentAlarmsIndex1,
              isarIcurrentAlarmsIndex2,
              isarIcurrentAlarmsAlarmNumber }
    ::= { isarIcurrentAlarmsTable  1 }


IsarIcurrentAlarmsEntry ::=
    SEQUENCE { 
      isarIcurrentAlarmsAlarmNumber
        INTEGER,
        
      isarIcurrentAlarmsTimeStamp
        INTEGER,
        
      isarIcurrentAlarmsSeverity
        INTEGER,

      isarIcurrentAlarmsSlotId
        INTEGER,

      isarIcurrentAlarmsStackNumber
        INTEGER,

      isarIcurrentAlarmsPhysPortId
        INTEGER,

      isarIcurrentAlarmsIndex1
        INTEGER,

      isarIcurrentAlarmsIndex2
        INTEGER,

      isarIcurrentAlarmsMessage
        OCTET STRING

    }


isarIcurrentAlarmsAlarmNumber OBJECT-TYPE
    SYNTAX  INTEGER (0..2147483647)
    ACCESS  read-only
    STATUS  mandatory
    DESCRIPTION
           "Numerical identification of the alarm."
    ::= { isarIcurrentAlarmsEntry  1 }

isarIcurrentAlarmsTimeStamp OBJECT-TYPE
    SYNTAX  INTEGER (0..2147483647)
    ACCESS  read-only
    STATUS  mandatory
    DESCRIPTION
           "The time when the alarm occured."
    ::= { isarIcurrentAlarmsEntry  2 }

isarIcurrentAlarmsSeverity OBJECT-TYPE
    SYNTAX  INTEGER { 
                      critical(1), 
                      major(2),
                      minor(3),
                      diagnostic(4) 
            }
    ACCESS  read-only
    STATUS  mandatory
    DESCRIPTION
           "Severity of the alarm."
    ::= { isarIcurrentAlarmsEntry  3 }


isarIcurrentAlarmsSlotId OBJECT-TYPE
    SYNTAX  INTEGER (0..3)
    ACCESS  read-only
    STATUS  mandatory
    DESCRIPTION
           "Identification of the slot that generated the alarm."
    ::= { isarIcurrentAlarmsEntry  4 }

isarIcurrentAlarmsStackNumber OBJECT-TYPE
    SYNTAX  INTEGER (0..63)
    ACCESS  read-only
    STATUS  mandatory
    DESCRIPTION
           "Identification of the IAD4700 that generated the alarm."
    ::= { isarIcurrentAlarmsEntry  5 }

isarIcurrentAlarmsPhysPortId OBJECT-TYPE
    SYNTAX  INTEGER (0..2147483647)
    ACCESS  read-only
    STATUS  mandatory
    DESCRIPTION
           "Identification of the physical port that generated the
            alarm."
    ::= { isarIcurrentAlarmsEntry  6 }

isarIcurrentAlarmsIndex1 OBJECT-TYPE
    SYNTAX  INTEGER (0..2147483647)
    ACCESS  read-only
    STATUS  mandatory
    DESCRIPTION
           "Index needed for unique identification of the object that
            generated the alarm (can be a VPI, a connection index)."
    ::= { isarIcurrentAlarmsEntry  7 }

isarIcurrentAlarmsIndex2 OBJECT-TYPE
    SYNTAX  INTEGER (0..2147483647)
    ACCESS  read-only
    STATUS  mandatory
    DESCRIPTION
           "Index needed for unique identification of the object that
            generated the alarm (can be a VCI)."
    ::= { isarIcurrentAlarmsEntry  8 }

isarIcurrentAlarmsMessage OBJECT-TYPE
    SYNTAX  OCTET STRING (SIZE (0..300))
    ACCESS  read-only
    STATUS  mandatory
    DESCRIPTION
           "Readable presentation of the alarm."
    ::= { isarIcurrentAlarmsEntry  9 }


--
-- ISAR alarmLogMIBObjects : end
--




-- This file cannot be used to create SNMP agent.
-- The file isarOneFile.my has to be used to create the agent.


-- isarIspeechProcessorMIBObjects     OBJECT IDENTIFIER ::= { isar  20 }


--
-- ISAR speechProcessorMIBObjects : begin
--
-- enterprise MIB for ISAR
-- The MIB is written for SNMPv1.


isarIspeechProcTable OBJECT-TYPE
    SYNTAX  SEQUENCE OF IsarIspeechProcEntry
    ACCESS  not-accessible
    STATUS  mandatory
    DESCRIPTION
           "This table contains general information about a speech
            processor."
    ::= { isarIspeechProcessorMIBObjects  1 }

isarIspeechProcEntry OBJECT-TYPE
    SYNTAX  IsarIspeechProcEntry
    ACCESS  not-accessible
    STATUS  mandatory
    DESCRIPTION
           "One row in the isarIspeechProcTable."
    INDEX   { isarIphysSlotId, isarIphysStackNo }
    ::= { isarIspeechProcTable  1 }


IsarIspeechProcEntry ::=
    SEQUENCE { 
      isarIspeechProcNoChannels
        INTEGER,
        
      isarIspeechProcNoFreeChannels
        INTEGER
    }

isarIspeechProcNoChannels OBJECT-TYPE
    SYNTAX  INTEGER (1..32)
    ACCESS  read-only
    STATUS  mandatory
    DESCRIPTION
           "Total number of channels in speech processor."
    ::= { isarIspeechProcEntry  1 }

isarIspeechProcNoFreeChannels OBJECT-TYPE
    SYNTAX  INTEGER (0..32)
    ACCESS  read-only
    STATUS  mandatory
    DESCRIPTION
           "Number of free channels in speech processor."
    ::= { isarIspeechProcEntry  2 }


isarIspeechBundleNextIndex OBJECT-TYPE
    SYNTAX  INTEGER (0..2147483647)
    ACCESS  read-only
    STATUS  mandatory
    DESCRIPTION
           "This object is used to assist the manager in
            selecting a value for isarIspeechBundleIndex.  
            The manager has to GET this index before creating a row in 
            isarIspeechBundleTable."
    ::= { isarIspeechProcessorMIBObjects 2 }


isarIspeechBundleTable OBJECT-TYPE
    SYNTAX  SEQUENCE OF IsarIspeechBundleEntry
    ACCESS  not-accessible
    STATUS  mandatory
    DESCRIPTION
           "This table contains general information about a speech
            processor.
            Rows are created by the operator."
    ::= { isarIspeechProcessorMIBObjects  3 }

isarIspeechBundleEntry OBJECT-TYPE
    SYNTAX  IsarIspeechBundleEntry
    ACCESS  not-accessible
    STATUS  mandatory
    DESCRIPTION
           "One row in the isarIspeechBundleTable."
    INDEX   { isarIspeechBundleIndex }
    ::= { isarIspeechBundleTable  1 }


IsarIspeechBundleEntry ::=
    SEQUENCE { 
      isarIspeechBundleIndex
        INTEGER,

      isarIspeechBundleCoder
        INTEGER,
        
      isarIspeechBundlePayloadFormat
        INTEGER,
        
      isarIspeechBundleSource
        INTEGER,
        
      isarIspeechBundleOutputGain
        INTEGER,
        
      isarIspeechBundleEnableHighPassFilter
        INTEGER,

      isarIspeechBundleEnablePostFilter
        INTEGER,

      isarIspeechBundleEnableEchoCancel
        INTEGER,        

      isarIspeechBundleEnableSilenceCompression
        INTEGER,

      isarIspeechBundleInputGain
        INTEGER,

      isarIspeechBundleLowerLayerIfIndex
        INTEGER,

      isarIspeechBundleAdminStatus
        INTEGER,

      isarIspeechBundleOperStatus
        INTEGER,

      isarIspeechBundleRowStatus
        INTEGER,

      isarIspeechBundleConnectionIdentifier
        INTEGER,

      isarIspeechBundlePackingFactor
        INTEGER

    }

isarIspeechBundleIndex OBJECT-TYPE
    SYNTAX  INTEGER (1..2147483647)
    ACCESS  read-only
    STATUS  mandatory
    DESCRIPTION
           "Index of speech bundle determined by manager via
            isarIspeechBundleNextIndex."
    ::= { isarIspeechBundleEntry  1 }

isarIspeechBundleCoder OBJECT-TYPE
    SYNTAX  INTEGER { 
                      g723Lo(1), 
                      g723Hi(2),
                      g729(3)
            }
    ACCESS  read-write
    STATUS  mandatory
    DESCRIPTION
           "Coding algorithm to be used.
            (it must be possible to add rows but it must be 
            impossible to modify this index)
            The SNMPv2 MAX-ACCESS is read-(only-)create."
    ::= { isarIspeechBundleEntry  2 }

isarIspeechBundlePayloadFormat OBJECT-TYPE
    SYNTAX  INTEGER { 
                      frf11(1), 
                      voIp(2)
            }
    ACCESS  read-only
    STATUS  mandatory
    DESCRIPTION
           "The format of the payload.
           
            IAD4700 R2.0 : only frf11 is supported."
    DEFVAL  { frf11 }
    ::= { isarIspeechBundleEntry  3 }

isarIspeechBundleSource OBJECT-TYPE
    SYNTAX  INTEGER { 
                      mute(1), 
                      decoder(2),
                      toneGenerator(3)
            }
    ACCESS  read-write
    STATUS  mandatory
    DESCRIPTION
           "source.
            The SNMPv2 MAX-ACCESS is read-create."
    ::= { isarIspeechBundleEntry  4 }

isarIspeechBundleOutputGain OBJECT-TYPE
    SYNTAX  INTEGER (-31..31)
    ACCESS  read-write
    STATUS  mandatory
    DESCRIPTION
           "The voice output gain in db.
            The SNMPv2 MAX-ACCESS is read-create."
    DEFVAL { 0 }
    ::= { isarIspeechBundleEntry  5 }

isarIspeechBundleEnableHighPassFilter OBJECT-TYPE
    SYNTAX  INTEGER {
                      true(1),
                      false(2)
            }
    ACCESS  read-write
    STATUS  mandatory
    DESCRIPTION
           ".
            The SNMPv2 MAX-ACCESS is read-create."
    DEFVAL { true }
    ::= { isarIspeechBundleEntry  6 }

isarIspeechBundleEnablePostFilter OBJECT-TYPE
    SYNTAX  INTEGER {
                      true(1),
                      false(2)
            }
    ACCESS  read-write
    STATUS  mandatory
    DESCRIPTION
           ".
            The SNMPv2 MAX-ACCESS is read-create."
    DEFVAL { true }
    ::= { isarIspeechBundleEntry  7 }

isarIspeechBundleEnableEchoCancel OBJECT-TYPE
    SYNTAX  INTEGER {
                      true(1),
                      false(2)
            }
    ACCESS  read-write
    STATUS  mandatory
    DESCRIPTION
           "Enable echo cancellation.
            The SNMPv2 MAX-ACCESS is read-create."
    DEFVAL { true }
    ::= { isarIspeechBundleEntry  8 }

isarIspeechBundleEnableSilenceCompression OBJECT-TYPE
    SYNTAX  INTEGER {
                      true(1),
                      false(2)
            }
    ACCESS  read-write
    STATUS  mandatory
    DESCRIPTION
           "Enable echo cancellation.
            The SNMPv2 MAX-ACCESS is read-create."
    DEFVAL { false }
    ::= { isarIspeechBundleEntry  9 }

isarIspeechBundleInputGain OBJECT-TYPE
    SYNTAX  INTEGER (-31..31)
    ACCESS  read-write
    STATUS  mandatory
    DESCRIPTION
           "The voice input gain in db.
            
            The SNMPv2 MAX-ACCESS is read-create."
    DEFVAL { 0 }
    ::= { isarIspeechBundleEntry  10 }

isarIspeechBundleLowerLayerIfIndex OBJECT-TYPE
    SYNTAX  INTEGER (1..2147483647)
    ACCESS  read-write
    STATUS  mandatory
    DESCRIPTION
           "The ifIndex of the layer on which the speech bundle is
            defined.
            Modify of this value is not allowed.
            The SNMPv2 MAX-ACCESS is read-create."
    ::= { isarIspeechBundleEntry  11 }

isarIspeechBundleAdminStatus OBJECT-TYPE
    SYNTAX  INTEGER {
                      up(1),
                      down(2)
            }
    ACCESS  read-write
    STATUS  optional
    DESCRIPTION
           "The desired administrative status of the speech bundle.
            The SNMPv2 MAX-ACCESS is read-create."
    ::= { isarIspeechBundleEntry  12 }

isarIspeechBundleOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  optional
    DESCRIPTION
           "The operational status of the speech bundle.
            Only 'up' and 'down' will be used. (Admin state is immediately
            reflected in Operational state)"
    ::= { isarIspeechBundleEntry  13 }

isarIspeechBundleRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIspeechBundleEntry  14 }

isarIspeechBundleConnectionIdentifier OBJECT-TYPE
    SYNTAX  INTEGER (0..2147483647)
    ACCESS  read-only
    STATUS  mandatory
    DESCRIPTION
           "The identification of the connection is filled in when an 
            entry in a connection is created.
            A value different from zero indicates that the interface
            is in use by a higher layer interface or by a service (IWF).
            The value itself has no meaning for the operator.
            For IAD4700 intern the value 0-1024 indicates the number of
            connection.  A value > 1024 is one specific connection."
    ::= { isarIspeechBundleEntry  15 }

isarIspeechBundlePackingFactor OBJECT-TYPE
    SYNTAX  INTEGER (1..2)
    ACCESS  read-write
    STATUS  mandatory
    DESCRIPTION
           "Defines the number of samples to put into a single frame
            before sending it to the other side.
            Depending on isarIspeechBundleCoder this value can 
            be :
                 for g729 the value can be 1 to 2
                 for g723lo and g723hi it must be 1
            The SNMPv2 MAX-ACCESS is read-(only-)create."
    ::= { isarIspeechBundleEntry  16 }


--
-- ISAR speechProcessorMIBObjects : end
--




-- This file cannot be used to create SNMP agent.
-- The file isarOneFile.my has to be used to create the agent.


-- isarIhdlcLogPortMIBObjects       OBJECT IDENTIFIER ::= { isar  21 }


--
-- ISAR hdlcLogPortMIBObjects : begin
--
-- enterprise MIB for ISAR
-- The MIB is written for SNMPv1.

-- next logical port index value

isarIhdlcLogPortNextIndex OBJECT-TYPE
    SYNTAX  INTEGER (0..2147483647)
    ACCESS  read-only
    STATUS  mandatory
    DESCRIPTION
           "This object is used to assist the manager in selecting
            a value for isarIhdlcLogPortIndex.  
            The manager has to GET this index before creating a row in 
            isarIhdlcLogPortTable."
    ::= { isarIhdlcLogPortMIBObjects  1 }


-- HDLC logical port table


isarIhdlcLogPortTable OBJECT-TYPE
    SYNTAX  SEQUENCE OF IsarIhdlcLogPortEntry
    ACCESS  not-accessible
    STATUS  mandatory
    DESCRIPTION
           "When an entry in this table is created it is necessary to 
            create an entry in the ifTable, in the ifIndex mapping
            table and in the isarIhdlcLogPortStatsTable.  When an entry of 
            this table is deleted, it is necessary to delete the corresponding
            entry in the ifTable, the mapping table and 
            isarIhdlcLogPortStatsTable.
            Once a row is created it is not allowed to modify it.  The 
            operator must delete and re-create the row.
            The operator is not allowed to delete HDLC logical ports with an 
            ifName that starts with Internal_."
    ::= { isarIhdlcLogPortMIBObjects  2 }

isarIhdlcLogPortEntry OBJECT-TYPE
    SYNTAX  IsarIhdlcLogPortEntry
    ACCESS  not-accessible
    STATUS  mandatory
    DESCRIPTION
           "One row in the isarIhdlcLogPortTable."
    INDEX   { isarIhdlcLogPortIndex }
    ::= { isarIhdlcLogPortTable  1 }


IsarIhdlcLogPortEntry ::=
    SEQUENCE { 
      isarIhdlcLogPortIndex
        INTEGER,

      isarIhdlcLogPortIfIndex
        INTEGER,

      isarIhdlcLogPortLowerLayerIfIndex
        INTEGER,

      isarIhdlcLogPortCrcType
        INTEGER,

      isarIhdlcLogPortNumberOfFlags
        INTEGER,

      isarIhdlcLogPortRowStatus
        INTEGER
    }
    


isarIhdlcLogPortIndex OBJECT-TYPE
    SYNTAX  INTEGER (1..2147483647)
    ACCESS  read-only
    STATUS  mandatory
    DESCRIPTION
           "The index of the HDLC logical port."
    ::= { isarIhdlcLogPortEntry  1 }

isarIhdlcLogPortIfIndex OBJECT-TYPE
    SYNTAX  INTEGER (1..2147483647)
    ACCESS  read-only
    STATUS  mandatory
    DESCRIPTION
           "The ifIndex of the HDLC logical port.  This index is 
            determined after creation of a row in the ifTable."
    ::= { isarIhdlcLogPortEntry  2 }

isarIhdlcLogPortLowerLayerIfIndex OBJECT-TYPE
    SYNTAX  INTEGER (1..2147483647)
    ACCESS  read-write
    STATUS  mandatory
    DESCRIPTION
           "The ifIndex of the layer on which this HDLC logical port
            is defined.  This lower layer can be a ds0Bundle or a
            HSSI port.
            Modify of this value is not allowed.
            The SNMPv2 MAX-ACCESS is read-create."
    ::= { isarIhdlcLogPortEntry  3 }

isarIhdlcLogPortCrcType OBJECT-TYPE
    SYNTAX  INTEGER {
                      crc16Bit(1),
                      crc32Bit(2)
            }
    ACCESS  read-write
    STATUS  mandatory
    DESCRIPTION
           "The type of CRC that will be applied to frames through this
            port.
            Modify of value is not allowed.
            The SNMPv2 MAX-ACCESS is read-create."
    DEFVAL { crc16Bit }
    ::= { isarIhdlcLogPortEntry  4 }

isarIhdlcLogPortNumberOfFlags OBJECT-TYPE
    SYNTAX  INTEGER (1..7)
    ACCESS  read-write
    STATUS  mandatory
    DESCRIPTION
           "The number of flags used for synchronisation.
            Modify of value is not allowed.
            The SNMPv2 MAX-ACCESS is read-create."
    DEFVAL { 2 }
    ::= { isarIhdlcLogPortEntry  5 }

isarIhdlcLogPortRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
                    }
    ACCESS  read-write
    STATUS  mandatory
    DESCRIPTION
           "This object is used to create and delete rows in the 
            isarIhdlcLogPortTable.
            The SNMPv2 MAX-ACCESS is read-create."
    ::= { isarIhdlcLogPortEntry  6 }



-- HDLC logical port ifIndex mapping table


isarIhdlcLogPortMappingTable OBJECT-TYPE
    SYNTAX  SEQUENCE OF IsarIhdlcLogPortMappingEntry
    ACCESS  not-accessible
    STATUS  mandatory
    DESCRIPTION
           "Mapping of ifIndex into isarIhdlcLogPortIndex."
    ::= { isarIhdlcLogPortMIBObjects  3 }

isarIhdlcLogPortMappingEntry OBJECT-TYPE
    SYNTAX  IsarIhdlcLogPortMappingEntry
    ACCESS  not-accessible
    STATUS  mandatory
    DESCRIPTION
           "One row in the isarIhdlcLogPortMappingTable."
    INDEX   { ifIndex }
    ::= { isarIhdlcLogPortMappingTable  1 }


IsarIhdlcLogPortMappingEntry ::=
    SEQUENCE { 
      isarIhdlcLogPortMappedIndex
        INTEGER
    }
    
isarIhdlcLogPortMappedIndex OBJECT-TYPE
    SYNTAX  INTEGER (1..2147483647)
    ACCESS  read-only
    STATUS  mandatory
    DESCRIPTION
           "The index of the HDLC logical port in
            isarIhdlcLogPortTable."
    ::= { isarIhdlcLogPortMappingEntry  1 }


--
-- ISAR hdlcLogPortMIBObjects : end
--




-- This file cannot be used to create SNMP agent.
-- The file isarOneFile.my has to be used to create the agent.


-- isarIvcsMIBObjects       OBJECT IDENTIFIER ::= { isar  22 }


--
-- ISAR vcsMIBObjects : begin
--
-- enterprise MIB for ISAR
-- The MIB is written for SNMPv1.


-- VCS interworking function table


isarIvcsIwfTable OBJECT-TYPE
    SYNTAX  SEQUENCE OF IsarIvcsIwfEntry
    ACCESS  not-accessible
    STATUS  mandatory
    DESCRIPTION
           "This table contains the VCS interworking functions
            present in the system.
            It must be possible to dynamically add and delete entries.
            
            When a row in this table is created, an entry in the
            isarIvcsIwfMappingTable is made by IAD4700 (inverse mapping
            of index).
            
            At the same time another table must be updated :
             - set field isarIatmVclCrossConnectIdentifier of the 
               corresponding entry in IsarIatmVclEntry with the
               value of isarIvcsIwfConnIndex and
             - set field isarIatmVclServiceType of the 
               corresponding entry in IsarIatmVclEntry to 'vcs'."
    ::= { isarIvcsMIBObjects  1 }

isarIvcsIwfEntry OBJECT-TYPE
    SYNTAX  IsarIvcsIwfEntry
    ACCESS  not-accessible
    STATUS  mandatory
    DESCRIPTION
           "One row in the isarIvcsIwfTable."
    INDEX   { isarIvcsIwfVoiceBundle }
    ::= { isarIvcsIwfTable  1 }


IsarIvcsIwfEntry ::=
    SEQUENCE { 
      isarIvcsIwfServiceIndex
        INTEGER,

      isarIvcsIwfConnIndex
        INTEGER,
                
      isarIvcsIwfVoiceBundle
        INTEGER,

      isarIvcsIwfVclIfIndex
        INTEGER,

      isarIvcsIwfVclVpi
        INTEGER,

      isarIvcsIwfVclVci
        INTEGER,

      isarIvcsIwfCodingAlgorithm
        INTEGER,

      isarIvcsIwfPackingFactor
        INTEGER,

      isarIvcsIwfSendFrHeader
        INTEGER,

      isarIvcsIwfPhysSlotId
        INTEGER,

      isarIvcsIwfPhysStackNo
        INTEGER,

      isarIvcsIwfAdminStatus
        INTEGER,

      isarIvcsIwfOperStatus
        INTEGER,

      isarIvcsIwfRowStatus
        INTEGER

    }
    
isarIvcsIwfServiceIndex OBJECT-TYPE
    SYNTAX  INTEGER
    ACCESS  read-write
    STATUS  mandatory
    DESCRIPTION
           "The index of the service to which this interworking function
            belongs.
            This is the same index as serviceIndex of isarIserviceTable.
            (it must be possible to add rows but it must be 
            impossible to modify this index)
            The SNMPv2 MAX-ACCESS is read-(only-)create."
    ::= { isarIvcsIwfEntry  1 }

isarIvcsIwfConnIndex OBJECT-TYPE
    SYNTAX  INTEGER
    ACCESS  read-only
    STATUS  mandatory
    DESCRIPTION
           "The value of this object is equal to the 
            isarIiwfNextConnIndex obtained (by IAD4700) to uniqely identify 
            this IWF."
    ::= { isarIvcsIwfEntry  2 }

isarIvcsIwfVoiceBundle OBJECT-TYPE
    SYNTAX  INTEGER
    ACCESS  read-only
    STATUS  mandatory
    DESCRIPTION
           "The index in the isarIspeechBundleTable of the bundle carrying
            the voice data to be compressed."
    ::= { isarIvcsIwfEntry  3 }

isarIvcsIwfVclIfIndex OBJECT-TYPE
    SYNTAX  INTEGER
    ACCESS  read-write
    STATUS  mandatory
    DESCRIPTION
           "Identification of the ATM port to be used.
            The combination of VclIfIndex, VclVpi and VclVpi identifies 
            the VCL on which to send/receive compressed voice data.
  
            (it must be possible to add rows but it must be 
            impossible to modify this index)
            The SNMPv2 MAX-ACCESS is read-(only-)create."
    ::= { isarIvcsIwfEntry  4 }

isarIvcsIwfVclVpi OBJECT-TYPE
    SYNTAX  INTEGER (0..4095)
    ACCESS  read-write
    STATUS  mandatory
    DESCRIPTION
           "The VPI value of the VCL used for this interworking 
            function.
            The combination of VclIfIndex, VclVpi and VclVpi identifies 
            the VCL on which to send/receive compressed voice data.          
            isarIvcsIwfVclVpi corresponds to isarIatmVclVpi of 
            isarIatmVclTable.
            (it must be possible to add rows but it must be 
            impossible to modify this index)
            The SNMPv2 MAX-ACCESS is read-(only-)create."
    ::= { isarIvcsIwfEntry  5 }

isarIvcsIwfVclVci OBJECT-TYPE
    SYNTAX  INTEGER (0..65535)
    ACCESS  read-write
    STATUS  mandatory
    DESCRIPTION
           "The VCI value of the VCL used for this interworking 
            function.
            The combination of VclIfIndex, VclVpi and VclVpi identifies 
            the VCL on which to send/receive compressed voice data.
            isarIvcsIwfVclVci corresponds to isarIatmVclVci of 
            isarIatmVclTable
            (it must be possible to add rows but it must be 
            impossible to modify this index)
            The SNMPv2 MAX-ACCESS is read-(only-)create."
    ::= { isarIvcsIwfEntry  6 }

isarIvcsIwfCodingAlgorithm OBJECT-TYPE
    SYNTAX  INTEGER { 
                      g723Lo(1), 
                      g723Hi(2),
                      g729(3)
            }
    ACCESS  read-only
    STATUS  mandatory
    DESCRIPTION
           "The compression method as defined in the SpeechBundle."
    ::= { isarIvcsIwfEntry  7 }

isarIvcsIwfPackingFactor OBJECT-TYPE
    SYNTAX  INTEGER (1..2)
    ACCESS  read-write
    STATUS  obsolete
    DESCRIPTION
           "Defines the number of samples to put into a single frame
            before sending it to the other side.
            The value is defined in the SpeechBundle."
    ::= { isarIvcsIwfEntry  8 }

isarIvcsIwfSendFrHeader OBJECT-TYPE
    SYNTAX  INTEGER {
                      noFrHeaderSend(1),
                      frHeaderSend(2)
            }
    ACCESS  read-only
    STATUS  mandatory
    DESCRIPTION
           "Depending on the value a frame relay header will be composed
            and put in front of the compressed data.  The value is not
            used at the moment and will allways be noFrHeaderSend.
            The SNMPv2 MAX-ACCESS is read-(only-)create."
    DEFVAL { noFrHeaderSend }
    ::= { isarIvcsIwfEntry  9 }

isarIvcsIwfPhysSlotId OBJECT-TYPE
    SYNTAX  INTEGER (1..3)
    ACCESS  read-write
    STATUS  mandatory
    DESCRIPTION
           "Slot Id of the Voice Compression Module (VCM) where the
            (de)compression will take place.
            
            When an Iwf is created on the E1/T1 port of a particular VCM,
            only the Slot Id of this VCM can be selected.
            
            When an Iwf is created on the E1/T1 port of the MAMO,
            any valid VCM Slot Id can be selected.
            
            Information about the number of available channels per VCM can
            be found in isarIspeechProcTable MIB.
            
            The SNMPv2 MAX-ACCESS is read-(only-)create."
    ::= { isarIvcsIwfEntry  10 }

isarIvcsIwfPhysStackNo OBJECT-TYPE
    SYNTAX  INTEGER (0..63)
    ACCESS  read-write
    STATUS  mandatory
    DESCRIPTION
           "Stack number of the Voice Compression Module (VCM) where the
            (de)compression will take place.
            The SNMPv2 MAX-ACCESS is read-(only-)create."
    ::= { isarIvcsIwfEntry  11 }

isarIvcsIwfAdminStatus OBJECT-TYPE
    SYNTAX  INTEGER {
                      up(1),
                      down(2)
            }
    ACCESS  read-write
    STATUS  mandatory
    DESCRIPTION
           "The administrative state of the interworking function.
            The SNMPv2 MAX-ACCESS is read-create."
    DEFVAL { down }
    ::= { isarIvcsIwfEntry  12 }

isarIvcsIwfOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "The operational state of the interworking function.
            Refer to RFC 2233 for the different states."
    ::= { isarIvcsIwfEntry  13 }


isarIvcsIwfRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIvcsIwfEntry  14 }


-- vcs iwf mapping

isarIvcsIwfMappingTable OBJECT-TYPE
    SYNTAX  SEQUENCE OF IsarIvcsIwfMappingEntry
    ACCESS  not-accessible
    STATUS  mandatory
    DESCRIPTION
           "The vcsIwf mapping table is used to map the IWF index
            into the index of the corresponding entry in the
            isarIvcsIwfTable."
    ::= { isarIvcsMIBObjects  2 }

isarIvcsIwfMappingEntry OBJECT-TYPE
    SYNTAX  IsarIvcsIwfMappingEntry
    ACCESS  not-accessible
    STATUS  mandatory
    DESCRIPTION
           "An entry in the vcsIwf mapping table."
    INDEX   { isarIvcsIwfConnIndex }
    ::= { isarIvcsIwfMappingTable  1 }

IsarIvcsIwfMappingEntry ::=
    SEQUENCE {
      isarIvcsIwfMapVoiceBundle
        INTEGER
    }

isarIvcsIwfMapVoiceBundle OBJECT-TYPE
    SYNTAX  INTEGER
    ACCESS  read-only
    STATUS  mandatory
    DESCRIPTION
           "Mapped index."
    ::= { isarIvcsIwfMappingEntry  1 }


-- statistics

isarIvcsIwfStatsTable OBJECT-TYPE
    SYNTAX  SEQUENCE OF IsarIvcsIwfStatsEntry
    ACCESS  not-accessible
    STATUS  mandatory
    DESCRIPTION
           "This table contains the statistics about the
            VCS interworking functions present in the system.
            Creation and deletion of entries is coupled with
            isarIvcsIwfTable."
    ::= { isarIvcsMIBObjects  3 }

isarIvcsIwfStatsEntry OBJECT-TYPE
    SYNTAX  IsarIvcsIwfStatsEntry
    ACCESS  not-accessible
    STATUS  mandatory
    DESCRIPTION
           "One row in the isarIvcsIwfStatsTable."
    INDEX   { isarIvcsIwfStatsVoiceBundle }
    ::= { isarIvcsIwfStatsTable  1 }


IsarIvcsIwfStatsEntry ::=
    SEQUENCE { 
      isarIvcsIwfStatsVoiceBundle
        INTEGER,

      isarIvcsIwfStatsDsToAsTransmFrames
        Counter,

      isarIvcsIwfStatsAsToDsTransmFrames
        Counter,

      isarIvcsIwfStatsDsToAsDroppedFrames
        Counter,

      isarIvcsIwfStatsAsToDsDroppedFrames
        Counter,

      isarIvcsIwfStatsNoOfTxBufferOverflow
        Counter,

      isarIvcsIwfStatsNoOfTxBufferUnderrun
        Counter,

      isarIvcsIwfStatsNoOfRxBufferOverflow
        Counter,

      isarIvcsIwfStatsNoOfRxBufferUnderrun
        Counter
    }

isarIvcsIwfStatsVoiceBundle OBJECT-TYPE
    SYNTAX  INTEGER
    ACCESS  read-only
    STATUS  mandatory
    DESCRIPTION
           "The index of this IWF."
    ::= { isarIvcsIwfStatsEntry  1 }

isarIvcsIwfStatsDsToAsTransmFrames OBJECT-TYPE
    SYNTAX  Counter
    ACCESS  read-only
    STATUS  mandatory
    DESCRIPTION
           "The number of frames that have been received from the drop
            side and have been sent to the aggregate side by this
            interworking function."
    ::= { isarIvcsIwfStatsEntry  2 }

isarIvcsIwfStatsAsToDsTransmFrames OBJECT-TYPE
    SYNTAX  Counter
    ACCESS  read-only
    STATUS  mandatory
    DESCRIPTION
           "The number of frames that have been received from the 
            aggregate side and have been sent to the drop side by this
            interworking function."
    ::= { isarIvcsIwfStatsEntry  3 }

isarIvcsIwfStatsDsToAsDroppedFrames OBJECT-TYPE
    SYNTAX  Counter
    ACCESS  read-only
    STATUS  mandatory
    DESCRIPTION
           "The number of frames that have been received from the drop
            side and have been dropped by the store and forward function."
    ::= { isarIvcsIwfStatsEntry  4 }

isarIvcsIwfStatsAsToDsDroppedFrames OBJECT-TYPE
    SYNTAX  Counter
    ACCESS  read-only
    STATUS  mandatory
    DESCRIPTION
           "The number of frames that have been received from the 
            aggregate side and have been dropped by the store and forward function."
    ::= { isarIvcsIwfStatsEntry  5 }

isarIvcsIwfStatsNoOfTxBufferOverflow OBJECT-TYPE
    SYNTAX  Counter
    ACCESS  read-only
    STATUS  mandatory
    DESCRIPTION
           "."
    ::= { isarIvcsIwfStatsEntry  6 }

isarIvcsIwfStatsNoOfTxBufferUnderrun OBJECT-TYPE
    SYNTAX  Counter
    ACCESS  read-only
    STATUS  mandatory
    DESCRIPTION
           "."
    ::= { isarIvcsIwfStatsEntry  7 }

isarIvcsIwfStatsNoOfRxBufferOverflow OBJECT-TYPE
    SYNTAX  Counter
    ACCESS  read-only
    STATUS  mandatory
    DESCRIPTION
           "."
    ::= { isarIvcsIwfStatsEntry  8 }

isarIvcsIwfStatsNoOfRxBufferUnderrun OBJECT-TYPE
    SYNTAX  Counter
    ACCESS  read-only
    STATUS  mandatory
    DESCRIPTION
           "."
    ::= { isarIvcsIwfStatsEntry  9 }



-- VCS interworking function read-only table


isarIvcsIwfRoTable OBJECT-TYPE
    SYNTAX  SEQUENCE OF IsarIvcsIwfRoEntry
    ACCESS  not-accessible
    STATUS  mandatory
    DESCRIPTION
           "This table contains the IAD4700 created VCS interworking 
            functions present in the system.
            
            When a row in this table is created, an entry in the
            isarIvcsIwfMappingRoTable is made by IAD4700 (inverse mapping
            of index).
            
            At the same time another table must be updated :
             - set field isarIatmVclRoCrossConnectIdentifier of the 
               corresponding entry in IsarIatmVclRoEntry with the
               value of isarIvcsIwfRoConnIndex and
             - set field isarIatmVclRoServiceType of the 
               corresponding entry in IsarIatmVclRoEntry to 'vcs'.

            This table is a duplicate of the isarIvcsIwfTable with all
            fields, except row status, set to read-only.  The operator
            is not allowed to modify entries in this table, only delete
            is permitted.
            Duplication is done for Call and connection control because
            this software creates its own VCSs.
            Rows are created/deleted by IAD4700."
    ::= { isarIvcsMIBObjects  4 }

isarIvcsIwfRoEntry OBJECT-TYPE
    SYNTAX  IsarIvcsIwfRoEntry
    ACCESS  not-accessible
    STATUS  mandatory
    DESCRIPTION
           "One row in the isarIvcsIwfRoTable."
    INDEX   { isarIvcsIwfRoVoiceBundle }
    ::= { isarIvcsIwfRoTable  1 }


IsarIvcsIwfRoEntry ::=
    SEQUENCE { 
      isarIvcsIwfRoServiceIndex
        INTEGER,

      isarIvcsIwfRoConnIndex
        INTEGER,
                
      isarIvcsIwfRoVoiceBundle
        INTEGER,

      isarIvcsIwfRoVclIfIndex
        INTEGER,

      isarIvcsIwfRoVclVpi
        INTEGER,

      isarIvcsIwfRoVclVci
        INTEGER,

      isarIvcsIwfRoCodingAlgorithm
        INTEGER,

      isarIvcsIwfRoPackingFactor
        INTEGER,

      isarIvcsIwfRoSendFrHeader
        INTEGER,

      isarIvcsIwfRoPhysSlotId
        INTEGER,

      isarIvcsIwfRoPhysStackNo
        INTEGER,

      isarIvcsIwfRoOperStatus
        INTEGER,

      isarIvcsIwfRoRowStatus
        INTEGER,

      isarIvcsIwfRoPhysPortId
        INTEGER,

      isarIvcsIwfRoDsx0BundleMap
        INTEGER

    }
    
isarIvcsIwfRoServiceIndex OBJECT-TYPE
    SYNTAX  INTEGER
    ACCESS  read-only
    STATUS  mandatory
    DESCRIPTION
           "The index of the service to which this interworking function
            belongs.
            This is the same index as serviceIndex of isarIserviceTable."
    ::= { isarIvcsIwfRoEntry  1 }

isarIvcsIwfRoConnIndex OBJECT-TYPE
    SYNTAX  INTEGER
    ACCESS  read-only
    STATUS  mandatory
    DESCRIPTION
           "The value of this object is equal to the 
            isarIiwfNextConnIndex obtained (by IAD4700) to uniqely identify 
            this IWF."
    ::= { isarIvcsIwfRoEntry  2 }

isarIvcsIwfRoVoiceBundle OBJECT-TYPE
    SYNTAX  INTEGER
    ACCESS  read-only
    STATUS  mandatory
    DESCRIPTION
           "The index in the isarIspeechBundleTable of the bundle carrying
            the voice data to be compressed."
    ::= { isarIvcsIwfRoEntry  3 }

isarIvcsIwfRoVclIfIndex OBJECT-TYPE
    SYNTAX  INTEGER
    ACCESS  read-only
    STATUS  mandatory
    DESCRIPTION
           "Identification of the ATM port to be used.
            The combination of VclIfIndex, VclVpi and VclVpi identifies 
            the VCL on which to send/receive compressed voice data."
    ::= { isarIvcsIwfRoEntry  4 }

isarIvcsIwfRoVclVpi OBJECT-TYPE
    SYNTAX  INTEGER (0..4095)
    ACCESS  read-only
    STATUS  mandatory
    DESCRIPTION
           "The VPI value of the VCL used for this interworking 
            function.
            The combination of VclIfIndex, VclVpi and VclVpi identifies 
            the VCL on which to send/receive compressed voice data.          
            isarIvcsIwfVclVpi corresponds to isarIatmVclVpi of 
            isarIatmVclTable."
    ::= { isarIvcsIwfRoEntry  5 }

isarIvcsIwfRoVclVci OBJECT-TYPE
    SYNTAX  INTEGER (0..65535)
    ACCESS  read-only
    STATUS  mandatory
    DESCRIPTION
           "The VCI value of the VCL used for this interworking 
            function.
            The combination of VclIfIndex, VclVpi and VclVpi identifies 
            the VCL on which to send/receive compressed voice data.
            isarIvcsIwfRoVclVci corresponds to isarIatmVclRoVci of 
            isarIatmVclRoTable."
    ::= { isarIvcsIwfRoEntry  6 }

isarIvcsIwfRoCodingAlgorithm OBJECT-TYPE
    SYNTAX  INTEGER { 
                      g723Lo(1), 
                      g723Hi(2),
                      g729(3)
            }
    ACCESS  read-only
    STATUS  mandatory
    DESCRIPTION
           "The compression method as defined in the SpeechBundle."
    ::= { isarIvcsIwfRoEntry  7 }

isarIvcsIwfRoPackingFactor OBJECT-TYPE
    SYNTAX  INTEGER (1..2)
    ACCESS  read-only
    STATUS  mandatory
    DESCRIPTION
           "Defines the number of samples to put into a single frame
            before sending it to the other side.
            Depending on isarIvcsIwfCodingAlgorithm this value can 
            be :
                 for g729 the value can be 1 to 2
                 for g723lo and g723hi it must be 1."
    ::= { isarIvcsIwfRoEntry  8 }

isarIvcsIwfRoSendFrHeader OBJECT-TYPE
    SYNTAX  INTEGER {
                      noFrHeaderSend(1),
                      frHeaderSend(2)
            }
    ACCESS  read-only
    STATUS  mandatory
    DESCRIPTION
           "Depending on the value a frame relay header will be composed
            and put in front of the compressed data.  The value is not
            used at the moment and will allways be noFrHeaderSend."
    DEFVAL { noFrHeaderSend }
    ::= { isarIvcsIwfRoEntry  9 }

isarIvcsIwfRoPhysSlotId OBJECT-TYPE
    SYNTAX  INTEGER (1..3)
    ACCESS  read-only
    STATUS  mandatory
    DESCRIPTION
           "Slot Id of the Voice Compression Module (VCM) where the
            (de)compression will take place.
            
            When an Iwf is created on the E1/T1 port of a particular VCM,
            only the Slot Id of this VCM can be selected.
            
            When an Iwf is created on the E1/T1 port of the MAMO,
            any valid VCM Slot Id can be selected.
            
            Information about the number of available channels per VCM can
            be found in isarIspeechProcTable MIB."
    ::= { isarIvcsIwfRoEntry  10 }

isarIvcsIwfRoPhysStackNo OBJECT-TYPE
    SYNTAX  INTEGER (0..63)
    ACCESS  read-only
    STATUS  mandatory
    DESCRIPTION
           "Stack number of the Voice Compression Module (VCM) where the
            (de)compression will take place."
    ::= { isarIvcsIwfRoEntry  11 }

isarIvcsIwfRoOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "The operational state of the interworking function.
            Refer to RFC 2233 for the different states."
    ::= { isarIvcsIwfRoEntry  13 }


isarIvcsIwfRoRowStatus OBJECT-TYPE
    SYNTAX  INTEGER {
                      -- the following two values are states:
                      -- these values may be read or written
                      active(1),
                      notInService(2),
 
                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIvcsIwfRoEntry  14 }

isarIvcsIwfRoPhysPortId OBJECT-TYPE
    SYNTAX  INTEGER
    ACCESS  read-only
    STATUS  mandatory
    DESCRIPTION
           "The physical port ID of the connection.
            This is the same as isarIifphysPortId in the corresponding
            isarIifXEntry of the used lower layer."
    ::= { isarIvcsIwfRoEntry  15 }

isarIvcsIwfRoDsx0BundleMap OBJECT-TYPE
    SYNTAX  INTEGER
    ACCESS  read-only
    STATUS  mandatory
    DESCRIPTION
           "A bitmap that indicates which ds0 channels belong to
            this bundle.
            This is the same as isarIdsx0BundleMap in the corresponding
            isarIdsx0BundleEntry."
    ::= { isarIvcsIwfRoEntry  16 }


-- vcs iwf read-only mapping

isarIvcsIwfMappingRoTable OBJECT-TYPE
    SYNTAX  SEQUENCE OF IsarIvcsIwfMappingRoEntry
    ACCESS  not-accessible
    STATUS  mandatory
    DESCRIPTION
           "The vcsIwf mapping read-only table is used to map the IWF index
            into the index of the corresponding entry in the
            isarIvcsIwfRoTable."
    ::= { isarIvcsMIBObjects  5 }

isarIvcsIwfMappingRoEntry OBJECT-TYPE
    SYNTAX  IsarIvcsIwfMappingRoEntry
    ACCESS  not-accessible
    STATUS  mandatory
    DESCRIPTION
           "An entry in the vcsIwf mapping Rotable."
    INDEX   { isarIvcsIwfRoConnIndex }
    ::= { isarIvcsIwfMappingRoTable  1 }

IsarIvcsIwfMappingRoEntry ::=
    SEQUENCE {
      isarIvcsIwfMapRoVoiceBundle
        INTEGER
    }

isarIvcsIwfMapRoVoiceBundle OBJECT-TYPE
    SYNTAX  INTEGER
    ACCESS  read-only
    STATUS  mandatory
    DESCRIPTION
           "Mapped index."
    ::= { isarIvcsIwfMappingRoEntry  1 }



-- trap defined in isarIiwfMIBObjects

--
-- ISAR vcsMIBObjects : end
--




-- This file cannot be used to create SNMP agent.
-- The file isarOneFile.my has to be used to create the agent.


-- isarIiwfMIBObjects   OBJECT IDENTIFIER ::= { isar  24 }


--
-- ISAR iwfMIBObjects : begin
--
-- enterprise MIB for ISAR
-- The MIB is written for SNMPv1.

-- next IWF index value

isarIiwfNextConnIndex OBJECT-TYPE
    SYNTAX  INTEGER (1025..2147483647)
    ACCESS  not-accessible
    STATUS  mandatory
    DESCRIPTION
           "This object is used to assist IAD4700 in selecting
            a value for isarI<xxx>IwfConnIndex.  
            IAD4700 has to GET this index before creating a row in 
            one of the isarI<xxx>IwfConnectionTables or 
            isarI<xxx>IwfTables.
            The value 0-1024 is reserved (see ifXEntry)."
    ::= { isarIiwfMIBObjects  1 }



isarIfrAtmIwfTraps OBJECT IDENTIFIER        ::= { isarIiwfMIBObjects 2 }
isarIthdlcsIwfTraps OBJECT IDENTIFIER       ::= { isarIiwfMIBObjects 3 }
isarIvcsIwfTraps OBJECT IDENTIFIER          ::= { isarIiwfMIBObjects 4 }
isarIcesIwfTraps OBJECT IDENTIFIER          ::= { isarIiwfMIBObjects 5 }
isarIlanisIwfTraps OBJECT IDENTIFIER        ::= { isarIiwfMIBObjects 6 }
isarIsignallingIwfTraps OBJECT IDENTIFIER   ::= { isarIiwfMIBObjects 7 }
                                    
isarIfrAtmSiIwfConnStatusChange TRAP-TYPE
    ENTERPRISE  isarIfrAtmIwfTraps
    VARIABLES   { isarIfrAtmSiIwfConnAtmIfIndex, 
                  isarIfrAtmSiIwfConnAtmVpi, 
                  isarIfrAtmSiIwfConnAtmVci,
                  isarIfrAtmSiIwfConnAdminStatus,
                  isarIfrAtmSiIwfConnOperStatus,
                  isarIfrAtmSiIwfConnOperStatus
                 }
    DESCRIPTION
           "An indication that the operation status of this interworking
            connection has changed.
            A status change is given when :
            1. isarIfrAtmSiIwfConnAdminStatus is 'up' and 
               isarIfrAtmSiIwfConnOperStatus is going 'down'
            2. when isarIfrAtmSiIwfConnOperStatus is leaving the 'down' 
               state.
            The first isarIfrAtmSiIwfConnOperStatus is the previous state,
            the second isarIfrAtmSiIwfConnOperStatus is the new state."
    ::= 1

isarIfrAtmNiIwfConnStatusChange TRAP-TYPE
    ENTERPRISE  isarIfrAtmIwfTraps
    VARIABLES   { isarIfrAtmNiIwfConnFrLPortIfIndex, 
                  isarIfrAtmNiIwfConnDlci, 
                  isarIfrAtmNiIwfConnAtmIfIndex, 
                  isarIfrAtmNiIwfConnAtmVpi, 
                  isarIfrAtmNiIwfConnAtmVci,
                  isarIfrAtmNiIwfConnAdminStatus,
                  isarIfrAtmNiIwfConnOperStatus,
                  isarIfrAtmNiIwfConnOperStatus
                 }
    DESCRIPTION
           "An indication that the operation status of this interworking
            connection has changed.
            A status change is given when :
            1. isarIfrAtmNiIwfConnAdminStatus is 'up' and 
               isarIfrAtmNiIwfConnOperStatus is going 'down'
            2. when isarIfrAtmNiIwfConnOperStatus is leaving the 'down' 
               state.
            The first isarIfrAtmNiIwfConnOperStatus is the previous state,
            the second isarIfrAtmNiIwfConnOperStatus is the new state."
    ::= 2


isarIthdlcsIwfStatusChange TRAP-TYPE
    ENTERPRISE  isarIthdlcsIwfTraps
    VARIABLES   { isarIthdlcsIwfServiceIndex, 
                  isarIthdlcsIwfHdlcIfIndex,
                  isarIthdlcsIwfAdminStatus,
                  isarIthdlcsIwfOperStatus,
                  isarIthdlcsIwfOperStatus
                 }
    DESCRIPTION
           "An indication that the operation status of this interworking
            function has changed.
            A status change is given when :
            1. isarIthdlcsIwfAdminStatus is 'up' and 
               isarIthdlcsIwfOperStatus is going 'down'
            2. when isarIthdlcsIwfOperStatus is leaving the 'down' 
               state.
            The first isarIthdlcsIwfOperStatus is the previous state,
            the second isarIthdlcsIwfOperStatus is the new state."
    ::= 1

isarIvcsIwfStatusChange TRAP-TYPE
    ENTERPRISE  isarIvcsIwfTraps
    VARIABLES   { isarIvcsIwfVoiceBundle,
                  isarIvcsIwfAdminStatus,
                  isarIvcsIwfOperStatus,
                  isarIvcsIwfOperStatus
                 }
    DESCRIPTION
           "An indication that the operation status of this interworking
            function has changed.
            A status change is given when :
            1. isarIvcsIwfAdminStatus is 'up' and 
               isarIvcsIwfOperStatus is going 'down'
            2. when isarIvcsIwfOperStatus is leaving the 'down' 
               state.
            The first isarIvcsIwfOperStatus is the previous state,
            the second isarIvcsIwfOperStatus is the new state."
    ::= 1

isarIcesIwfStatusChange TRAP-TYPE
    ENTERPRISE  isarIcesIwfTraps
    VARIABLES   { isarIatmfCESCbrIndex,
                  isarIatmfCESAtmIndex,
                  isarIatmfCESAtmVpi,
                  isarIatmfCESAtmVci,
                  isarIatmfCESAdminStatus,
                  isarIatmfCESOperStatus,
                  isarIatmfCESOperStatus
                 }
    DESCRIPTION
           "An indication that the operation status of this interworking
            function has changed.
            A status change is given when :
            1. isarIatmfCESAdminStatus is 'up' and 
               isarIatmfCESOperStatus is going 'down'
            2. when isarIatmfCESOperStatus is leaving the 'down' 
               state.
            The first isarIatmfCESOperStatus is the previous state,
            the second isarIatmfCESOperStatus is the new state."
    ::= 1

isarIcesIwfThresholdExceeded TRAP-TYPE
    ENTERPRISE  isarIcesIwfTraps
    VARIABLES   { isarIatmfCESCbrIndex,
                  isarIatmfCESAtmIndex,
                  isarIatmfCESAtmVpi,
                  isarIatmfCESAtmVci
                 }
    DESCRIPTION
           "An indication that a counter threshold of this connection has been 
            exceeded."
    ::= 2


isarIlanisIwfStatusChange TRAP-TYPE
    ENTERPRISE  isarIlanisIwfTraps
    VARIABLES   { isarIlanisIwfServiceIndex,
                  isarIlanisIwfPortNumber,
                  isarIlanisIwfAdminStatus,
                  isarIlanisIwfOperStatus,
                  isarIlanisIwfOperStatus
                 }
    DESCRIPTION
           "An indication that the operation status of this interworking
            function has changed.
            A status change is given when :
            1. isarIlanisIwfAdminStatus is 'up' and 
               isarIlanisIwfOperStatus is going 'down'
            2. when isarIlanisIwfOperStatus is leaving the 'down' 
               state.
            The first isarIlanisIwfOperStatus is the previous state,
            the second isarIlanisIwfOperStatus is the new state."
    ::= 1


isarIsignallingIwfStatusChange TRAP-TYPE
    ENTERPRISE  isarIsignallingIwfTraps
    VARIABLES   { isarIsignallingIwfAtmIfIndex,
                  isarIsignallingIwfAtmVpi,
                  isarIsignallingIwfAtmVci,
                  isarIsignallingIwfAdminStatus,
                  isarIsignallingIwfOperStatus,
                  isarIsignallingIwfOperStatus
                 }
    DESCRIPTION
           "An indication that the operation status of this interworking
            function has changed.
            A status change is given when :
            1. isarIsignallingIwfAdminStatus is 'up' and 
               isarIsignallingIwfOperStatus is going 'down'
            2. when isarIsignallingIwfOperStatus is leaving the 'down' 
               state.
            The first isarIsignallingIwfOperStatus is the previous state,
            the second isarIsignallingIwfOperStatus is the new state."
    ::= 1




--
-- ISAR iwfMIBObjects : end
--
-- This file cannot be used to create SNMP agent.
-- The file isarOneFile.my has to be used to create the agent.


-- isarIfrAtmIwfMIBObjects   OBJECT IDENTIFIER ::= { isar  23 }


--
-- ISAR  frAtmIwfMIBObjects : begin
--
-- This MIB is based on the MIB described in IETF draft
-- draft-ietf-frnetmib-atmiwf-00.
-- The MIB is written for SNMPv1.
-- The textual conventions have been replaced by their base types
-- (because the 45020 does not know these textual conventions).




-- Replaced textual conventions

-- imported textual conventions


-- AtmVpIdentifier : The VPI value for a VPL or VCL. The value VPI=0
--                   is only allowed for a VCL. For ATM UNIs supporting
--                   VPCs the VPI value ranges from 0 to 255.  The VPI
--                   value 0 is supported for ATM UNIs conforming to
--                   the ATM Forum UNI 4.0 Annex 8 (Virtual UNIs)
--                   specification. For ATM UNIs supporting VCCs the
--                   VPI value ranges from 0 to 255.  For ATM NNIs the
--                   VPI value ranges from 0 to 4095.  The maximum VPI
--                   value cannot exceed the value allowable by
--                   atmInterfaceMaxVpiBits defined in ATM-MIB.
--                   See draft-ietf-atommib-atm2TC-08.
-- is replaced by INTEGER (0..4095)
-- originally used in : frAtmIwfConnVpi

-- AtmVcIdentifier : The VCI value for a VCL. The maximum VCI value
--                   cannot exceed the value allowable by
--                   atmInterfaceMaxVciBits defined in ATM-MIB.
--                   See draft-ietf-atommib-atm2TC-08.
-- is replaced by INTEGER (0..65535)
-- originally used in : frAtmIwfConnVci

-- AtmAddr : An ATM address. The semantics are implied by
--           the length. The address types are: - no address (0 octets)
--           - E.164 (8 octets) - NSAP (20 octets) In addition, when
--           subaddresses are used the AtmAddr may represent the
--           concatenation of address and subaddress. The associated
--           address types are: - E.164, E.164 (16 octets) - E.164,
--           NSAP (28 octets) - NSAP, NSAP (40 octets) Address lengths
--           other than defined in this definition imply address types
--           defined elsewhere.  Note: The E.164 address is encoded in
--           BCD format.  See draft-ietf-atommib-atm2TC-08.
--           Display hint '1x'
-- is replaced by OCTET STRING (SIZE(0..20))
-- originally used in : frAtmIwfConnAtmAddress

-- InterfaceIndex : A unique value, greater than zero, for each interface
--                  or interface sub-layer in the managed system.  It is
--                  recommended that values are assigned contiguously
--                  starting from 1.  The value for each interface sub-
--                  layer must remain constant at least from one re-
--                  initialization of the entity's network management
--                 system to the next re-initialization.  See RFC2233.
-- is replaced by INTEGER  (1..2147483647)
-- originally used in :  frAtmIwfConnFrPort

-- RowStatus : The RowStatus textual convention is used to manage the
--             creation and deletion of conceptual rows. See RFC1903.
-- is replaced by INTEGER {...}
-- originally used in : frAtmIwfConnRowStatus



-- textual conventions defined in the document

-- Dlci : This data type is a DLCI for a PVC segment end-point.
-- is replaced by INTEGER
-- originally used in : frAtmIwfConnDlci

-- FrAddress : This data type is a Q.931 Frame Relay address.
-- is replaced by INTEGER
-- originally used in : frAtmIwfConnFrAddress




-- The Frame Relay/ATM PVC Service Interworking connection table

isarIfrAtmSiIwfConnectionTable OBJECT-TYPE
    SYNTAX  SEQUENCE OF IsarIfrAtmSiIwfConnectionEntry
    ACCESS  not-accessible
    STATUS  mandatory
    DESCRIPTION
           "A table in which each row represents a Frame Relay/ATM
            interworking connection.
            
            When a row in this table is created, it is necessary to
            create an entry in the isarIfrAtmSiIwfMappingTable
            (inverse mapping of index).

            At the same time two other tables must be updated :
            1. set field isarIfrPVCEndptConnectIdentifier of the
               corresponding entry in isarIfrPVCEndptTable with the
               value of isarIfrAtmSiIwfConnIndex
            2. set field isarIatmVclCrossConnectIdentifier of the
               corresponding entry in IsarIatmVclEntry with the
               value of isarIfrAtmSiIwfConnIndex and
               set field isarIatmVclServiceType  of the
               corresponding entry in IsarIatmVclEntry to 'frs'."
    ::= { isarIfrAtmIwfMIBObjects  1 }

isarIfrAtmSiIwfConnectionEntry OBJECT-TYPE
    SYNTAX  IsarIfrAtmSiIwfConnectionEntry
    ACCESS  not-accessible
    STATUS  mandatory
    DESCRIPTION
           "An entry for an interworking connection between a Frame
            Relay PVC and an ATM PVC."
    INDEX   { isarIfrAtmSiIwfConnAtmIfIndex,
              isarIfrAtmSiIwfConnAtmVpi,
              isarIfrAtmSiIwfConnAtmVci }
    ::= { isarIfrAtmSiIwfConnectionTable  1 }


IsarIfrAtmSiIwfConnectionEntry ::=
    SEQUENCE {
      isarIfrAtmSiIwfConnFrLPortIfIndex
        INTEGER,

      isarIfrAtmSiIwfConnDlci
        INTEGER,

      isarIfrAtmSiIwfConnAtmIfIndex
        INTEGER,

      isarIfrAtmSiIwfConnAtmVpi
        INTEGER,

      isarIfrAtmSiIwfConnAtmVci
        INTEGER,

      isarIfrAtmSiIwfConnAdminStatus
        INTEGER,

      isarIfrAtmSiIwfConnOperStatus
        INTEGER,

      isarIfrAtmSiIwfConnLastChange
        TimeTicks,

      isarIfrAtmSiIwfConnDeToClpMappingMode
        INTEGER,

      isarIfrAtmSiIwfConnClpToDeMappingMode
        INTEGER,

      isarIfrAtmSiIwfConnCongestionMappingMode
        INTEGER,

      isarIfrAtmSiIwfConnEncapsulationMappingMode
        INTEGER,

      isarIfrAtmSiIwfConnEncapsulationMappings
        INTEGER,
        
      isarIfrAtmSiIwfConnFragAndReassEnabled
        INTEGER,

      isarIfrAtmSiIwfConnArpTranslationEnabled
        INTEGER,

      isarIfrAtmSiIwfConnFrAddress
        OCTET STRING,

      isarIfrAtmSiIwfConnFrAddressType
        INTEGER,

      isarIfrAtmSiIwfConnAtmAddress
        OCTET STRING,

      isarIfrAtmSiIwfConnAtmAddressType
        INTEGER,

      isarIfrAtmSiIwfConnAtmSubAddress
        OCTET STRING,

      isarIfrAtmSiIwfConnAtmSubAddressType
        INTEGER,

      isarIfrAtmSiIwfConnRowStatus
        INTEGER,

      isarIfrAtmSiIwfConnServiceIndex
        INTEGER,

      isarIfrAtmSiIwfConnIndex
        INTEGER,

      isarIfrAtmSiIwfConnAAL5InFrames
        Counter,

      isarIfrAtmSiIwfConnAAL5OutFrames
        Counter,

      isarIfrAtmSiIwfConnAAL5InOctets
	Counter,

      isarIfrAtmSiIwfConnAAL5OutOctets
	Counter,

      isarIfrAtmSiIwfConnAAL5InDiscards
	Counter,

      isarIfrAtmSiIwfConnAAL5OutDiscards
	Counter,

      isarIfrAtmSiIwfConnAAL5InUnkProts
	Counter,

      isarIfrAtmSiIwfConnAAL5ArpNakDiscards
	Counter,

      isarIfrAtmSiIwfConnFrInFrames
	Counter,

      isarIfrAtmSiIwfConnFrOutFrames
	Counter,

      isarIfrAtmSiIwfConnFrInOctets
	Counter,

      isarIfrAtmSiIwfConnFrOutOctets
	Counter,

      isarIfrAtmSiIwfConnFrInDiscards
	Counter,

      isarIfrAtmSiIwfConnFrOutDiscards
	Counter
    }


isarIfrAtmSiIwfConnFrLPortIfIndex OBJECT-TYPE
    SYNTAX  INTEGER
    ACCESS  read-write
    STATUS  mandatory
    DESCRIPTION
           "The index in the ifTable that identifies the Frame Relay
            port for this interworking connection.
            Modify of this value is not allowed.
            The SNMPv2 MAX-ACCESS is read(-only)-create."
    ::= { isarIfrAtmSiIwfConnectionEntry  1 }

isarIfrAtmSiIwfConnDlci OBJECT-TYPE
    SYNTAX  INTEGER (0..1023)
    ACCESS  read-write
    STATUS  mandatory
    DESCRIPTION
           "The DLCI that identifies the Frame Relay PVC end point
            for this interworking connection.
            Modify of this value is not allowed.
            The SNMPv2 MAX-ACCESS is read(-only)-create."
    DEFVAL  { 16 }
    ::= { isarIfrAtmSiIwfConnectionEntry  2 }

isarIfrAtmSiIwfConnAtmIfIndex OBJECT-TYPE
    SYNTAX  INTEGER
    ACCESS  read-only
    STATUS  mandatory
    DESCRIPTION
           "The index in the ifTable that identifies the ATM
            port for this interworking connection."
    ::= { isarIfrAtmSiIwfConnectionEntry  3 }

isarIfrAtmSiIwfConnAtmVpi OBJECT-TYPE
    SYNTAX  INTEGER (0..4095)
    ACCESS  read-only
    STATUS  mandatory
    DESCRIPTION
           "The VPI of the ATM PVC end point for this interworking
            connection."
    ::= { isarIfrAtmSiIwfConnectionEntry  4 }

isarIfrAtmSiIwfConnAtmVci OBJECT-TYPE
    SYNTAX  INTEGER (0..65535)
    ACCESS  read-only
    STATUS  mandatory
    DESCRIPTION
           "The VCI of the ATM PVC end point for this interworking
            connection."
    ::= { isarIfrAtmSiIwfConnectionEntry  5 }

isarIfrAtmSiIwfConnAdminStatus OBJECT-TYPE
    SYNTAX  INTEGER {
                      up(1),
                      down(2)
            }
    ACCESS  read-write
    STATUS  mandatory
    DESCRIPTION
           "The desired operational state for this interworking 
            connection.
            The SNMPv2 MAX-ACCESS is read-create."
    ::= { isarIfrAtmSiIwfConnectionEntry  6 }

isarIfrAtmSiIwfConnOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "The current operational state of this interworking 
            connection.
            Refer to RFC 2233 for the description of the states."
    ::= { isarIfrAtmSiIwfConnectionEntry  7 }

isarIfrAtmSiIwfConnLastChange OBJECT-TYPE
    SYNTAX  TimeTicks
    ACCESS  read-only
    STATUS  mandatory
    DESCRIPTION
           "The value of sysUpTime at the time this interworking
            connection entered its current operational state.
            If the current state was entered prior to the last
            re-initialization of the local network management
            subsystem, then this object contains a zero value."
    ::= { isarIfrAtmSiIwfConnectionEntry  8 }

isarIfrAtmSiIwfConnDeToClpMappingMode OBJECT-TYPE
    SYNTAX  INTEGER {
                      mode1(1),
                      mode2(2)
            }
    ACCESS  read-only
    STATUS  mandatory
    DESCRIPTION
           "This object describes which mode of translation is in
            use for loss priority mapping in the Frame Relay to ATM
            direction.
            IAD4700 : only 'mode1' is valid."
--  REFERENCE "Section 4.2.1 of FRF.8 [9]."
    DEFVAL  { mode1 }
    ::= { isarIfrAtmSiIwfConnectionEntry  9 }

isarIfrAtmSiIwfConnClpToDeMappingMode OBJECT-TYPE
    SYNTAX  INTEGER {
                      mode1(1),
                      mode2(2)
            }
    ACCESS  read-only
    STATUS  mandatory
    DESCRIPTION
           "This object describes which mode of translation is in
            use for loss priority mapping in the ATM to Frame Relay
            direction.
            IAD4700 : only 'mode1' is valid."
--  REFERENCE "Section 4.2.2 of FRF.8 [9]."
    DEFVAL  { mode1 }
    ::= { isarIfrAtmSiIwfConnectionEntry  10 }

isarIfrAtmSiIwfConnCongestionMappingMode OBJECT-TYPE
    SYNTAX  INTEGER {
                      mode1(1),
                      mode2(2)
            }
    ACCESS  read-write
    STATUS  mandatory
    DESCRIPTION
           "This object describes which mode of translation is in
            use for forward congestion indication mapping in the
            Frame Relay to ATM direction.
            Modify of this value is not allowed.
            The SNMPv2 MAX-ACCESS is read(-only)-create."
--  REFERENCE "Section 4.3.1.1 of FRF.8 [9]."
    DEFVAL  { mode1 }
    ::= { isarIfrAtmSiIwfConnectionEntry  11 }

isarIfrAtmSiIwfConnEncapsulationMappingMode OBJECT-TYPE
    SYNTAX  INTEGER {
                      transparentMode(1),
                      translationMode(2)
            }
    ACCESS  read-write
    STATUS  mandatory
    DESCRIPTION
           "This object indicates whether the mapping of upper layer
            protocol encapsulation is enabled on this interworking
            connection as defined in section 5.3 of FRF.8 [9].
            At least one mapped protocol must be defined in
            isarIfrAtmSiIwfConnEncapsulationMappings when translation mode
            is enabled.
            Modify of this value is not allowed.
            The SNMPv2 MAX-ACCESS is read(-only)-create."
    DEFVAL  { transparentMode }
    ::= { isarIfrAtmSiIwfConnectionEntry  12 }

isarIfrAtmSiIwfConnEncapsulationMappings OBJECT-TYPE
    SYNTAX  INTEGER (1..31)
    ACCESS  read-write
    STATUS  mandatory
    DESCRIPTION
           "If upper layer protocol encapsulation mapping is enabled
            on this interworking connection, then this attribute
            enumerates which of the encapsulation mappings defined
            in section 5.3.1 of FRF.8 [9] are supported.
            The SNMPv2 SYNTAX of this object is BITS.  This syntax does
            not exist in SNMPv1 and is replaced by INTEGER.
            Description of the bit positions :
              bit         meaning
               0      bridged802.3 with FCS     PID: 0x00-01
               1      bridged802.3 no FCS       PID: 0x00-07
               2      bridged802.5 with FCS     PID: 0x00-03
               3      bridged802.5 no FCS       PID: 0x00-09
               4      routedIp                  NLPID: OxCC

            At least one bit must be set when translation mode is
            enabled.
            Each listed protocol corresponds with an entry
            in the isarIfrAtmSiIwfProtocolTable.
            It is possible that several bits are set at the same time.
            The SNMPv2 MAX-ACCESS is read-create."
    ::= { isarIfrAtmSiIwfConnectionEntry  13 }

isarIfrAtmSiIwfConnFragAndReassEnabled OBJECT-TYPE
    SYNTAX  INTEGER {
                      enabled(1),
                      notEnabled(2)
            }
    ACCESS  read-only
    STATUS  mandatory
    DESCRIPTION
           "The attribute indicates whether fragmentation and
            reassembly is enabled for this connection as described
            in section 5.3.1.4 of FRF.8 [9].
            IAD4700 : always notEnabled."
    DEFVAL  { notEnabled }
    ::= { isarIfrAtmSiIwfConnectionEntry  14 }

isarIfrAtmSiIwfConnArpTranslationEnabled OBJECT-TYPE
    SYNTAX  INTEGER {
                      enabled(1),
                      notEnabled(2)
            }
    ACCESS  read-only
    STATUS  mandatory
    DESCRIPTION
           "The attribute indicates whether ARP translation is enabled
            for this connection as described in section 5.4 of
            FRF.8 [9].
            IAD4700 : always notEnabled."
    DEFVAL  { notEnabled }
    ::= { isarIfrAtmSiIwfConnectionEntry  15 }

isarIfrAtmSiIwfConnFrAddress OBJECT-TYPE
    SYNTAX  OCTET STRING (SIZE(0..32))
    ACCESS  read-write
    STATUS  mandatory
    DESCRIPTION
           "The Frame Relay Q.933 address, in E.164 format, if known,
            of the Frame Relay Service User end point.
            Modify of this value is not allowed.
            The SNMPv2 MAX-ACCESS is read(-only)-create."
    DEFVAL  { "" }
    ::= { isarIfrAtmSiIwfConnectionEntry  16 }

isarIfrAtmSiIwfConnFrAddressType OBJECT-TYPE
    SYNTAX  INTEGER {
	              null(1),
	              e164(2)
            }
    ACCESS  read-write
    STATUS  mandatory
    DESCRIPTION
           "The type of the address in isarIfrAtmSiIwfConnFrAddress.
            Modify of this value is not allowed.
            The SNMPv2 MAX-ACCESS is read(-only)-create."
    ::= { isarIfrAtmSiIwfConnectionEntry  17 }

isarIfrAtmSiIwfConnAtmAddress OBJECT-TYPE
    SYNTAX  OCTET STRING (SIZE(0..20))
    ACCESS  read-write
    STATUS  mandatory
    DESCRIPTION
           "The ATM Q.2931 address,  in E.164 or
            NSAP format, if known, of the ATM Service User end point.
            The ATM address used by the network entity.  The address
            types are: no address (0 octets), E.164 (8 octets), and
            NSAP-encoded ATM Endsystem Address (20 octets).
            Note: The E.164 address is encoded in BCD format.
            Modify of this value is not allowed.
            The SNMPv2 MAX-ACCESS is read(-only)-create."
    DEFVAL  { "" }
    ::= { isarIfrAtmSiIwfConnectionEntry  18 }

isarIfrAtmSiIwfConnAtmAddressType OBJECT-TYPE
    SYNTAX  INTEGER {
		      null(1),
		      e164(2),
		      nsap(4)
	    }
    ACCESS  read-write
    STATUS  mandatory
    DESCRIPTION
	   "The type of the ATM address in isarIfrAtmSiIwfConnAtmAddress.
            Modify of this value is not allowed.
            The SNMPv2 MAX-ACCESS is read(-only)-create."
   ::= { isarIfrAtmSiIwfConnectionEntry  19 }

isarIfrAtmSiIwfConnAtmSubAddress OBJECT-TYPE
    SYNTAX  OCTET STRING (SIZE(0..20))
    ACCESS  read-write
    STATUS  mandatory
    DESCRIPTION
           "The ATM Q.2931 subaddress,  in E.164 or
            NSAP format, if known, of the ATM Service User end point.
            The ATM address used by the network entity.  The address
            types are: no address (0 octets), E.164 (8 octets), and
            NSAP-encoded ATM Endsystem Address (20 octets).
            Note: The E.164 address is encoded in BCD format.
            Modify of this value is not allowed.
            The SNMPv2 MAX-ACCESS is read(-only)-create."
    DEFVAL  { "" }
    ::= { isarIfrAtmSiIwfConnectionEntry  20 }

isarIfrAtmSiIwfConnAtmSubAddressType OBJECT-TYPE
    SYNTAX  INTEGER {
		      null(1),
		      e164(2),
		      nsap(4)
	    }
    ACCESS   read-write
    STATUS   mandatory
    DESCRIPTION
     	   "The type of the ATM subaddress in 
     	    isarIfrAtmSiIwfConnAtmSubAddress.
            Modify of this value is not allowed.
            The SNMPv2 MAX-ACCESS is read(-only)-create."
   ::= { isarIfrAtmSiIwfConnectionEntry  21 }

isarIfrAtmSiIwfConnRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
                    }
    ACCESS  read-write
    STATUS  mandatory
    DESCRIPTION
           "This object is used to create and delete rows in the
            isarIfrAtmSiIwfConnectionTable.
            The SNMPv2 MAX-ACCESS is read-create."
    ::= { isarIfrAtmSiIwfConnectionEntry  22 }


isarIfrAtmSiIwfConnServiceIndex OBJECT-TYPE
    SYNTAX  INTEGER
    ACCESS  read-only
    STATUS  mandatory
    DESCRIPTION
           "The index of the service to which this interworking function
            belongs.
            This is the same index as serviceIndex of isarIserviceTable and
            can be found via isarIfrAtmSiIwfConnFrLPortIfIndex."
    ::= { isarIfrAtmSiIwfConnectionEntry  23 }

isarIfrAtmSiIwfConnIndex OBJECT-TYPE
    SYNTAX  INTEGER
    ACCESS  read-only
    STATUS  mandatory
    DESCRIPTION
           "The value of this object is equal to the
            isarIiwfNextConnIndex obtained (by IAD4700) to uniqely identify
            this IWF."
    ::= { isarIfrAtmSiIwfConnectionEntry  24 }

isarIfrAtmSiIwfConnAAL5InFrames	OBJECT-TYPE
    SYNTAX  Counter
    ACCESS  read-only
    STATUS  mandatory
    DESCRIPTION
           "The number of AAL-5 PDU's received by FRF.8 on this
            interworking connection."
    ::= { isarIfrAtmSiIwfConnectionEntry 25 }

isarIfrAtmSiIwfConnAAL5OutFrames	OBJECT-TYPE
    SYNTAX  Counter
    ACCESS  read-only
    STATUS  mandatory
    DESCRIPTION
           "The number of AAL-5 PDU's transmitted by FRF.8 on this
            interworking connection."
    ::= { isarIfrAtmSiIwfConnectionEntry 26 }

isarIfrAtmSiIwfConnAAL5InOctets  OBJECT-TYPE
    SYNTAX  Counter
    ACCESS  read-only
    STATUS  mandatory
    DESCRIPTION
           "The number of AAL-5 octets received by FRF.8 on this
            interworking connection."
    ::= { isarIfrAtmSiIwfConnectionEntry 27 }

isarIfrAtmSiIwfConnAAL5OutOctets  OBJECT-TYPE
    SYNTAX  Counter
    ACCESS  read-only
    STATUS  mandatory
    DESCRIPTION
           "The number of AAL-5 octets transmitted by FRF.8 on this
            interworking connection."
    ::= { isarIfrAtmSiIwfConnectionEntry 28 }

isarIfrAtmSiIwfConnAAL5InDiscards  OBJECT-TYPE
    SYNTAX  Counter
    ACCESS  read-only
    STATUS  mandatory
    DESCRIPTION
           "The number of AAL-5 PDU's discarded on input by FRF.8 on this
            interworking connection."
    ::= { isarIfrAtmSiIwfConnectionEntry 29 }

isarIfrAtmSiIwfConnAAL5OutDiscards  OBJECT-TYPE
    SYNTAX  Counter
    ACCESS  read-only
    STATUS  mandatory
    DESCRIPTION
           "The number of AAL-5 PDU's discarded on output by FRF.8 on this
            interworking connection."
    ::= { isarIfrAtmSiIwfConnectionEntry 30 }

isarIfrAtmSiIwfConnAAL5InUnkProts  OBJECT-TYPE
    SYNTAX  Counter
    ACCESS  read-only
    STATUS  mandatory
    DESCRIPTION
           "The number of AAL-5 PDU's received with an unknown protocol 
            type by FRF.8 on this interworking connection."
    ::= { isarIfrAtmSiIwfConnectionEntry 31 }

isarIfrAtmSiIwfConnAAL5ArpNakDiscards  OBJECT-TYPE
    SYNTAX  Counter
    ACCESS  read-only
    STATUS  mandatory
    DESCRIPTION
           "The number of AAL-5 ARP NAK PDU's that are discarded by FRF.8
            on this interworking connection."
    ::= { isarIfrAtmSiIwfConnectionEntry 32 }

isarIfrAtmSiIwfConnFrInFrames  OBJECT-TYPE
    SYNTAX  Counter
    ACCESS  read-only
    STATUS  mandatory
    DESCRIPTION
           "The number of Frame Relay frames received by FRF.8 from Frame
            Relay subsystem for this interworking connection."
    ::= { isarIfrAtmSiIwfConnectionEntry 33 }

isarIfrAtmSiIwfConnFrOutFrames  OBJECT-TYPE
    SYNTAX  Counter
    ACCESS  read-only
    STATUS  mandatory
    DESCRIPTION
           "The number of Frame Relay frames sent from FRF.8 to the Frame
            Relay subsystem for this interworking connection."
    ::= { isarIfrAtmSiIwfConnectionEntry 34 }

isarIfrAtmSiIwfConnFrInOctets  OBJECT-TYPE
    SYNTAX  Counter
    ACCESS  read-only
    STATUS  mandatory
    DESCRIPTION
           "The number of Frame Relay octets received by FRF.8 from the
            Frame Relay subsystem for this interworking connection."
    ::= { isarIfrAtmSiIwfConnectionEntry 35 }

isarIfrAtmSiIwfConnFrOutOctets  OBJECT-TYPE
    SYNTAX  Counter
    ACCESS  read-only
    STATUS  mandatory
    DESCRIPTION
           "The number of Frame Relay octets sent by FRF.8 to the Frame
            Relay subsystem for this interworking connection."
    ::= { isarIfrAtmSiIwfConnectionEntry 36 }

isarIfrAtmSiIwfConnFrInDiscards  OBJECT-TYPE
    SYNTAX  Counter
    ACCESS  read-only
    STATUS  mandatory
    DESCRIPTION
           "The number of Frame Relay frames received from the Frame
            Relay subsystem then discarded by FRF.8 for this 
            interworking connection."
    ::= { isarIfrAtmSiIwfConnectionEntry 37 }

isarIfrAtmSiIwfConnFrOutDiscards  OBJECT-TYPE
    SYNTAX  Counter
    ACCESS  read-only
    STATUS  mandatory
    DESCRIPTION
           "The number of Frame Relay frames discarded by FRF.8 rather
            than sending to the Frame Relay subsystem for this interworking
            connection."
    ::= { isarIfrAtmSiIwfConnectionEntry 38 }



-- The Frame Relay/ATM PVC Service Interworking Protocol Table

isarIfrAtmSiIwfProtocolTable OBJECT-TYPE
    SYNTAX  SEQUENCE OF IsarIfrAtmSiIwfProtTblEntry
    ACCESS  not-accessible
    STATUS  mandatory
    DESCRIPTION
           "A table in which each row represents an enabled mapping for
            an encapsulated protocol for a Frame Relay/ATM Service
            Interworking connection.
            A connection can occur several times is the table.
            A connection can only occur in this table when in the 
            corresponding entry in the isarIfrAtmSiIwfConnTable the 
            EncapsulationMappingMode is set to translationMode.
            Entries in this table are created when corresponding bits
            are set in isarIfrAtmSiIwfConnEncapsulationMappings
            in the isarIfrAtmSiIwfConnTable."
    ::= { isarIfrAtmIwfMIBObjects  2 }

isarIfrAtmSiIwfProtTblEntry OBJECT-TYPE
    SYNTAX  IsarIfrAtmSiIwfProtTblEntry
    ACCESS  not-accessible
    STATUS  mandatory
    DESCRIPTION
           "An entry for an encapsulated protocol."
    INDEX   { isarIfrAtmSiIwfProtTblAtmIfIndex,
              isarIfrAtmSiIwfProtTblAtmVpi,
              isarIfrAtmSiIwfProtTblAtmVci,
              isarIfrAtmSiIwfProtTblProtocol }
    ::= { isarIfrAtmSiIwfProtocolTable  1 }


IsarIfrAtmSiIwfProtTblEntry ::=
    SEQUENCE {
      isarIfrAtmSiIwfProtTblAtmIfIndex
        INTEGER,

      isarIfrAtmSiIwfProtTblAtmVpi
        INTEGER,

      isarIfrAtmSiIwfProtTblAtmVci
        INTEGER,

      isarIfrAtmSiIwfProtTblProtocol
        INTEGER,

      isarIfrAtmSiIwfProtTblAAL5InFrames
        Counter,

      isarIfrAtmSiIwfProtTblAAL5OutFrames
        Counter,

      isarIfrAtmSiIwfProtTblAAL5InOctets
        Counter,

      isarIfrAtmSiIwfProtTblAAL5OutOctets
        Counter,

      isarIfrAtmSiIwfProtTblAAL5OutDiscards
        Counter,

      isarIfrAtmSiIwfProtTblFrInFrames
        Counter,

      isarIfrAtmSiIwfProtTblFrOutFrames
        Counter,

      isarIfrAtmSiIwfProtTblFrInOctets
        Counter,

      isarIfrAtmSiIwfProtTblFrOutOctets
        Counter,

      isarIfrAtmSiIwfProtTblFrOutDiscards
      	Counter

    }

isarIfrAtmSiIwfProtTblAtmIfIndex  OBJECT-TYPE
    SYNTAX  INTEGER
    ACCESS  read-only
    STATUS  mandatory
    DESCRIPTION
           "The index in the ifTable that identifies the ATM
            port for this interworking connection."
    ::= { isarIfrAtmSiIwfProtTblEntry 1 }

isarIfrAtmSiIwfProtTblAtmVpi  OBJECT-TYPE
    SYNTAX  INTEGER
    ACCESS  read-only
    STATUS  mandatory
    DESCRIPTION
           "The VPI of the ATM PVC end point for this interworking
            connection."
    ::= { isarIfrAtmSiIwfProtTblEntry 2 }

isarIfrAtmSiIwfProtTblAtmVci  OBJECT-TYPE
    SYNTAX  INTEGER
    ACCESS  read-only
    STATUS  mandatory
    DESCRIPTION
           "The VCI of the ATM PVC end point for this interworking
            connection."
    ::= { isarIfrAtmSiIwfProtTblEntry 3 }

isarIfrAtmSiIwfProtTblProtocol  OBJECT-TYPE
    SYNTAX  INTEGER {
                      bridged8023Fcs(1),   --  PID: 0x00-01
                      bridged8023(2),      --  PID: 0x00-07
                      bridged8025Fcs(3),   --  PID: 0x00-03
                      bridged8025(4),      --  PID: 0x00-09
                      routedIp(5)          --  NLPID: OxCC
            }
    ACCESS  read-only
    STATUS  mandatory
    DESCRIPTION
           "The protocol(s) registered over this interworking connection."
    ::= { isarIfrAtmSiIwfProtTblEntry 4 }

isarIfrAtmSiIwfProtTblAAL5InFrames  OBJECT-TYPE
    SYNTAX  Counter
    ACCESS  read-only
    STATUS  mandatory
    DESCRIPTION
           "The number of AAL-5 PDU's received by FRF.8 of this protocol
            type on this interworking connection."
    ::= { isarIfrAtmSiIwfProtTblEntry 5 }

isarIfrAtmSiIwfProtTblAAL5OutFrames  OBJECT-TYPE
    SYNTAX  Counter
    ACCESS  read-only
    STATUS  mandatory
    DESCRIPTION
           "The number of AAL-5 PDU's transmitted by FRF.8 of this protocol
            type on this interworking connection."
    ::= { isarIfrAtmSiIwfProtTblEntry 6 }

isarIfrAtmSiIwfProtTblAAL5InOctets  OBJECT-TYPE
    SYNTAX  Counter
    ACCESS  read-only
    STATUS  mandatory
    DESCRIPTION
           "The number of AAL-5 octets received by FRF.8 of this protocol
            type on this interworking connection."
    ::= { isarIfrAtmSiIwfProtTblEntry 7 }

isarIfrAtmSiIwfProtTblAAL5OutOctets  OBJECT-TYPE
    SYNTAX  Counter
    ACCESS  read-only
    STATUS  mandatory
    DESCRIPTION
           "The number of AAL-5 octets transmitted by FRF.8 of this
            protocol type on this interworking connection."
    ::= { isarIfrAtmSiIwfProtTblEntry 8 }

isarIfrAtmSiIwfProtTblAAL5OutDiscards  OBJECT-TYPE
    SYNTAX  Counter
    ACCESS  read-only
    STATUS  mandatory
    DESCRIPTION
           "The number of AAL-5 PDU's discarded on output by FRF.8 of this
            protocol type on this interworking connection."
    ::= { isarIfrAtmSiIwfProtTblEntry 9 }

-- isarIfrAtmSiIwfProtTblAAL5ArpNakDiscards  { isarIfrAtmSiIwfProtTblEntry 10 }

isarIfrAtmSiIwfProtTblFrInFrames  OBJECT-TYPE
    SYNTAX  Counter
    ACCESS  read-only
    STATUS  mandatory
    DESCRIPTION
           "The number of Frame Relay frames received by FRF.8 from Frame
            Relay subsystem of this protocol type on this interworking
            connection."
    ::= { isarIfrAtmSiIwfProtTblEntry 11 }

isarIfrAtmSiIwfProtTblFrOutFrames  OBJECT-TYPE
    SYNTAX  Counter
    ACCESS  read-only
    STATUS  mandatory
    DESCRIPTION
           "The number of Frame Relay frames sent from FRF.8 to the Frame
            Relay subsystem of this protocol type on this interworking
            connection."
    ::= { isarIfrAtmSiIwfProtTblEntry 12 }

isarIfrAtmSiIwfProtTblFrInOctets  OBJECT-TYPE
    SYNTAX  Counter
    ACCESS  read-only
    STATUS  mandatory
    DESCRIPTION
           "The number of Frame Relay octets received by FRF.8 from the
            Frame Relay subsystem of this protocol type on this
            interworking connection."
    ::= { isarIfrAtmSiIwfProtTblEntry 13 }

isarIfrAtmSiIwfProtTblFrOutOctets  OBJECT-TYPE
    SYNTAX  Counter
    ACCESS  read-only
    STATUS  mandatory
    DESCRIPTION
           "The number of Frame Relay octets sent by FRF.8 to the Frame
            Relay subsystem of this protocol type on this interworking
            connection."
    ::= { isarIfrAtmSiIwfProtTblEntry 14 }

isarIfrAtmSiIwfProtTblFrOutDiscards  OBJECT-TYPE
    SYNTAX  Counter
    ACCESS  read-only
    STATUS  mandatory
    DESCRIPTION
           "The number of Frame Relay frames discarded by FRF.8 rather than
            sending to the Frame Relay subsystem of this protocol type
            on this interworking connection."
    ::= { isarIfrAtmSiIwfProtTblEntry 15 }




-- frAtmSiIwf Mapping

isarIfrAtmSiIwfMappingTable OBJECT-TYPE
    SYNTAX  SEQUENCE OF IsarIfrAtmSiIwfMappingEntry
    ACCESS  not-accessible
    STATUS  mandatory
    DESCRIPTION
           "The frAtmSiIwf mapping table is used to map the IWF index
            into the index of the corresponding entry in the
            isarIfrAtmSiIwfConnectionTable."
    ::= { isarIfrAtmIwfMIBObjects  3 }

isarIfrAtmSiIwfMappingEntry OBJECT-TYPE
    SYNTAX  IsarIfrAtmSiIwfMappingEntry
    ACCESS  not-accessible
    STATUS  mandatory
    DESCRIPTION
           "An entry in the frAtmSiIwf mapping table."
    INDEX   { isarIfrAtmSiIwfConnIndex }
    ::= { isarIfrAtmSiIwfMappingTable  1 }

IsarIfrAtmSiIwfMappingEntry ::=
    SEQUENCE {
      isarIfrAtmSiIwfMapAtmIfIndex
        INTEGER,

      isarIfrAtmSiIwfMapAtmVpi
        INTEGER,

      isarIfrAtmSiIwfMapAtmVci
        INTEGER
    }

isarIfrAtmSiIwfMapAtmIfIndex OBJECT-TYPE
    SYNTAX  INTEGER
    ACCESS  read-only
    STATUS  mandatory
    DESCRIPTION
           "Mapped index."
    ::= { isarIfrAtmSiIwfMappingEntry  1 }

isarIfrAtmSiIwfMapAtmVpi OBJECT-TYPE
    SYNTAX  INTEGER (0..4095)
    ACCESS  read-only
    STATUS  mandatory
    DESCRIPTION
           "Mapped index."
    ::= { isarIfrAtmSiIwfMappingEntry  2 }

isarIfrAtmSiIwfMapAtmVci OBJECT-TYPE
    SYNTAX  INTEGER (0..65535)
    ACCESS  read-only
    STATUS  mandatory
    DESCRIPTION
           "Mapped index."
    ::= { isarIfrAtmSiIwfMappingEntry  3 }





-- The Frame Relay/ATM PVC Network Interworking connection table

isarIfrAtmNiIwfConnectionTable OBJECT-TYPE
    SYNTAX  SEQUENCE OF IsarIfrAtmNiIwfConnectionEntry
    ACCESS  not-accessible
    STATUS  mandatory
    DESCRIPTION
           "A table in which each row represents a Frame Relay/ATM
            interworking connection (IWF).
            Only one PVC endpoint can be mapped to an IWF (multiplexing
            is not supported in IAD4700).

            When an entry in this table is created, an entry in
            isarIfrAtmNiIwfMappingTable is made by IAD4700 (inverse mapping
            of index).

            At the same time two other tables must be updated :
            1. set field isarIfrPVCEndptConnectIdentifier of the
               corresponding entry in isarIfrPVCEndptTable with the
               value of isarIfrAtmNiIwfConnIndex
            2. set field isarIatmVclCrossConnectIdentifier of the
               corresponding entry in IsarIatmVclEntry with the
               value of isarIfrAtmNiIwfConnIndex and
               set field isarIatmVclServiceType of the
               corresponding entry in IsarIatmVclEntry to 'frs'."
    ::= { isarIfrAtmIwfMIBObjects  4 }

isarIfrAtmNiIwfConnectionEntry OBJECT-TYPE
    SYNTAX  IsarIfrAtmNiIwfConnectionEntry
    ACCESS  not-accessible
    STATUS  mandatory
    DESCRIPTION
           "An entry for an interworking connection."
    INDEX   { isarIfrAtmNiIwfConnFrLPortIfIndex,
              isarIfrAtmNiIwfConnDlci,
              isarIfrAtmNiIwfConnAtmIfIndex,
              isarIfrAtmNiIwfConnAtmVpi,
              isarIfrAtmNiIwfConnAtmVci }
    ::= { isarIfrAtmNiIwfConnectionTable  1 }


IsarIfrAtmNiIwfConnectionEntry ::=
    SEQUENCE {
      isarIfrAtmNiIwfConnFrLPortIfIndex
        INTEGER,

      isarIfrAtmNiIwfConnDlci
        INTEGER,

      isarIfrAtmNiIwfConnAtmIfIndex
        INTEGER,

      isarIfrAtmNiIwfConnAtmVpi
        INTEGER,

      isarIfrAtmNiIwfConnAtmVci
        INTEGER,

      isarIfrAtmNiIwfConnSscsDlci
        INTEGER,

      isarIfrAtmNiIwfConnAdminStatus
        INTEGER,

      isarIfrAtmNiIwfConnOperStatus
        INTEGER,

      isarIfrAtmNiIwfConnLastChange
        TimeTicks,

      isarIfrAtmNiIwfConnDeToClpMappingMode
        INTEGER,

      isarIfrAtmNiIwfConnClpToDeMappingMode
        INTEGER,

      isarIfrAtmNiIwfConnRowStatus
        INTEGER,

      isarIfrAtmNiIwfConnServiceIndex
        INTEGER,

      isarIfrAtmNiIwfConnIndex
        INTEGER,

      isarIfrAtmNiIwfConnBceTimeout
        INTEGER,

      isarIfrAtmNiIwfConnFramesOut
        Counter,

      isarIfrAtmNiIwfConnFramesIn
        Counter,

      isarIfrAtmNiIwfConnFramesInError
        Counter,

      isarIfrAtmNiIwfConnFramesDiscard
        Counter,

      isarIfrAtmNiIwfConnSscsVCSigProtocol
        INTEGER,

      isarIfrAtmNiIwfConnSscsUserN391
        INTEGER,

      isarIfrAtmNiIwfConnSscsUserT391
        INTEGER,

      isarIfrAtmNiIwfConnSscsNetT392
        INTEGER
    }


isarIfrAtmNiIwfConnFrLPortIfIndex OBJECT-TYPE
    SYNTAX  INTEGER
    ACCESS  read-only
    STATUS  mandatory
    DESCRIPTION
           "The index in the ifTable that identifies the Frame Relay
            logical port for this interworking connection."
    ::= { isarIfrAtmNiIwfConnectionEntry  1 }

isarIfrAtmNiIwfConnDlci OBJECT-TYPE
    SYNTAX  INTEGER (0..1023)
    ACCESS  read-only
    STATUS  mandatory
    DESCRIPTION
           "The DLCI that identifies the Frame Relay PVC end point for
            this interworking connection."
    DEFVAL  { 16 }
    ::= { isarIfrAtmNiIwfConnectionEntry  2 }

isarIfrAtmNiIwfConnAtmIfIndex OBJECT-TYPE
    SYNTAX  INTEGER
    ACCESS  read-only
    STATUS  mandatory
    DESCRIPTION
           "The index in the ifTable that identifies the ATM
            port for this interworking connection."
    ::= { isarIfrAtmNiIwfConnectionEntry  3 }

isarIfrAtmNiIwfConnAtmVpi OBJECT-TYPE
    SYNTAX  INTEGER (0..4095)
    ACCESS  read-only
    STATUS  mandatory
    DESCRIPTION
           "The VPI of the ATM PVC end point for this interworking
            connection."
    ::= { isarIfrAtmNiIwfConnectionEntry  4 }

isarIfrAtmNiIwfConnAtmVci OBJECT-TYPE
    SYNTAX  INTEGER (0..65535)
    ACCESS  read-only
    STATUS  mandatory
    DESCRIPTION
           "The VCI of the ATM PVC end point for this interworking
            connection."
    ::= { isarIfrAtmNiIwfConnectionEntry  5 }

isarIfrAtmNiIwfConnSscsDlci OBJECT-TYPE
    SYNTAX  INTEGER (0..1023)
    ACCESS  read-write
    STATUS  mandatory
    DESCRIPTION
           "The DLCI that identifies the Frame Relay PVC on the ATM
            virtual channel of this interworking connection.
            Modification of this value is not allowed.
            Allowed DLCI values depend on the selected LMI type
            (isarIfrAtmNiIwfConnSscsVCSigProtocol):
             (1) No LMI selected:     16-1007, 1022, 1023
             (2) (Original)LMI:       16-1007, 1022
             (3) ANSI T1.617 Annex D: 16-991, 1022
             (4) ITU Q.933 Annex A:   16-991, 1022 (default SSCS LMI type).

            The SNMPv2 MAX-ACCESS is read(-only)-create."
    DEFVAL  { 1022 }
    ::= { isarIfrAtmNiIwfConnectionEntry  6 }

isarIfrAtmNiIwfConnAdminStatus OBJECT-TYPE
    SYNTAX  INTEGER {
                      up(1),
                      down(2)
            }
    ACCESS  read-write
    STATUS  mandatory
    DESCRIPTION
           "The desired operational state for this interworking
            connection.
            The SNMPv2 MAX-ACCESS is read-create."
    ::= { isarIfrAtmNiIwfConnectionEntry  7 }

isarIfrAtmNiIwfConnOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "The current operational state of this interworking 
            connection.
            Refer to RFC 2233 for the description of the states."
    ::= { isarIfrAtmNiIwfConnectionEntry  8 }

isarIfrAtmNiIwfConnLastChange OBJECT-TYPE
    SYNTAX  TimeTicks
    ACCESS  read-only
    STATUS  mandatory
    DESCRIPTION
           "The value of sysUpTime at the time this interworking
            connection entered its current operational state.
            If the current state was entered prior to the last
            re-initialization of the local network management
            subsystem, then this object contains a zero value."
    ::= { isarIfrAtmNiIwfConnectionEntry  9 }

isarIfrAtmNiIwfConnDeToClpMappingMode OBJECT-TYPE
    SYNTAX  INTEGER {
                      mode1(1),
                      mode2(2)
            }
    ACCESS  read-only
    STATUS  mandatory
    DESCRIPTION
           "This object describes which mode of translation is in
            use for loss priority mapping in the Frame Relay to ATM
            direction.
            IAD4700 : only 'mode1' is valid."
--  REFERENCE "Section 4.2.1 of FRF.8 [9]."
    DEFVAL  { mode1 }
    ::= { isarIfrAtmNiIwfConnectionEntry  10 }

isarIfrAtmNiIwfConnClpToDeMappingMode OBJECT-TYPE
    SYNTAX  INTEGER {
                      mode1(1),
                      mode2(2)
            }
    ACCESS  read-only
    STATUS  mandatory
    DESCRIPTION
           "This object describes which mode of translation is in
            use for loss priority mapping in the ATM to Frame Relay
            direction.
            IAD4700 : only 'mode1' is valid."
--  REFERENCE "Section 4.2.2 of FRF.8 [9]."
    DEFVAL  { mode1 }
    ::= { isarIfrAtmNiIwfConnectionEntry  11 }

isarIfrAtmNiIwfConnRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
                    }
    ACCESS  read-write
    STATUS  mandatory
    DESCRIPTION
           "This object is used to create and delete rows in the
            isarIfrAtmNiIwfConnectionTable.
            The SNMPv2 MAX-ACCESS is read-create."
    ::= { isarIfrAtmNiIwfConnectionEntry  12 }


isarIfrAtmNiIwfConnServiceIndex OBJECT-TYPE
    SYNTAX  INTEGER
    ACCESS  read-only
    STATUS  mandatory
    DESCRIPTION
           "The index of the service to which this interworking function
            belongs.
            This is the same index as serviceIndex of isarIserviceTable and
            can be found via isarIfrAtmNiIwfConnFrLPortIfIndex."
    ::= { isarIfrAtmNiIwfConnectionEntry  13 }

isarIfrAtmNiIwfConnIndex OBJECT-TYPE
    SYNTAX  INTEGER
    ACCESS  read-only
    STATUS  mandatory
    DESCRIPTION
           "The value of this object is equal to the
            isarIiwfNextConnIndex obtained (by IAD4700) to uniqely identify
            this IWF."
    ::= { isarIfrAtmNiIwfConnectionEntry  14 }

isarIfrAtmNiIwfConnBceTimeout OBJECT-TYPE
    SYNTAX  INTEGER (0..500)
    ACCESS  read-write
    STATUS  mandatory
    DESCRIPTION
	   "The Backwards Congestion Experienced
	    (BCE) Time-out Period, in seconds.  The
            VCC Congestion State is cleared after
	    BCE time-out seconds if no frames have
	    been received in the ATM -to- FR
	    direction.  The default is 200 seconds.
            Modify of this value is not allowed.
	    The SNMPv2 MAX-ACCESS is read(-only)-create."
    DEFVAL  { 200 }
    ::= { isarIfrAtmNiIwfConnectionEntry  15 }

isarIfrAtmNiIwfConnFramesOut OBJECT-TYPE
    SYNTAX  Counter
    ACCESS  read-only
    STATUS  mandatory
    DESCRIPTION
           "A statistical counter of number of Frames
            Transmitted over this PVC."
    ::= { isarIfrAtmNiIwfConnectionEntry  16 }

isarIfrAtmNiIwfConnFramesIn OBJECT-TYPE
    SYNTAX  Counter
    ACCESS  read-only
    STATUS  mandatory
    DESCRIPTION
	   "A statistical counter of number of Frames
            Received over this PVC."
    ::= { isarIfrAtmNiIwfConnectionEntry  17 }

isarIfrAtmNiIwfConnFramesInError OBJECT-TYPE
    SYNTAX  Counter
    ACCESS  read-only
    STATUS  mandatory
    DESCRIPTION
	   "A Statistical counter of number of Frames
            received in error over this PVC."
    ::= { isarIfrAtmNiIwfConnectionEntry  18 }

isarIfrAtmNiIwfConnFramesDiscard OBJECT-TYPE
    SYNTAX  Counter
    ACCESS  read-only
    STATUS  mandatory
    DESCRIPTION
	   "A statistical counter of number of Frames
            Discarded by FR-SSCS for this PVC."
    ::= { isarIfrAtmNiIwfConnectionEntry  19 }

isarIfrAtmNiIwfConnSscsVCSigProtocol OBJECT-TYPE
    SYNTAX  INTEGER {
                      none(1),
                      lmi(2),
                      ansiT1617D(3),
                      ccittQ933A(4)
            }
    ACCESS  read-write
    STATUS  mandatory
    DESCRIPTION
           "The value of this object identifies the Local
            In-Channel Signaling Protocol that is used at
            the sscs level for this interworking connection.
            To be compliant with FRF.5 the value should be ccittQ933A.
            Modification of this value is not allowed.
            The SNMPv2 MAX-ACCESS is read(only)-create."
    DEFVAL  { ccittQ933A }
    ::= { isarIfrAtmNiIwfConnectionEntry  20 }

isarIfrAtmNiIwfConnSscsUserN391 OBJECT-TYPE
    SYNTAX  INTEGER (1..255)
    ACCESS  read-write
    STATUS  mandatory
    DESCRIPTION
           "The value of this object identifies the User-side
            N391 full status polling cycle value.
            This object applies to Q.933 Annex A and T1.617 Annex D."
    DEFVAL  { 1 }
    ::= { isarIfrAtmNiIwfConnectionEntry  21 }

isarIfrAtmNiIwfConnSscsUserT391 OBJECT-TYPE
    SYNTAX  INTEGER (5..180)
    ACCESS  read-write
    STATUS  mandatory
    DESCRIPTION
           "The value of this object identifies the User-side
            T391 link integrity verification polling timer value.
            This object applies to Q.933 Annex A and T1.617 Annex D."
    DEFVAL  { 180 }
    ::= { isarIfrAtmNiIwfConnectionEntry  22 }

isarIfrAtmNiIwfConnSscsNetT392 OBJECT-TYPE
    SYNTAX  INTEGER (5..200)
    ACCESS  read-write
    STATUS  mandatory
    DESCRIPTION
           "The value of this object identifies the Network-side
            T392 polling verification timer value.
            T392 should be greater than T391.
            This object applies to Q.933 Annex A, T1.617 Annex D and LMI."
    DEFVAL  { 200 }
    ::= { isarIfrAtmNiIwfConnectionEntry  23 }


-- frAtmNiIwf Mapping

isarIfrAtmNiIwfMappingTable OBJECT-TYPE
    SYNTAX  SEQUENCE OF IsarIfrAtmNiIwfMappingEntry
    ACCESS  not-accessible
    STATUS  mandatory
    DESCRIPTION
           "The frAtmNiIwf mapping table is used to map the IWF index
            into the index of the corresponding entry in the
            isarIfrAtmNiIwfConnectionTable."
    ::= { isarIfrAtmIwfMIBObjects  5 }

isarIfrAtmNiIwfMappingEntry OBJECT-TYPE
    SYNTAX  IsarIfrAtmNiIwfMappingEntry
    ACCESS  not-accessible
    STATUS  mandatory
    DESCRIPTION
           "An entry in the frAtmNiIwf mapping table."
    INDEX   { isarIfrAtmNiIwfConnIndex }
    ::= { isarIfrAtmNiIwfMappingTable  1 }

IsarIfrAtmNiIwfMappingEntry ::=
    SEQUENCE {
      isarIfrAtmNiIwfMapFrLPortIfIndex
        INTEGER,

      isarIfrAtmNiIwfMapDlci
        INTEGER,

      isarIfrAtmNiIwfMapAtmIfIndex
        INTEGER,

      isarIfrAtmNiIwfMapAtmVpi
        INTEGER,

      isarIfrAtmNiIwfMapAtmVci
        INTEGER
    }

isarIfrAtmNiIwfMapFrLPortIfIndex OBJECT-TYPE
    SYNTAX  INTEGER
    ACCESS  read-only
    STATUS  mandatory
    DESCRIPTION
           "Mapped index."
    ::= { isarIfrAtmNiIwfMappingEntry  1 }

isarIfrAtmNiIwfMapDlci OBJECT-TYPE
    SYNTAX  INTEGER
    ACCESS  read-only
    STATUS  mandatory
    DESCRIPTION
           "Mapped index."
    ::= { isarIfrAtmNiIwfMappingEntry  2 }

isarIfrAtmNiIwfMapAtmIfIndex OBJECT-TYPE
    SYNTAX  INTEGER
    ACCESS  read-only
    STATUS  mandatory
    DESCRIPTION
           "Mapped index."
    ::= { isarIfrAtmNiIwfMappingEntry  3 }

isarIfrAtmNiIwfMapAtmVpi OBJECT-TYPE
    SYNTAX  INTEGER (0..4095)
    ACCESS  read-only
    STATUS  mandatory
    DESCRIPTION
           "Mapped index."
    ::= { isarIfrAtmNiIwfMappingEntry  4 }

isarIfrAtmNiIwfMapAtmVci OBJECT-TYPE
    SYNTAX  INTEGER (0..65535)
    ACCESS  read-only
    STATUS  mandatory
    DESCRIPTION
           "Mapped index."
    ::= { isarIfrAtmNiIwfMappingEntry  5 }







-- traps (moved to isarIiwfMIBObjects )





--
-- ISAR frAtmIwfMIBObjects : end
--




-- This file cannot be used to create SNMP agent.
-- The file isarOneFile.my has to be used to create the agent.


-- isarIdebugMIBObjects      OBJECT IDENTIFIER ::= { isar  30 }


--
-- ISAR debugMIBObjects : begin
--
-- enterprise MIB for ISAR
-- The MIB is written for SNMPv1.



-- ISAR debug CBR port configuration table

isarIdbCbrPortConfTable OBJECT-TYPE
    SYNTAX  SEQUENCE OF IsarIdbCbrPortConfEntry
    ACCESS  not-accessible
    STATUS  mandatory
    DESCRIPTION
           "Debug information."
    ::= { isarIdebugMIBObjects  1 }

isarIdbCbrPortConfEntry OBJECT-TYPE
    SYNTAX  IsarIdbCbrPortConfEntry
    ACCESS  not-accessible
    STATUS  mandatory
    DESCRIPTION
           "One row in the isarIdbCbrPortConfTable."
    INDEX   { isarIdbCbrPortId }
    ::= { isarIdbCbrPortConfTable  1 }


IsarIdbCbrPortConfEntry ::=
    SEQUENCE { 
      isarIdbCbrPortId
        INTEGER,

       isarIdbCbrPortServiceType
        INTEGER,
       
      isardbCbrPortTpTimingSource
        INTEGER,
        
      isarIdbCbrPortFrameFormat
        INTEGER,

      isarIdbCbrPortSignal
        INTEGER
    }
    
isarIdbCbrPortId OBJECT-TYPE
    SYNTAX  INTEGER (1..8)
    ACCESS  read-only
    STATUS  mandatory
    DESCRIPTION
           "."
    ::= { isarIdbCbrPortConfEntry  1 }

isarIdbCbrPortServiceType OBJECT-TYPE
    SYNTAX  INTEGER {
                      illegal(1),
                      atm(2),
                      nx64(3),
                      unCes(4)
            }
    ACCESS  read-only
    STATUS  mandatory
    DESCRIPTION
           "."
    DEFVAL { nx64 }
    ::= { isarIdbCbrPortConfEntry  2 }

isardbCbrPortTpTimingSource OBJECT-TYPE
    SYNTAX  INTEGER {
                      illegal(1),
                      system(2),
                      loop(3)
            }
    ACCESS  read-only
    STATUS  mandatory
    DESCRIPTION
           "."
    DEFVAL { system }
    ::= { isarIdbCbrPortConfEntry  3 }

isarIdbCbrPortFrameFormat OBJECT-TYPE
    SYNTAX  INTEGER {
                      illegal(1),
                      double(2),
                      crc(3),
                      super(4),
                      extended(5)
            }
    ACCESS  read-only
    STATUS  mandatory
    DESCRIPTION
           "The default value is crc for E1 and super for T1."
    DEFVAL { crc }
    ::= { isarIdbCbrPortConfEntry  4 }

isarIdbCbrPortSignal OBJECT-TYPE
    SYNTAX  INTEGER {
                      illegal(1),
                      none(2),
                      cas(3),
                      ccs(4)
            }
    ACCESS  read-only
    STATUS  mandatory
    DESCRIPTION
           "."
    ::= { isarIdbCbrPortConfEntry  5 }






-- ISAR debug QMC channel table

isarIdbQmcChannelTable OBJECT-TYPE
    SYNTAX  SEQUENCE OF IsarIdbQmcChannelEntry
    ACCESS  not-accessible
    STATUS  mandatory
    DESCRIPTION
           "Debug information.
            Contains information for the HDLC log port by
            QMC and HSSI."
    ::= { isarIdebugMIBObjects  2 }

isarIdbQmcChannelEntry OBJECT-TYPE
    SYNTAX  IsarIdbQmcChannelEntry
    ACCESS  not-accessible
    STATUS  mandatory
    DESCRIPTION
           "One row in the isarIdbQmcChannelTable."
    INDEX   { isarIdbQmcChannelConnIndex }
    ::= { isarIdbQmcChannelTable  1 }


IsarIdbQmcChannelEntry ::=
    SEQUENCE { 
      isarIdbQmcChannelConnIndex
        INTEGER,

      isarIdbQmcChannelTimeSlot
        INTEGER

    }
    
isarIdbQmcChannelConnIndex OBJECT-TYPE
    SYNTAX  INTEGER (1..2147483647)
    ACCESS  read-only
    STATUS  mandatory
    DESCRIPTION
           "Identification of the connection."
    ::= { isarIdbQmcChannelEntry  1 }

isarIdbQmcChannelTimeSlot OBJECT-TYPE
    SYNTAX  INTEGER
    ACCESS  read-only
    STATUS  mandatory
    DESCRIPTION
           "This is a bitmap that indicates which timeslots belong to
            this connection.  The field is defined as the sum of (2 to the 
            power of timeslot) where timeslot is a value from 0 to 31."
    ::= { isarIdbQmcChannelEntry  2 }




-- ISAR debug TSS connection table
-- table is optional

isarIdbTssConnTable OBJECT-TYPE
    SYNTAX  SEQUENCE OF IsarIdbTssConnEntry
    ACCESS  not-accessible
    STATUS  mandatory
    DESCRIPTION
           "Debug information.
            List of connections laid in on a time space switch."
    ::= { isarIdebugMIBObjects  3 }

isarIdbTssConnEntry OBJECT-TYPE
    SYNTAX  IsarIdbTssConnEntry
    ACCESS  not-accessible
    STATUS  mandatory
    DESCRIPTION
           "One row in the isarIdbTssConnTable."
    INDEX   { isarIdbTssConnId }
    ::= { isarIdbTssConnTable  1 }


IsarIdbTssConnEntry ::=
    SEQUENCE { 
      isarIdbTssConnSwitchId
        INTEGER,

      isarIdbTssConnInputPort
        INTEGER,

      isarIdbTssConnInputBundle
        INTEGER,

      isarIdbTssConnOutputPort
        INTEGER,

      isarIdbTssConnOutputBundle
        INTEGER,

      isarIdbTssConnDirection
        INTEGER,

      isarIdbTssConnId
        INTEGER

    }
    
isarIdbTssConnSwitchId OBJECT-TYPE
    SYNTAX  INTEGER
    ACCESS  read-only
    STATUS  mandatory
    DESCRIPTION
           "Identification of the switch (= hierarchical number)."
    ::= { isarIdbTssConnEntry  1 }

isarIdbTssConnInputPort OBJECT-TYPE
    SYNTAX  INTEGER (0..7)
    ACCESS  read-only
    STATUS  mandatory
    DESCRIPTION
           "Input port identification."
    ::= { isarIdbTssConnEntry  2 }

isarIdbTssConnInputBundle OBJECT-TYPE
    SYNTAX  INTEGER
    ACCESS  read-only
    STATUS  mandatory
    DESCRIPTION
           "Bundle (bitmap) on input port."
    ::= { isarIdbTssConnEntry  3 }

isarIdbTssConnOutputPort OBJECT-TYPE
    SYNTAX  INTEGER (0..7)
    ACCESS  read-only
    STATUS  mandatory
    DESCRIPTION
           "Output port identification."
    ::= { isarIdbTssConnEntry  4 }

isarIdbTssConnOutputBundle OBJECT-TYPE
    SYNTAX  INTEGER
    ACCESS  read-only
    STATUS  mandatory
    DESCRIPTION
           "Bundle (bitmap) on output port."
    ::= { isarIdbTssConnEntry  5 }

isarIdbTssConnDirection OBJECT-TYPE
    SYNTAX  INTEGER {
                      upstream(1),
                      downstream(2),
                      bidirectional(3)
            }
    ACCESS  read-only
    STATUS  mandatory
    DESCRIPTION
           "Direction of the connection."
    ::= { isarIdbTssConnEntry  6 }

isarIdbTssConnId OBJECT-TYPE
    SYNTAX  INTEGER (1..2147483647)
    ACCESS  read-only
    STATUS  mandatory
    DESCRIPTION
           "Identification of the connection."
    ::= { isarIdbTssConnEntry  7 }



-- mapping

isarIdbTssMappingTable OBJECT-TYPE
    SYNTAX  SEQUENCE OF IsarIdbTssMappingEntry
    ACCESS  not-accessible
    STATUS  mandatory
    DESCRIPTION
           "Debug information.
            List of connections on an interface (only E1/T1 port,
            Ds0 bundle or Ds0 channel) at the drop side of the ISAR."
    ::= { isarIdebugMIBObjects  9 }

isarIdbTssMappingEntry OBJECT-TYPE
    SYNTAX  IsarIdbTssMappingEntry
    ACCESS  not-accessible
    STATUS  mandatory
    DESCRIPTION
           "One row in the isarIdbTssMappingTable."
    INDEX   { isarIdbTssMappConnIndex }
    ::= { isarIdbTssMappingTable  1 }


IsarIdbTssMappingEntry ::=
    SEQUENCE { 
      isarIdbTssMappConnIndex
        INTEGER,

      isarIdbTssMappTssConnId
        INTEGER

    }

isarIdbTssMappConnIndex OBJECT-TYPE
    SYNTAX  INTEGER (1..2147483647)
    ACCESS  read-only
    STATUS  mandatory
    DESCRIPTION
           "Index of the connection, equal to
            isarIdbInterfaceConnIndex of isarIdbInterfaceTable."
    ::= { isarIdbTssMappingEntry  1 }
    
isarIdbTssMappTssConnId OBJECT-TYPE
    SYNTAX  INTEGER
    ACCESS  read-only
    STATUS  mandatory
    DESCRIPTION
           "Is equal to isarIdbTssConnIndex of isarIdbTssConnTable."
    ::= { isarIdbTssMappingEntry  2 }






-- ISAR debug CBR endpoint table
-- table is optional

isarIdbCbrEndpntTable OBJECT-TYPE
    SYNTAX  SEQUENCE OF IsarIdbCbrEndpntEntry
    ACCESS  not-accessible
    STATUS  mandatory
    DESCRIPTION
           "Debug information.
            List of CbrEndPoints on CbrProcessor."
    ::= { isarIdebugMIBObjects  4 }

isarIdbCbrEndpntEntry OBJECT-TYPE
    SYNTAX  IsarIdbCbrEndpntEntry
    ACCESS  not-accessible
    STATUS  mandatory
    DESCRIPTION
           "One row in the isarIdbCbrEndpntTable."
    INDEX   { isarIdbCbrEndpntConnIndex }
    ::= { isarIdbCbrEndpntTable  1 }


IsarIdbCbrEndpntEntry ::=
    SEQUENCE { 
      isarIdbCbrEndpntCbrProcessor
        INTEGER,

      isarIdbCbrEndpntCbrEndpoint
        INTEGER,

      isarIdbCbrEndpntCbrPort
        INTEGER,

      isarIdbCbrEndpntTsBundle
        INTEGER,

      isarIdbCbrEndpntConnIndex
        INTEGER

    }
    
isarIdbCbrEndpntCbrProcessor OBJECT-TYPE
    SYNTAX  INTEGER
    ACCESS  read-only
    STATUS  mandatory
    DESCRIPTION
           "Identification of the CBR processor (= hierarchical number)."
    ::= { isarIdbCbrEndpntEntry  1 }

isarIdbCbrEndpntCbrEndpoint OBJECT-TYPE
    SYNTAX  INTEGER
    ACCESS  read-only
    STATUS  mandatory
    DESCRIPTION
           "Identification of the CBR end point (= extension number of
            UOID)."
    ::= { isarIdbCbrEndpntEntry  2 }

isarIdbCbrEndpntCbrPort OBJECT-TYPE
    SYNTAX  INTEGER
    ACCESS  read-only
    STATUS  mandatory
    DESCRIPTION
           "Identification of the CBR port (= extension number of UOID)."
    ::= { isarIdbCbrEndpntEntry  3 }

isarIdbCbrEndpntTsBundle OBJECT-TYPE
    SYNTAX  INTEGER
    ACCESS  read-only
    STATUS  mandatory
    DESCRIPTION
           "Indicates which timeslots belong to this bundle. The field
            is defined as the sum of (2 to the power of timeslot number)
            where timeslot number (0..31) represents the channels
            belonging to the bundle."
    ::= { isarIdbCbrEndpntEntry  4 }

isarIdbCbrEndpntConnIndex OBJECT-TYPE
    SYNTAX  INTEGER (1..2147483647)
    ACCESS  read-only
    STATUS  mandatory
    DESCRIPTION
           "Identification of the connection."
    ::= { isarIdbCbrEndpntEntry  5 }


-- ISAR debug interface table
-- table is optional

isarIdbInterfaceTable OBJECT-TYPE
    SYNTAX  SEQUENCE OF IsarIdbInterfaceEntry
    ACCESS  not-accessible
    STATUS  mandatory
    DESCRIPTION
           "Debug information.
            List of connections on an interface (only E1/T1 port,
            Ds0 bundle or Ds0 channel) at the drop side of the ISAR."
    ::= { isarIdebugMIBObjects  5 }

isarIdbInterfaceEntry OBJECT-TYPE
    SYNTAX  IsarIdbInterfaceEntry
    ACCESS  not-accessible
    STATUS  mandatory
    DESCRIPTION
           "One row in the isarIdbInterfaceTable."
    INDEX   { isarIdbInterfaceConnIndex }
    ::= { isarIdbInterfaceTable  1 }


IsarIdbInterfaceEntry ::=
    SEQUENCE { 
      isarIdbInterfaceConnIndex
        INTEGER,

      isarIdbInterfaceIfIndex
        INTEGER

    }

isarIdbInterfaceConnIndex OBJECT-TYPE
    SYNTAX  INTEGER (1..214748364)
    ACCESS  read-only
    STATUS  mandatory
    DESCRIPTION
           "Identification of the connection."
    ::= { isarIdbInterfaceEntry  1 }
    
isarIdbInterfaceIfIndex OBJECT-TYPE
    SYNTAX  INTEGER
    ACCESS  read-only
    STATUS  mandatory
    DESCRIPTION
           "Interface index of the specific E1/T1 port, Dso bundle or Ds0 
            channel."
    ::= { isarIdbInterfaceEntry  2 }


--
-- ISAR debugMIBObjects : end
--




-- This file cannot be used to create SNMP agent.
-- The file isarOneFile.my has to be used to create the agent.


-- isarIpowerOnSTMIBObjects      OBJECT IDENTIFIER ::= { isar  25 }


--
-- ISAR powerOnSTMIBObjects : begin
--
-- enterprise MIB for ISAR
-- The MIB is written for SNMPv1.


isarItestLockedForRead OBJECT-TYPE
    SYNTAX  INTEGER { 
                      true(1), 
                      false(2) 
            }
    ACCESS  read-write
    STATUS  mandatory
    DESCRIPTION
           "Indicates if the test buffer is currently locked for 
            reading. If locked, other snmp managers are not able to read
            the data. 
            When the value is set from true to false, a check has to be
            made to verify that the same snmp manager is resetting the
            value. There are three possible ways this variable can be set
            to false.
            a. set to false by the same manager who set it previously to
               true,
            b. automatically when during sequential get, the test buffer
               is sent completely,
            c. via a time out in order not to block the test buffer
               indefinite."
    ::= { isarIpowerOnSTMIBObjects  1 }

isarItestResultLevel OBJECT-TYPE
    SYNTAX  INTEGER { 
                      allResults(1), 
                      onlyPassed(2),
                      onlyFailed(3)
            }
    ACCESS  read-write
    STATUS  mandatory
    DESCRIPTION
           "Indicates which results are returned via GET."
    DEFVAL { onlyFailed }
    ::= { isarIpowerOnSTMIBObjects  2 }



-- ISAR power on self test : results


isarIpowerOnSTTable OBJECT-TYPE
    SYNTAX  SEQUENCE OF IsarIpowerOnSTEntry
    ACCESS  not-accessible
    STATUS  mandatory
    DESCRIPTION
           "."
    ::= { isarIpowerOnSTMIBObjects  3 }

isarIpowerOnSTEntry OBJECT-TYPE
    SYNTAX  IsarIpowerOnSTEntry
    ACCESS  not-accessible
    STATUS  mandatory
    DESCRIPTION
           "One row in the isarIpowerOnSTTable."
    INDEX   { isarIpowerOnSTIndex }
    ::= { isarIpowerOnSTTable  1 }


IsarIpowerOnSTEntry ::=
    SEQUENCE { 
      isarIpowerOnSTIndex
        INTEGER,
        
      isarIpowerOnSTMessage
        OCTET STRING
    }
    
isarIpowerOnSTIndex OBJECT-TYPE
    SYNTAX  INTEGER
    ACCESS  read-only
    STATUS  mandatory
    DESCRIPTION
           "Dummy index not used to access the table.
            The table will always be sequentially read."
    ::= { isarIpowerOnSTEntry  1 }

isarIpowerOnSTMessage OBJECT-TYPE
    SYNTAX  OCTET STRING
    ACCESS  read-only
    STATUS  mandatory
    DESCRIPTION
           "During a 'get', the snmp agent will verify whether the 
            calling manager is the same as the one who has set the
            isarItestLockedForRead variable. Each 'get' will return the 
            next test result message that is conform with the value of 
            isarItestResultLevel.
            The message contains the following information :
               incrementing number for ID of the test,
               name of the component,
               description of the test,
               the test level,
               the test type,
               the test group,
               the test result (passed or failed),
               fail data when the test failed.
            E.g. '1.PLD_MAMO. Register Access Test. Component. Basic. 
            Core. Failed - 0x10 (16), 0x20 (32), 0x30 (48).'
            '2. PLD_VCM. Register Access Test. Component. Basic. Core. 
            Passed.'"
    ::= { isarIpowerOnSTEntry  2 }





--
-- ISAR powerOnSTMIBObjects : end
--
-- This file cannot be used to create SNMP agent.
-- The file isarOneFile.my has to be used to create the agent.


-- isarIhdlcStatisticsMIBObjects      OBJECT IDENTIFIER ::= { isar  26 }


--
-- ISAR hdlcStatisticsMIBObjects : begin
--
-- enterprise MIB for ISAR
-- The MIB is written for SNMPv1.

--
-- ISAR hdlc statistics
--
-- scalars are moved to a table
--

isarIhdlcStatDisf OBJECT-TYPE
    SYNTAX  Counter
    ACCESS  read-only
    STATUS  obsolete
    DESCRIPTION
           "discard frame counter."
    ::= { isarIhdlcStatisticsMIBObjects  1 }

isarIhdlcStatCrcError OBJECT-TYPE
    SYNTAX  Counter
    ACCESS  read-only
    STATUS  obsolete
    DESCRIPTION
           "CRC error counter."
    ::= { isarIhdlcStatisticsMIBObjects  2 }

isarIhdlcStatAbtS OBJECT-TYPE
    SYNTAX  Counter
    ACCESS  read-only
    STATUS  obsolete
    DESCRIPTION
           "abort sequence counter."
    ::= { isarIhdlcStatisticsMIBObjects  3 }

isarIhdlcStatNma OBJECT-TYPE
    SYNTAX  Counter
    ACCESS  read-only
    STATUS  obsolete
    DESCRIPTION
           "non matching address Rx counter."
    ::= { isarIhdlcStatisticsMIBObjects  4 }

isarIhdlcStatRet OBJECT-TYPE
    SYNTAX  Counter
    ACCESS  read-only
    STATUS  obsolete
    DESCRIPTION
           "frame retransmission counter."
    ::= { isarIhdlcStatisticsMIBObjects  5 }



-- global QMC coounters : counters valid for all QMC channels = valid for all
-- HDLC logical ports with ds0bundle as lower layer

isarIhdlcQmcStatGov OBJECT-TYPE
    SYNTAX  Counter
    ACCESS  read-only
    STATUS  mandatory
    DESCRIPTION
           "Global overrun, affects all channels."
    ::= { isarIhdlcStatisticsMIBObjects  6 }

isarIhdlcQmcStatGun OBJECT-TYPE
    SYNTAX  Counter
    ACCESS  read-only
    STATUS  mandatory
    DESCRIPTION
           "Global underrun, affects all channels."
    ::= { isarIhdlcStatisticsMIBObjects  7 }

isarIhdlcQmcStatIqov OBJECT-TYPE
    SYNTAX  Counter
    ACCESS  read-only
    STATUS  mandatory
    DESCRIPTION
           "Interrupt queue overrun, new interrupt has no place in queueu
            because of previous interrupt or not handled."
    ::= { isarIhdlcStatisticsMIBObjects  8 }



-- HDLC logical port statistics table


isarIhdlcLogPortStatsTable OBJECT-TYPE
    SYNTAX  SEQUENCE OF IsarIhdlcLogPortStatsEntry
    ACCESS  not-accessible
    STATUS  mandatory
    DESCRIPTION
           "This table contains the statistics of an HDLC 
            logical port.
            There are 3 types of counters in this table.  The counters that
            are used depend on the ifType of the lower layer of the HDLC
            logical port.
            The first part of the counters are valid when the HDLC logical
            port is based on an SI port.
            The first and second part of the counters are valid when the HDLC logical
            port is based on a ds0bundle.
            The third part of the counters are valid when the HDLC logical
            port is based on an S0 port."
    ::= { isarIhdlcStatisticsMIBObjects  9 }

isarIhdlcLogPortStatsEntry OBJECT-TYPE
    SYNTAX  IsarIhdlcLogPortStatsEntry
    ACCESS  not-accessible
    STATUS  mandatory
    DESCRIPTION
           "One row in the isarIhdlcLogPortStatsTable."
    INDEX   { isarIhdlcLogPortIndex }
    ::= { isarIhdlcLogPortStatsTable  1 }


IsarIhdlcLogPortStatsEntry ::=
    SEQUENCE { 
      isarIhdlcLogPortStatsDisf
        Counter,

      isarIhdlcLogPortStatsCrcError
        Counter,

      isarIhdlcLogPortStatsAbtS
        Counter,

      isarIhdlcLogPortStatsNma
        Counter,

      isarIhdlcLogPortStatsRet
        Counter,

      isarIhdlcLogPortStatsUnc
        Counter,

      isarIhdlcLogPortStatsRxFlvc
        Counter,

      isarIhdlcLogPortStatsRxNo
        Counter,

      isarIhdlcLogPortStatsDChannelTxDataOverFlow
        Counter,

      isarIhdlcLogPortStatsDChannelTxDataUnderrun
        Counter,

      isarIhdlcLogPortStatsDChannelFrameOverFlow
        Counter,

      isarIhdlcLogPortStatsDChannelRxDataOverFlow
        Counter,

      isarIhdlcLogPortStatsDChannelRxCrcError
        Counter,

      isarIhdlcLogPortStatsDChannelRxMessageAborted
        Counter,

      isarIhdlcLogPortStatsDChannelRxLengthOverflow
        Counter,

      isarIhdlcLogPortStatsDChannelTxBufferUnderrun
        Counter,

      isarIhdlcLogPortStatsDChannelRxBufferUnderrun
        Counter
    }
    
-- These counters are valid when the lower layer of the HDLC log port
-- is a SI port (ifType = v35(45)) or a ds0bundle (ifType = ds0(81)).

isarIhdlcLogPortStatsDisf OBJECT-TYPE
    SYNTAX  Counter
    ACCESS  read-only
    STATUS  mandatory
    DESCRIPTION
           "discard frame counter."
    ::= { isarIhdlcLogPortStatsEntry  1 }

isarIhdlcLogPortStatsCrcError OBJECT-TYPE
    SYNTAX  Counter
    ACCESS  read-only
    STATUS  mandatory
    DESCRIPTION
           "CRC error counter."
    ::= { isarIhdlcLogPortStatsEntry  2 }

isarIhdlcLogPortStatsAbtS OBJECT-TYPE
    SYNTAX  Counter
    ACCESS  read-only
    STATUS  mandatory
    DESCRIPTION
           "abort sequence counter."
    ::= { isarIhdlcLogPortStatsEntry  3 }

isarIhdlcLogPortStatsNma OBJECT-TYPE
    SYNTAX  Counter
    ACCESS  read-only
    STATUS  mandatory
    DESCRIPTION
           "non matching address Rx counter."
    ::= { isarIhdlcLogPortStatsEntry  4 }

isarIhdlcLogPortStatsRet OBJECT-TYPE
    SYNTAX  Counter
    ACCESS  read-only
    STATUS  mandatory
    DESCRIPTION
           "frame retransmission counter."
    ::= { isarIhdlcLogPortStatsEntry  5 }



-- following counters are only valid for QMC
-- These counters are only valid when the lower layer of the HDLC log port
-- is a ds0bundle (ifType = ds0(81)).

isarIhdlcLogPortStatsUnc OBJECT-TYPE
    SYNTAX  Counter
    ACCESS  read-only
    STATUS  mandatory
    DESCRIPTION
           "There is no valid data to send to the transmitter, abort
            sequence followed by idles are sent."
    ::= { isarIhdlcLogPortStatsEntry  6 }

isarIhdlcLogPortStatsRxFlvc OBJECT-TYPE
    SYNTAX  Counter
    ACCESS  read-only
    STATUS  mandatory
    DESCRIPTION
           "Rx frame length violation counter."
    ::= { isarIhdlcLogPortStatsEntry  7 }

isarIhdlcLogPortStatsRxNo OBJECT-TYPE
    SYNTAX  Counter
    ACCESS  read-only
    STATUS  mandatory
    DESCRIPTION
           "Rx non-octet-aligned frame counter."
    ::= { isarIhdlcLogPortStatsEntry  8 }


-- following counters are only valid for D Channel (of S0 port)
-- These counters are only valid when the lower layer of the HDLC log port
-- is an S0 port (ifType = isdns(75)).

isarIhdlcLogPortStatsDChannelTxDataOverFlow OBJECT-TYPE
    SYNTAX  Counter
    ACCESS  read-only
    STATUS  mandatory
    DESCRIPTION
           "Data can not be transmitted because of TxFIFO overflow."
    ::= { isarIhdlcLogPortStatsEntry  9 }

isarIhdlcLogPortStatsDChannelTxDataUnderrun OBJECT-TYPE
    SYNTAX  Counter
    ACCESS  read-only
    STATUS  mandatory
    DESCRIPTION
           "processor failed to respond to an interrupt quickly enough."
    ::= { isarIhdlcLogPortStatsEntry  10 }

isarIhdlcLogPortStatsDChannelFrameOverFlow OBJECT-TYPE
    SYNTAX  Counter
    ACCESS  read-only
    STATUS  mandatory
    DESCRIPTION
           "The received data of a frame could not be stored because
            the RxFiFo is occupied."
    ::= { isarIhdlcLogPortStatsEntry  11 }

isarIhdlcLogPortStatsDChannelRxDataOverFlow OBJECT-TYPE
    SYNTAX  Counter
    ACCESS  read-only
    STATUS  mandatory
    DESCRIPTION
           "Rx data overflow - byte could not be stored in RxFIFO."
    ::= { isarIhdlcLogPortStatsEntry  12 }

isarIhdlcLogPortStatsDChannelRxCrcError OBJECT-TYPE
    SYNTAX  Counter
    ACCESS  read-only
    STATUS  mandatory
    DESCRIPTION
           "CRC error counter."
    ::= { isarIhdlcLogPortStatsEntry  13 }

isarIhdlcLogPortStatsDChannelRxMessageAborted OBJECT-TYPE
    SYNTAX  Counter
    ACCESS  read-only
    STATUS  mandatory
    DESCRIPTION
           "Rx message aborted counter."
    ::= { isarIhdlcLogPortStatsEntry  14 }

isarIhdlcLogPortStatsDChannelRxLengthOverflow OBJECT-TYPE
    SYNTAX  Counter
    ACCESS  read-only
    STATUS  mandatory
    DESCRIPTION
           "Frame length too long or buffer too small counter."
    ::= { isarIhdlcLogPortStatsEntry  15 }

isarIhdlcLogPortStatsDChannelTxBufferUnderrun OBJECT-TYPE
    SYNTAX  Counter
    ACCESS  read-only
    STATUS  mandatory
    DESCRIPTION
           "Tx buffer underrun counter - no UBD buffer available with Tx 
            data."
    ::= { isarIhdlcLogPortStatsEntry  16 }

isarIhdlcLogPortStatsDChannelRxBufferUnderrun OBJECT-TYPE
    SYNTAX  Counter
    ACCESS  read-only
    STATUS  mandatory
    DESCRIPTION
           "Rx buffer underrun counter - no UBD buffer available to store
            Rx data."
    ::= { isarIhdlcLogPortStatsEntry  17 }



--
-- ISAR hdlcStatisticsMIBObjects : end
--


-- This file cannot be used to create SNMP agent.
-- The file isarOneFile.my has to be used to create the agent.


-- isarIinbandIpMIBObjects       OBJECT IDENTIFIER ::= { isar  28 }


--
-- ISAR inbandIpMIBObjects : begin
--
-- enterprise MIB for ISAR
-- The MIB is written for SNMPv1.


-- ISAR inband IP protocol table
-- extension of the protocol handler table
-- table is optional


isarIinbandIpProtocolHandlerTable OBJECT-TYPE
    SYNTAX  SEQUENCE OF IsarIinbandIpProtocolHandlerEntry
    ACCESS  not-accessible
    STATUS  mandatory
    DESCRIPTION
           "This table contains the inband IP protocol handlers present in
            the system.
            It must be possible to dynamically add and delete entries.
            Creation of an entry in this table results in the creation of
            an entry in the isarIprotocolHandlerTable (done by IAD4700).
            It is the isarIprotocolHandlerTable who determines the index. 
            
            An entry cannot be deleted when it is in use by (an) inband IP
            channel(s)"
    ::= { isarIinbandIpMIBObjects  1 }

isarIinbandIpProtocolHandlerEntry OBJECT-TYPE
    SYNTAX  IsarIinbandIpProtocolHandlerEntry
    ACCESS  not-accessible
    STATUS  mandatory
    DESCRIPTION
           "Description of the inband IP protocol handlers present in the 
            IAD4700."
    INDEX   { isarIinbandIpProtocolHandlerIndex }
    ::= { isarIinbandIpProtocolHandlerTable  1 }


IsarIinbandIpProtocolHandlerEntry ::=
    SEQUENCE {
      isarIinbandIpProtocolHandlerIndex
        INTEGER,

      isarIinbandIpProtocolHandlerMultiplexingMethod
        INTEGER,

      isarIinbandIpProtocolHandlerIpInterfaceId
        INTEGER,

      isarIinbandIpProtocolHandlerRowStatus
        INTEGER
    }

isarIinbandIpProtocolHandlerIndex OBJECT-TYPE
    SYNTAX  INTEGER (0..2147483647)
    ACCESS  read-only
    STATUS  mandatory
    DESCRIPTION
           "Unique protocol handler identification.
            This is the same index as isarIprotocolHandlerIndex in
            isarIprotocolHandlerTable.  
            The manager has to GET the isarIprotocolHandlerNextIndex before
            creating a row in isarIinbandIpProtocolHandlerTable."
    ::= { isarIinbandIpProtocolHandlerEntry  1 }

isarIinbandIpProtocolHandlerMultiplexingMethod OBJECT-TYPE
    SYNTAX  INTEGER {
                      llcEncapsulation(1),
                      vcBasedMultiplexing(2)
            }
    ACCESS  read-write
    STATUS  mandatory
    DESCRIPTION
           "Multiplexing method supported by the protocol handler.
            See RFC 1483 for a description of the methods for carrying
            connectionless network interconnect traffic, routed and
            bridged Protocol Data Units, over an ATM network.
            Modify is not allowed.
            The SNMPv2 MAX-ACCESS is read(-only)-create."
    ::= { isarIinbandIpProtocolHandlerEntry  2 }

isarIinbandIpProtocolHandlerIpInterfaceId OBJECT-TYPE
    SYNTAX  INTEGER
    ACCESS  read-only
    STATUS  mandatory
    DESCRIPTION
           "The index of the IP channel that uses this protocol handler.
            A value 0 indicates: no IP channels.
            A value 1 indicates: several IP channels.
            Otherwise, the index is the same as 
            isarIinbandIpChannelIpInterfaceIndex in the 
            isarIipInterfaceTable.
            The value of this object is initialized by the agent after the
            associated entry in the isarIinbandIpChannelTable has been
            created."
    ::= { isarIinbandIpProtocolHandlerEntry  3 }

isarIinbandIpProtocolHandlerRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIinbandIpProtocolHandlerEntry 4 }



-- inband IP channel table
-- table is optional


isarIinbandIpChannelTable OBJECT-TYPE
    SYNTAX  SEQUENCE OF IsarIinbandIpChannelEntry
    ACCESS  not-accessible
    STATUS  mandatory
    DESCRIPTION
           "This table contains the inband IP channels present in the
            system.
            An entry defines the relation between an inband IP protocol 
            handler and an IP interface.
            It must be possible to dynamically add and delete entries.
            An entry cannot be deleted when it is in use by an inband IP
            interworking function."
    ::= { isarIinbandIpMIBObjects  2 }

isarIinbandIpChannelEntry OBJECT-TYPE
    SYNTAX  IsarIinbandIpChannelEntry
    ACCESS  not-accessible
    STATUS  mandatory
    DESCRIPTION
           "One row in the isarIinbandIpChannelTable."
    INDEX   { isarIinbandIpChannelIpInterfaceIndex }
    ::= { isarIinbandIpChannelTable  1 }


IsarIinbandIpChannelEntry ::=
    SEQUENCE {
      isarIinbandIpChannelIpInterfaceIndex
        INTEGER,

      isarIinbandIpChannelProtocolHandlerIndex
        INTEGER,

      isarIinbandIpChannelRowStatus
        INTEGER,

      isarIinbandIpChannelConnectionIndication
        INTEGER
    }

isarIinbandIpChannelIpInterfaceIndex OBJECT-TYPE
    SYNTAX  INTEGER
    ACCESS  read-only
    STATUS  mandatory
    DESCRIPTION
           "The index of the IP interface of this channel.
            The index is the same as isarIipInterfaceId in the 
            isarIipInterfaceTable."
    ::= { isarIinbandIpChannelEntry  1 }

isarIinbandIpChannelProtocolHandlerIndex OBJECT-TYPE
    SYNTAX  INTEGER
    ACCESS  read-write
    STATUS  mandatory
    DESCRIPTION
           "The index of the inband IP protocol handler of this channel.
            The index is the same as isarIinbandIpProtocolHandlerIndex in
            the isarIinbandIpProtocolHandlerTable.
            Modify is not allowed.
            The SNMPv2 MAX-ACCESS is read(-only)-create."
    ::= { isarIinbandIpChannelEntry  2 }

isarIinbandIpChannelRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in this table.
            The SNMPv2 MAX-ACCESS is read-create."
    ::= { isarIinbandIpChannelEntry  3 }

isarIinbandIpChannelConnectionIndication OBJECT-TYPE
    SYNTAX  INTEGER {
                      inUse(1),
                      free(2)
            }
    ACCESS  read-only
    STATUS  mandatory
    DESCRIPTION
           "This object is used to indicate whether the IP channel is in
            use by an inband IP interworking function.
            The value of this object is initialized by the agent after the
            associated entry in the isarIinbandIpSignallingIwfTable has
            been created."
    ::= { isarIinbandIpChannelEntry  4 }



--
-- ISAR inbandIpMIBObjects : end
--



-- This file cannot be used to create SNMP agent.
-- The file isarOneFile.my has to be used to create the agent.


-- isarIsignallingMIBObjects       OBJECT IDENTIFIER ::= { isar  29 }


--
-- ISAR signallingMIBObjects : begin
--
-- enterprise MIB for ISAR
-- The MIB is written for SNMPv1.


isarIprotocolHandlerNextIndex OBJECT-TYPE
    SYNTAX  INTEGER (0..2147483647)
    ACCESS  read-only
    STATUS  mandatory
    DESCRIPTION
           "This object is used to assist the manager in
            selecting a value for isarIprotocolHandlerIndex.  
            The manager has to GET this index before creating a row in 
            a table that is related to the isarIprotocolHandlerTable (e.g.
            isarIinbandIpProtocolHandlerTable)."
    ::= { isarIsignallingMIBObjects  1 }


-- ISAR protocol handler table
-- table is optional


isarIprotocolHandlerTable OBJECT-TYPE
    SYNTAX  SEQUENCE OF IsarIprotocolHandlerEntry
    ACCESS  not-accessible
    STATUS  mandatory
    DESCRIPTION
           "This table contains protocol handlers present in the system.
            Entries are added and deleted when corresponding entries in
            specific protocol handler tables are added or deleted.
            An entry cannot be deleted when it is in use by (a) signalling
            interworking function(s)."
    ::= { isarIsignallingMIBObjects  2 }

isarIprotocolHandlerEntry OBJECT-TYPE
    SYNTAX  IsarIprotocolHandlerEntry
    ACCESS  not-accessible
    STATUS  mandatory
    DESCRIPTION
           "Description of the protocol handlers present in the IAD4700."
    INDEX   { isarIprotocolHandlerIndex }
    ::= { isarIprotocolHandlerTable  1 }


IsarIprotocolHandlerEntry ::=
    SEQUENCE {
      isarIprotocolHandlerIndex
        INTEGER,

      isarIprotocolHandlerType
        INTEGER,

      isarIprotocolHandlerConnIndex
        INTEGER
    }

isarIprotocolHandlerIndex OBJECT-TYPE
    SYNTAX  INTEGER (0..2147483647)
    ACCESS  read-only
    STATUS  mandatory
    DESCRIPTION
           "Unique protocol handler identification."
    ::= { isarIprotocolHandlerEntry  1 }

isarIprotocolHandlerType OBJECT-TYPE
    SYNTAX  INTEGER {
                      inbandIp(1)
            }
    ACCESS  read-only
    STATUS  mandatory
    DESCRIPTION
           "Identification of the protocol that is executed
            by the protocol handler."
    ::= { isarIprotocolHandlerEntry  2 }

isarIprotocolHandlerConnIndex OBJECT-TYPE
    SYNTAX  INTEGER (0..2147483647)
    ACCESS  read-only
    STATUS  mandatory
    DESCRIPTION
           "The index of the signalling interworking function that uses 
            this protocol handler.
            A value 0 indicates: no interworking functions.
            A value 1 indicates: several interworking functions.
            Otherwise, the index is the same as isarIsignallingIwfConnIndex
            in the isarIsignallingIwfTable.
            The value of this object is initialized by the agent
            after the associated entry in the isarIsignallingIwfTable
            has been created."
    ::= { isarIprotocolHandlerEntry  3 }



-- signalling interworking function table
-- table is optional


isarIsignallingIwfTable OBJECT-TYPE
    SYNTAX  SEQUENCE OF IsarIsignallingIwfEntry
    ACCESS  not-accessible
    STATUS  mandatory
    DESCRIPTION
           "This table contains the signalling interworking functions
            present in the system.
            It must be possible to dynamically add and delete entries.
            An entry cannot be deleted when it is in use by another, 
            coordinating interworking function.
           
            Addition (or deletion) of an entry will automatically add
            (or delete) a corresponding entry in the
            isarIsignallingIwfStatsTable.

            When a row in this table is created, an entry in the
            isarIsignallingIwfMappingTable is made by IAD4700 (inverse mapping
            of index).

             At the same time another table must be updated :
             - set field isarIatmVclCrossConnectIdentifier of the
               corresponding entry in IsarIatmVclEntry with the
               value of isarIthdlcsIwfConnIndex and
             - set field isarIatmVclServiceType of the
               corresponding entry in IsarIatmVclEntry to 'signalling'."
    ::= { isarIsignallingMIBObjects  3 }

isarIsignallingIwfEntry OBJECT-TYPE
    SYNTAX  IsarIsignallingIwfEntry
    ACCESS  not-accessible
    STATUS  mandatory
    DESCRIPTION
           "One row in the isarIsignallingIwfTable."
    INDEX   { isarIsignallingIwfAtmIfIndex,
              isarIsignallingIwfAtmVpi,
              isarIsignallingIwfAtmVci }
    ::= { isarIsignallingIwfTable  1 }


IsarIsignallingIwfEntry ::=
    SEQUENCE {
      isarIsignallingIwfAtmIfIndex
        INTEGER,

      isarIsignallingIwfAtmVpi
        INTEGER,

      isarIsignallingIwfAtmVci
        INTEGER,

      isarIsignallingIwfProtocolHandlerIndex
        INTEGER,

      isarIsignallingIwfServiceIndex
        INTEGER,

      isarIsignallingIwfConnIndex
        INTEGER,

      isarIsignallingIwfAdminStatus
        INTEGER,

      isarIsignallingIwfOperStatus
        INTEGER,

      isarIsignallingIwfRowStatus
        INTEGER,

      isarIsignallingIwfUsageIndication
        INTEGER
    }

isarIsignallingIwfAtmIfIndex OBJECT-TYPE
    SYNTAX  INTEGER
    ACCESS  read-only
    STATUS  mandatory
    DESCRIPTION
           "The ifIndex of the ATM interface of this interworking
            function."
    ::= { isarIsignallingIwfEntry 1 }

isarIsignallingIwfAtmVpi OBJECT-TYPE
    SYNTAX  INTEGER (0..4095)
    ACCESS  read-only
    STATUS  mandatory
    DESCRIPTION
           "The VPI value of the VCL used for this interworking
            function."
    ::= { isarIsignallingIwfEntry 2 }

isarIsignallingIwfAtmVci OBJECT-TYPE
    SYNTAX  INTEGER (0..65535)
    ACCESS  read-only
    STATUS  mandatory
    DESCRIPTION
           "The VCI value of the VCL used for this interworking
            function."
    ::= { isarIsignallingIwfEntry 3 }

isarIsignallingIwfProtocolHandlerIndex OBJECT-TYPE
    SYNTAX  INTEGER
    ACCESS  read-write
    STATUS  mandatory
    DESCRIPTION
           "The index of the protocol handler of this interworking
            function.
            This is the same index as isarIprotocolHandlerIndex of
            the isarIprotocolHandlerTable.
            Modification of this index is not allowed.
            The SNMPv2 MAX-ACCESS is read(-only)-create."
    ::= { isarIsignallingIwfEntry 4 }

isarIsignallingIwfServiceIndex OBJECT-TYPE
    SYNTAX  INTEGER
    ACCESS  read-write
    STATUS  mandatory
    DESCRIPTION
           "The index of the service to which this interworking function
            belongs.
            This is the same index as serviceIndex of isarIserviceTable.
            (it is not allowed to modify this index)
            The SNMPv2 MAX-ACCESS is read(-only)-create."
    ::= { isarIsignallingIwfEntry 5 }

isarIsignallingIwfConnIndex OBJECT-TYPE
    SYNTAX  INTEGER
    ACCESS  read-only
    STATUS  mandatory
    DESCRIPTION
           "The value of this object is equal to the
            isarIiwfNextConnIndex obtained (by IAD4700) to uniqely identify
            this IWF."
    ::= { isarIsignallingIwfEntry 6 }

isarIsignallingIwfAdminStatus OBJECT-TYPE
    SYNTAX  INTEGER {
                      up(1),
                      down(2)
            }
    ACCESS  read-write
    STATUS  mandatory
    DESCRIPTION
           "The administrative state of the interworking function.
            The SNMPv2 MAX-ACCESS is read-create."
    DEFVAL { down }
    ::= { isarIsignallingIwfEntry 7 }

isarIsignallingIwfOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "The operational state of the interworking function.
            Refer to RFC 2233 for the different states."
    ::= { isarIsignallingIwfEntry 8 }


isarIsignallingIwfRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIsignallingIwfEntry  9 }

isarIsignallingIwfUsageIndication OBJECT-TYPE
    SYNTAX  INTEGER {
                      inUse(1),
                      free(2)
            }
    ACCESS  read-only
    STATUS  mandatory
    DESCRIPTION
           "This object is used to indicate whether the interworking 
            function is in use by another, coordinating interworking 
            function.
            The value of this object is set to 'inUse' by the agent after 
            the associated entry has been created."
    ::= { isarIsignallingIwfEntry  10 }


-- signalling iwf mapping

isarIsignallingIwfMappingTable OBJECT-TYPE
    SYNTAX  SEQUENCE OF IsarIsignallingIwfMappingEntry
    ACCESS  not-accessible
    STATUS  mandatory
    DESCRIPTION
           "The signallingIwf mapping table is used to map the IWF index
            into the index of the corresponding entry in the
            isarIsignallingIwfTable."
    ::= { isarIsignallingMIBObjects  4 }

isarIsignallingIwfMappingEntry OBJECT-TYPE
    SYNTAX  IsarIsignallingIwfMappingEntry
    ACCESS  not-accessible
    STATUS  mandatory
    DESCRIPTION
           "An entry in the signallingIwf mapping table."
    INDEX   { isarIsignallingIwfConnIndex }
    ::= { isarIsignallingIwfMappingTable  1 }

IsarIsignallingIwfMappingEntry ::=
    SEQUENCE {
      isarIsignallingIwfMappingAtmIfIndex
        INTEGER,

      isarIsignallingIwfMappingAtmVpi
        INTEGER,

      isarIsignallingIwfMappingAtmVci
        INTEGER
    }

isarIsignallingIwfMappingAtmIfIndex OBJECT-TYPE
    SYNTAX  INTEGER
    ACCESS  read-only
    STATUS  mandatory
    DESCRIPTION
           "Mapped index."
    ::= { isarIsignallingIwfMappingEntry  1 }

isarIsignallingIwfMappingAtmVpi OBJECT-TYPE
    SYNTAX  INTEGER
    ACCESS  read-only
    STATUS  mandatory
    DESCRIPTION
           "Mapped index."
    ::= { isarIsignallingIwfMappingEntry  2 }

isarIsignallingIwfMappingAtmVci OBJECT-TYPE
    SYNTAX  INTEGER
    ACCESS  read-only
    STATUS  mandatory
    DESCRIPTION
           "Mapped index."
    ::= { isarIsignallingIwfMappingEntry  3 }




-- signalling interworking function statistics table
-- table is optional


isarIsignallingIwfStatsTable OBJECT-TYPE
    SYNTAX  SEQUENCE OF IsarIsignallingIwfStatsEntry
    ACCESS  not-accessible
    STATUS  mandatory
    DESCRIPTION
           "This table contains the statistic about the signalling
            interworking functions.
            Creation and deletion of entries is coupled with the
            isarIsignallingIwfTable."
    ::= { isarIsignallingMIBObjects  5 }

isarIsignallingIwfStatsEntry OBJECT-TYPE
    SYNTAX  IsarIsignallingIwfStatsEntry
    ACCESS  not-accessible
    STATUS  mandatory
    DESCRIPTION
           "One row in the isarIsignallingIwfStatsTable."
    INDEX   { isarIsignallingIwfStatsAtmIfIndex,
              isarIsignallingIwfStatsAtmVpi,
              isarIsignallingIwfStatsAtmVci }
    ::= { isarIsignallingIwfStatsTable  1 }


IsarIsignallingIwfStatsEntry ::=
    SEQUENCE {
      isarIsignallingIwfStatsAtmIfIndex
        INTEGER,

      isarIsignallingIwfStatsAtmVpi
        INTEGER,

      isarIsignallingIwfStatsAtmVci
        INTEGER,

      isarIsignallingIwfStatsPhToAsTransmFrames
        Counter,

      isarIsignallingIwfStatsAsToPhTransmFrames
        Counter
    }


isarIsignallingIwfStatsAtmIfIndex OBJECT-TYPE
    SYNTAX  INTEGER
    ACCESS  read-only
    STATUS  mandatory
    DESCRIPTION
           "The ifIndex of the ATM interface of this interworking function."
    ::= { isarIsignallingIwfStatsEntry 1 }

isarIsignallingIwfStatsAtmVpi OBJECT-TYPE
    SYNTAX  INTEGER (0..4095)
    ACCESS  read-only
    STATUS  mandatory
    DESCRIPTION
           "The VPI value of the VCL used for this interworking function."
    ::= { isarIsignallingIwfStatsEntry 2 }

isarIsignallingIwfStatsAtmVci OBJECT-TYPE
    SYNTAX  INTEGER (0..65535)
    ACCESS  read-only
    STATUS  mandatory
    DESCRIPTION
           "The VCI value of the VCL used for this interworking function."
    ::= { isarIsignallingIwfStatsEntry 3 }

isarIsignallingIwfStatsPhToAsTransmFrames OBJECT-TYPE
    SYNTAX  Counter
    ACCESS  read-only
    STATUS  mandatory
    DESCRIPTION
           "The number of frames that have been sent to the aggregate
            side by the protocol handler."
    ::= { isarIsignallingIwfStatsEntry 4 }

isarIsignallingIwfStatsAsToPhTransmFrames OBJECT-TYPE
    SYNTAX  Counter
    ACCESS  read-only
    STATUS  mandatory
    DESCRIPTION
           "The number of frames that have been received at the
            aggregate side and have been sent to the protocol handler
            by this interworking function."
    ::= { isarIsignallingIwfStatsEntry 5 }



-- inband IP signalling interworking function table
-- table is optional


isarIinbandIpSignallingIwfTable OBJECT-TYPE
    SYNTAX  SEQUENCE OF IsarIinbandIpSignallingIwfEntry
    ACCESS  not-accessible
    STATUS  mandatory
    DESCRIPTION
           "This table contains the inband IP signalling interworking
            functions present in the system.
            It must be possible to dynamically add and delete entries."
    ::= { isarIsignallingMIBObjects  6 }

isarIinbandIpSignallingIwfEntry OBJECT-TYPE
    SYNTAX  IsarIinbandIpSignallingIwfEntry
    ACCESS  not-accessible
    STATUS  mandatory
    DESCRIPTION
           "Describes an inband IP signalling interworking function,
            the relation between a signalling interworking function and
            an inband IP channel."
    INDEX   { isarIinbandIpSignallingIwfConnIndex,
              isarIinbandIpSignallingIwfIpInterfaceIndex }
    ::= { isarIinbandIpSignallingIwfTable  1 }


IsarIinbandIpSignallingIwfEntry ::=
    SEQUENCE {
      isarIinbandIpSignallingIwfServiceIndex
        INTEGER,

      isarIinbandIpSignallingIwfConnIndex
        INTEGER,

      isarIinbandIpSignallingIwfIpInterfaceIndex
        INTEGER,

      isarIinbandIpSignallingIwfRowStatus
        INTEGER
    }

isarIinbandIpSignallingIwfServiceIndex OBJECT-TYPE
    SYNTAX  INTEGER
    ACCESS  read-only
    STATUS  mandatory
    DESCRIPTION
           "The index of the service to which this interworking function
            belongs.
            This is the same index as serviceIndex of isarIserviceTable."
    ::= { isarIinbandIpSignallingIwfEntry 1 }

isarIinbandIpSignallingIwfConnIndex OBJECT-TYPE
    SYNTAX  INTEGER
    ACCESS  read-only
    STATUS  mandatory
    DESCRIPTION
           "The index of the signalling connection.
            Is equal to isarIsignallingIwfConnIndex in the 
            isarIsignallingIwfTable."
    ::= { isarIinbandIpSignallingIwfEntry 2 }

isarIinbandIpSignallingIwfIpInterfaceIndex OBJECT-TYPE
    SYNTAX  INTEGER
    ACCESS  read-only
    STATUS  mandatory
    DESCRIPTION
           "The index of the IP interface of this channel.
            The index is the same as isarIipInterfaceId in
            the isarIipInterfaceTable."
    ::= { isarIinbandIpSignallingIwfEntry 3 }

isarIinbandIpSignallingIwfRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIinbandIpSignallingIwfEntry  4 }



-- trap defined in isarIiwfMIBObjects

--
-- ISAR signallingMIBObjects : end
--




-- This file cannot be used to create SNMP agent.
-- The file isarOneFile.my has to be used to create the agent.




-- isarItftpMIBObjects  OBJECT IDENTIFIER ::= { isar  27 }



--
-- ISAR tftpMIBObjects : begin
--  
-- enterprise MIB for configuration TFTP
-- The MIB is written for SNMPv1.



-- For TFTP a server specific userid and password are not needed.
-- TFTP MIB objects are not persistent


isarItftpLock OBJECT-TYPE
    SYNTAX  INTEGER {
                      true(1),
                      false(2)
            }
    ACCESS  read-write
    STATUS  mandatory
    DESCRIPTION
           "This flag indicates if the IAD4700 file system is locked for
            TFTP actions by an SNMP manager (based on IpAddress).
            If the IAD4700 file system is not locked for TFTP actions 
            (isarItftpLock = false), one SNMP manager can lock it by 
            setting isarItftpLock to true.  TFTP actions can be done by  
            this SNMP manager. TFTP actions from other SNMP managers (= 
            other IpAddress) will be refuced.
            The IAD4700 file system can be unlocked for TFTP actions on 3 
            ways :
            1. The SNMP manager who has set isarItftpLock to true can set 
               isarItftpLock to false.
            2. automatically after end of TFTP actions
            2. after a time out (timer value larger than time to download 
               all selected load palettes)."
    ::= { isarItftpMIBObjects 1 }


-- The following objects can only be changed when isarItftpLock=true
-- (reading is always possible)

isarItftpIpAddress OBJECT-TYPE
    SYNTAX  IpAddress
    ACCESS  read-write
    STATUS  mandatory
    DESCRIPTION
           "IP address of TFTP server platform from where download/upload
            action will take place.
            Default=0.0.0.0 ."
    ::= { isarItftpMIBObjects  2 }

isarItftpPort OBJECT-TYPE
    SYNTAX  INTEGER (0..65535)
    ACCESS  read-write
    STATUS  mandatory
    DESCRIPTION
           "A non-zero value specifies the portnumber of the TFTP server.
            Zero means that the default port number (=69 for TFTP) will be
            used."
    ::= { isarItftpMIBObjects  3 }


isarItftpError OBJECT-TYPE
    SYNTAX  DisplayString
    ACCESS  read-only
    STATUS  mandatory
    DESCRIPTION
           "A string that gives more information about the reason why
            tftp failed (e.g. lack of resources)."
    ::= { isarItftpMIBObjects  12 }





-- It should be possible to upload (from IAD4700 to TFTP server) or download
-- (from TFTP server to IAD4700) a single file of a primary or secondary MAMO
-- or active PM load palette.
-- This single file can be :
-- for the MAMO : initialisation file, MLS file, SNMP configuration file
--                and the configuration file (= persistent store of the
--                running load)
-- for an active PM : initialisation file

isarItftpFileLoad OBJECT-TYPE
    SYNTAX  INTEGER {
                      primaryMamo(1),
                      secondaryMamo(2),
                      primaryPM1(3),
                      secondaryPM1(4),
                      primaryPM2(5),
                      secondaryPM2(6),
                      primaryPM3(7),
                      secondaryPM3(8)
            }
    ACCESS  read-write
    STATUS  mandatory
    DESCRIPTION
           "MAMO or PM Load Palette from/to where the file will be
            uploaded/downloaded.
            PMx is the PM in slotx.
            Initial value = secondaryMamo"
    ::= { isarItftpMIBObjects 4 }

isarItftpFileLocation OBJECT-TYPE
    SYNTAX  DisplayString (SIZE (0..100))
    ACCESS  read-write
    STATUS  mandatory
    DESCRIPTION
           "Location (directory and filename) where TFTP server 
            will look for or put the file. This location must be
            relative to the location where the TFTP server is 
            started. 
            E.g. '/tftp/upload' is used as directory for upload; 
                 TFTP server is started in '/tftp';
                 isarItftpFileLocation must be set to 
                 '/upload/filename'.
            Initial value = an empty string."
    ::= { isarItftpMIBObjects 5 }

isarItftpFileAction OBJECT-TYPE
    SYNTAX  INTEGER {
                      noAction(1),
                      uploadConfigFile(2),
                      downloadConfigFile(3),
                      uploadInifile(4),
                      downloadInifile(5),
                      uploadMlsfile(6),
                      downloadMlsfile(7),
                      uploadSnmpConfigfile(8),
                      downloadSnmpConfigfile(9)
            }
    ACCESS  read-write
    STATUS  mandatory
    DESCRIPTION
           "1. read-only value (SET of this value is not allowed)
            2. TFTP upload (IAD4700 -> TFTP server) of configuration file
            3. TFTP download (TFTP server -> IAD4700) of configuration file.
            4. TFTP upload (IAD4700 -> TFTP server) of initialisation file
            5. TFTP download (TFTP server -> IAD4700) of initialisation file.
            6. TFTP upload (IAD4700 -> TFTP server) of MLS file
            7. TFTP download (TFTP server -> IAD4700) of MLS file.
            8. TFTP upload (IAD4700 -> TFTP server) of SNMP config file
            9. TFTP download (TFTP server -> IAD4700) of SNMP config file.
            Initial value = noAction (reset by IAD4700)."
    ::= { isarItftpMIBObjects 6 }

isarItftpFileStatus OBJECT-TYPE
    SYNTAX  INTEGER {
                      initial(1),
                      tftpActionStarted(2),
                      tftpActionSucceeded(3),
                      tftpActionFailed(4),
                      fileNotFound(7),
                      emptySlot(8),
                      unknownModule(9),
                      invalidModule(10),
                      notArmedModule(11),
                      passiveModule(12),
                      slotEntryNotFound(13),
                      actionNotAllowed(14)
            }
    ACCESS  read-only
    STATUS  mandatory
    DESCRIPTION
           " 1. initial status
             2. download/upload of file started
             3. download/upload of file successful
             4. download/upload of file unsuccessful
             7. unable to open or create the file on IAD4700
             8. action not started because isarIslotType = empty
             9. action not started because isarIslotType = unknown
            10. action not started because isarIslotType = invalid
            11. action not started because isarIisArmed = false
            12. action not started because isarIssCompatibility = 
                notApplicable
            13. entry in slot table not found
            14. invalid combination of isarItftpFileAction and 
                isarItftpFileLoad (active PM has no configuration files 
                and no MLS file)
            Initial value = initial (reset by IAD4700 at the start of a 
            new action)."
    ::= { isarItftpMIBObjects 7 }

isarItftpFileTimeStamp OBJECT-TYPE
    SYNTAX  TimeTicks
    ACCESS  read-only
    STATUS  mandatory
    DESCRIPTION
           "Time when TFTP action has ended.
            Initial value = 0 (reset by IAD4700 at the start of a 
            new action)."
    ::= { isarItftpMIBObjects 8 }






-- The MAMO and each armed active PM can have both a primary and a 
-- secondary load palette. It should be possible to download (from TFTP 
-- server to IAD4700) such a load palette (without configuration file). 
-- The load palettes are stored on the corresponding module and this means
-- that when an active PM is not armed, it is not possible to download a 
-- load palette for this PM.
-- The isarItftpLoadTable contains for each slot, information about 
-- load palettes to be downloaded.


isarItftpDownload OBJECT-TYPE
    SYNTAX  INTEGER {
                      no(1),
                      yes(2)
            }
    ACCESS  read-write
    STATUS  mandatory
    DESCRIPTION
           "Trigger to start the TFTP download of a complete (but without
            configuration file) load palettes as indicated in
            isarItftpLoadTable.
            1 = no TFTP download
            2 = start TFTP download
            Is set back to no after end of download."
    ::= { isarItftpMIBObjects 9 }




-- info about next download action(s)


isarItftpLoadTable OBJECT-TYPE
    SYNTAX  SEQUENCE OF IsarItftpLoadEntry
    ACCESS  not-accessible
    STATUS  mandatory
    DESCRIPTION
           "Table with the to be downloaded load palettes.
            The table is created by IAD4700."
    ::= { isarItftpMIBObjects  10 }

isarItftpLoadEntry OBJECT-TYPE
    SYNTAX  IsarItftpLoadEntry
    ACCESS  not-accessible
    STATUS  mandatory
    DESCRIPTION
           "One row in the isarItftpLoadTable."
    INDEX   { isarItftpLoadId, isarIphysSlotId }
    ::= { isarItftpLoadTable  1 }


IsarItftpLoadEntry ::=
    SEQUENCE { 
      isarItftpLoadId
        INTEGER,

      isarItftpLoadLocation
        DisplayString,

      isarItftpLoadDownload
        INTEGER,
        
      isarItftpLoadStatus
        INTEGER

    }
    
isarItftpLoadId OBJECT-TYPE
    SYNTAX  INTEGER {
                      primary(1),
                      secondary(2)
            }
    ACCESS  read-only
    STATUS  mandatory
    DESCRIPTION
           "The primary or secondary load palette."
    ::= { isarItftpLoadEntry  1 }

-- next fields have only meaning for 
-- MAMO or known armed active PMs


isarItftpLoadLocation OBJECT-TYPE
    SYNTAX  DisplayString (SIZE (0..100))
    ACCESS  read-write
    STATUS  mandatory
    DESCRIPTION
           "Location (drive and directory) where TFTP server will look
            for the complete load palette.
            E.g. 'C:\directory' ."
    ::= { isarItftpLoadEntry  3 }

isarItftpLoadDownload OBJECT-TYPE
    SYNTAX  INTEGER {
                      no(1),
                      yes(2)
            }
    ACCESS  read-write
    STATUS  mandatory
    DESCRIPTION
           "Flag indicating that this load palette has to be downloaded
            when the download action is triggered (via isarItftpDownload).
            This flag will be set to 'no' by IAD4700 after the download."
    ::= { isarItftpLoadEntry  4 }

isarItftpLoadStatus OBJECT-TYPE
    SYNTAX  INTEGER {
                      initial(1),
                      loadInUse(2),
                      tftpDownloadStarted(5),
                      tftpDownloadSucceeded(6),
                      tftpDownloadFailed(7),
                      emptySlot(8),
                      unknownModule(9),
                      invalidModule(10),
                      notArmedModule(11),
                      passiveModule(12)
            }
    ACCESS  read-only
    STATUS  mandatory
    DESCRIPTION
           "Status of the TFTP download action.
             1 : initial status
             2 : when the load is in use by IAD4700
                 i.e. isarIthisLoad(isarIphysSlotId) = tftpLoadId
             5 : when TFTP download has started
             6 : when TFTP download has succeeded
             7 : when TFTP download has failed
             8 : download not started because isarIslotType = empty
             9 : download not started because isarIslotType = unknown
            10 : download not started because isarIslotType = invalid
            11 : download not started because isarIisArmed = false
            12 : download not started because isarIssCompatibility = 
                 notApplicable
            Initial value = 1."
    ::= { isarItftpLoadEntry  5 }


isarItftpTraps OBJECT IDENTIFIER ::= { isarItftpMIBObjects  11 }

isarItftpFileStatus TRAP-TYPE
    ENTERPRISE  isarItftpTraps
    VARIABLES   { isarItftpFileStatus,
                  isarItftpError }
    DESCRIPTION
           "An indication of the status of the file upload/download."
    ::= 1

isarItftpDownloadStatus TRAP-TYPE
    ENTERPRISE  isarItftpTraps
    VARIABLES   { isarIphysSlotId,
                  isarItftpLoadId,
                  isarItftpLoadStatus,
                  isarItftpError }
    DESCRIPTION
           "An indication of the status of the load palette download."
    ::= 2


--
-- ISAR tftpMIBObjects : end
--  




-- This file cannot be used to create SNMP agent.
-- The file isarOneFile.my has to be used to create the agent.




-- isarItimeMIBObjects  OBJECT IDENTIFIER ::= { isar  31 }



--
-- ISAR timeMIBObjects : begin
--  
-- enterprise MIB for configuration TIME
-- The MIB is written for SNMPv1.



-- TIME MIB objects are not persistent

isarItimeYear OBJECT-TYPE
    SYNTAX  INTEGER (1900..2147483647)
    ACCESS  read-write
    STATUS  mandatory
    DESCRIPTION
           ""
    ::= { isarItimeMIBObjects 1 }

isarItimeMonth OBJECT-TYPE
    SYNTAX  INTEGER (0..11)
    ACCESS  read-write
    STATUS  mandatory
    DESCRIPTION
           ""
    ::= { isarItimeMIBObjects 2 }

isarItimeDay OBJECT-TYPE
    SYNTAX  INTEGER (1..31)
    ACCESS  read-write
    STATUS  mandatory
    DESCRIPTION
           ""
    ::= { isarItimeMIBObjects 3 }

isarItimeHour OBJECT-TYPE
    SYNTAX  INTEGER (0..23)
    ACCESS  read-write
    STATUS  mandatory
    DESCRIPTION
           ""
    ::= { isarItimeMIBObjects 4 }

isarItimeMinutes OBJECT-TYPE
    SYNTAX  INTEGER (0..59)
    ACCESS  read-write
    STATUS  mandatory
    DESCRIPTION
           ""
    ::= { isarItimeMIBObjects 5 }

isarItimeSeconds OBJECT-TYPE
    SYNTAX  INTEGER (0..59)
    ACCESS  read-write
    STATUS  mandatory
    DESCRIPTION
           ""
    ::= { isarItimeMIBObjects 6 }


-- This file cannot be used to create SNMP agent.
-- The file isarOneFile.my has to be used to create the agent.


-- isarIsonetMIBObjects      OBJECT IDENTIFIER ::= { isar  32 }


--
-- ISAR sonetMIBObjects : begin
--
-- This MIB is based on one of the MIBs described in IETF RFC 1595
-- The MIB is written for SNMPv1.
-- The textual conventions have been replaced by their base types
-- (because the 45020 does not know these textual conventions).
--

-- created from sonetMIB (9401030000Z)

--  This is the MIB module for the SONET/SDH objects



isarIsonetObjects OBJECT IDENTIFIER ::= { isarIsonetMIBObjects  1 }

isarIsonetObjectsPath OBJECT IDENTIFIER ::= { isarIsonetMIBObjects  2 }

isarIsonetMedium OBJECT IDENTIFIER ::= { isarIsonetObjects  1 }

isarIsonetSection OBJECT IDENTIFIER ::= { isarIsonetObjects  2 }

isarIsonetLine OBJECT IDENTIFIER ::= { isarIsonetObjects  3 }

isarIsonetFarEndLine OBJECT IDENTIFIER ::= { isarIsonetObjects  4 }

isarIsonetPath OBJECT IDENTIFIER ::= { isarIsonetObjectsPath  1 }

isarIsonetFarEndPath OBJECT IDENTIFIER ::= { isarIsonetObjectsPath  2 }

isarIsonetAtm OBJECT IDENTIFIER ::= { isarIsonetMIBObjects  3 }

isarIsonetThresholds OBJECT IDENTIFIER ::= { isarIsonetMIBObjects  4 }


-- the SONET/SDH Medium group

-- SONET/SDH interfaces for some applications may be
-- electrical interfaces and not optical interfaces.
-- This group handles the configuration information for
-- both optical SONET/SDH interfaces and electrical
-- SONET/SDH interfaces.

isarIsonetMediumTable OBJECT-TYPE
    SYNTAX  SEQUENCE OF IsarIsonetMediumEntry
    ACCESS  not-accessible
    STATUS  mandatory
    DESCRIPTION
           "The SONET/SDH Medium table."
    ::= { isarIsonetMedium  1 }

isarIsonetMediumEntry OBJECT-TYPE
    SYNTAX  IsarIsonetMediumEntry
    ACCESS  not-accessible
    STATUS  mandatory
    DESCRIPTION
           "An entry in the SONET/SDH Medium table."
    INDEX   { ifIndex }
    ::= { isarIsonetMediumTable  1 }

IsarIsonetMediumEntry ::=
    SEQUENCE {
      isarIsonetMediumType
        INTEGER,

      isarIsonetMediumTimeElapsed
        INTEGER,

      isarIsonetMediumValidIntervals
        INTEGER,

      isarIsonetMediumLineCoding
        INTEGER,

      isarIsonetMediumLineType
        INTEGER,

      isarIsonetMediumCircuitIdentifier
        DisplayString,

      isarIsonetMediumAutoPrdi
        INTEGER,

      isarIsonetMediumAutoLrdi
        INTEGER,

      isarIsonetMediumAutoFeBe
        INTEGER,

      isarIsonetMediumClockMode
        INTEGER,

      isarIsonetMediumLoopMode
        INTEGER,

      isarIsonetMediumLaserStatus
        INTEGER
    }

isarIsonetMediumType OBJECT-TYPE
    SYNTAX  INTEGER {
                      sonet(1),
                      sdh(2)
            }
    ACCESS  read-write
    STATUS  mandatory
    DESCRIPTION
           "This variable identifies whether a SONET (= Sts3c)
            or a SDH (= Stm1) signal is used across this interface."
    ::= { isarIsonetMediumEntry  1 }

isarIsonetMediumTimeElapsed OBJECT-TYPE
    SYNTAX  INTEGER (1..900)
    ACCESS  read-only
    STATUS  mandatory
    DESCRIPTION
           "The number of seconds, including partial
            seconds, that have elapsed since the beginning of
            the current error-measurement period."
    ::= { isarIsonetMediumEntry  2 }

isarIsonetMediumValidIntervals OBJECT-TYPE
    SYNTAX  INTEGER (0..96)
    ACCESS  read-only
    STATUS  mandatory
    DESCRIPTION
           "The number of previous intervals for which valid
            data has been stored.  A SONET device must support
            at least n intervals.
            The minimum value of n is 4.
            The default of n is 32.
            The maximum value of n is 96.
            The value of this object will be n unless
            the device was brought online within the last
            (nx15) minutes, in which case the value will be the
            number of complete 15 minute intervals the device has
            been online.
            IAD4700 : the maximum value of n will be used."
    ::= { isarIsonetMediumEntry  3 }

isarIsonetMediumLineCoding OBJECT-TYPE
    SYNTAX  INTEGER {
                      nrz(4)
            }
    ACCESS  read-only
    STATUS  mandatory
    DESCRIPTION
           "This variable describes the line coding for
            this interface.
            The Non-Return to Zero (NRZ) is used for optical SONET/SDH 
            signals."
    ::= { isarIsonetMediumEntry  4 }

isarIsonetMediumLineType OBJECT-TYPE
    SYNTAX  INTEGER {
                      sonetOther(1),
                      shortReach(7),
                      intermediateReach(8),
                      longReach(9),
                      veryLongReach(10)
            }
    ACCESS  read-only
    STATUS  mandatory
    DESCRIPTION
           "This variable describes the line type for
            this interface. The line types are
            short Reach, intermediate Reach, long Reach
            and very Long Reach for optical interfaces.  The
            value sonetOther should be used when the Line Type is
            not one of the listed values."
    ::= { isarIsonetMediumEntry  5 }

isarIsonetMediumCircuitIdentifier OBJECT-TYPE
    SYNTAX  DisplayString (SIZE (0..255))
    ACCESS  read-only
    STATUS  mandatory
    DESCRIPTION
           "This variable contains the transmission
            vendor's circuit identifier, for the
            purpose of facilitating troubleshooting."
    ::= { isarIsonetMediumEntry  6 }

isarIsonetMediumAutoPrdi OBJECT-TYPE
    SYNTAX  INTEGER {
                      on(1),
                      off(2)
            }
    ACCESS  read-write
    STATUS  mandatory
    DESCRIPTION
           "When 'on' : automatically send Path RDI on detection of alarm."
    ::= { isarIsonetMediumEntry  7 }

isarIsonetMediumAutoLrdi OBJECT-TYPE
    SYNTAX  INTEGER {
                      on(1),
                      off(2)
            }
    ACCESS  read-write
    STATUS  mandatory
    DESCRIPTION
           "When 'on' : automatically send Line RDI on detection of alarm."
    ::= { isarIsonetMediumEntry  8 }

isarIsonetMediumAutoFeBe OBJECT-TYPE
    SYNTAX  INTEGER {
                      on(1),
                      off(2)
            }
    ACCESS  read-write
    STATUS  mandatory
    DESCRIPTION
           "When 'on' : automatically send Path Line End Path FEBE on
            detection of alarm."
    ::= { isarIsonetMediumEntry  9 }

isarIsonetMediumClockMode OBJECT-TYPE
    SYNTAX  INTEGER {
                      loopTimed(1),
                      localTimed(2)
            }
    ACCESS  read-write
    STATUS  mandatory
    DESCRIPTION
           "Specifies the operating mode of the clock.
            'loopTimed' indicates that the recovered receive 
             clock is used as the transmit clock.

            'localTimed' (also called system timed) indicates that a local
             clock source is used or when an external clock is attached
             to the box containing the interface."
    ::= { isarIsonetMediumEntry  10 }

isarIsonetMediumLoopMode OBJECT-TYPE
    SYNTAX  INTEGER {
                      loopModeNone(1),
                      loopModeLine(2),
                      loopModeSerialDiagnostics(3),
                      loopModeParallelDiagnostics(4)
            }
    ACCESS  read-write
    STATUS  mandatory
    DESCRIPTION
           "For test purposes only.
            loopModeNone
                sending looped or normal data

            loopModeLine
                sending a request for a line loopback

            loopModeSerialDiagnostics
                inward loop at service interface of framer

            loopModeParallelDiagnostics
                inward loop at parallel interface of framer."
    ::= { isarIsonetMediumEntry  11 }

isarIsonetMediumLaserStatus OBJECT-TYPE
    SYNTAX  INTEGER {
                      on(1),
                      off(2)
            }
    ACCESS  read-only
    STATUS  mandatory
    DESCRIPTION
           "Status of the laser."
    ::= { isarIsonetMediumEntry  12 }



-- the SONET/SDH Section group

-- this group consists of 2 tables:
-- - the SONET/SDH Section Current Table
-- - the SONET/SDH Section Interval Table



-- the SONET/SDH Section Current Table

-- The SONET/SDH Section
-- current table contains various statistics
-- being collected for the current 15 minute interval.

isarIsonetSectionCurrentTable OBJECT-TYPE
    SYNTAX  SEQUENCE OF IsarIsonetSectionCurrentEntry
    ACCESS  not-accessible
    STATUS  mandatory
    DESCRIPTION
           "The SONET/SDH Section Current table."
    ::= { isarIsonetSection  1 }

isarIsonetSectionCurrentEntry OBJECT-TYPE
    SYNTAX  IsarIsonetSectionCurrentEntry
    ACCESS  not-accessible
    STATUS  mandatory
    DESCRIPTION
           "An entry in the SONET/SDH Section Current table."
    INDEX   { ifIndex }
    ::= { isarIsonetSectionCurrentTable  1 }

IsarIsonetSectionCurrentEntry ::=
    SEQUENCE {
      isarIsonetSectionCurrentStatus
        INTEGER,

      isarIsonetSectionCurrentESs
        Gauge,

      isarIsonetSectionCurrentSESs
        Gauge,

      isarIsonetSectionCurrentSEFSs
        Gauge,

      isarIsonetSectionCurrentCVs
        Gauge
    }

isarIsonetSectionCurrentStatus OBJECT-TYPE
    SYNTAX  INTEGER (1..6)
    ACCESS  read-only
    STATUS  mandatory
    DESCRIPTION
           "This variable indicates the
            status of the interface.
            The isarIsonetSectionCurrentStatus
            is a bit map represented
            as a sum, therefore,
            it can represent multiple defects
            simultaneously.
            The sonetSectionNoDefect should be
            set if and only if
            no other flag is set.

            The various bit positions are:
             1   sonetSectionNoDefect
             2   sonetSectionLOS
             4   sonetSectionLOF"
    ::= { isarIsonetSectionCurrentEntry  1 }

isarIsonetSectionCurrentESs OBJECT-TYPE
    SYNTAX  Gauge
    ACCESS  read-only
    STATUS  mandatory
    DESCRIPTION
           "The counter associated with the number of Errored
            Seconds encountered by a SONET/SDH
            Section in the current 15 minute interval."
    ::= { isarIsonetSectionCurrentEntry  2 }

isarIsonetSectionCurrentSESs OBJECT-TYPE
    SYNTAX  Gauge
    ACCESS  read-only
    STATUS  mandatory
    DESCRIPTION
           "The counter associated with the number of
            Severely Errored Seconds
            encountered by a SONET/SDH Section in the current 15
            minute interval."
    ::= { isarIsonetSectionCurrentEntry  3 }

isarIsonetSectionCurrentSEFSs OBJECT-TYPE
    SYNTAX  Gauge
    ACCESS  read-only
    STATUS  mandatory
    DESCRIPTION
           "The counter associated with the number of
            Severely Errored Framing Seconds
            encountered by a SONET/SDH Section in the current
            15 minute interval."
    ::= { isarIsonetSectionCurrentEntry  4 }

isarIsonetSectionCurrentCVs OBJECT-TYPE
    SYNTAX  Gauge
    ACCESS  read-only
    STATUS  mandatory
    DESCRIPTION
           "The counter associated with the number of Coding
            Violations encountered by a
            SONET/SDH Section in the current 15 minute interval."
    ::= { isarIsonetSectionCurrentEntry  5 }



-- the SONET/SDH Section Interval Table

-- The SONET/SDH Section Interval Table
-- contains various statistics
-- collected by each system over a maximum
-- of the previous 24 hours of
-- operation.  The past 24 hours may be broken into 96
-- completed 15 minute intervals.
-- A system is required to store at
-- least 4 completed 15 minute interval.
-- The default value is 32 intervals.
-- IAD4700 : the maximum value of n will be used.

isarIsonetSectionIntervalTable OBJECT-TYPE
    SYNTAX  SEQUENCE OF IsarIsonetSectionIntervalEntry
    ACCESS  not-accessible
    STATUS  mandatory
    DESCRIPTION
           "The SONET/SDH Section Interval table."
    ::= { isarIsonetSection  2 }

isarIsonetSectionIntervalEntry OBJECT-TYPE
    SYNTAX  IsarIsonetSectionIntervalEntry
    ACCESS  not-accessible
    STATUS  mandatory
    DESCRIPTION
           "An entry in the SONET/SDH Section Interval table."
    INDEX   { ifIndex,  isarIsonetSectionIntervalNumber }
    ::= { isarIsonetSectionIntervalTable  1 }

IsarIsonetSectionIntervalEntry ::=
    SEQUENCE {
      isarIsonetSectionIntervalNumber
        INTEGER,

      isarIsonetSectionIntervalESs
        Gauge,

      isarIsonetSectionIntervalSESs
        Gauge,

      isarIsonetSectionIntervalSEFSs
        Gauge,

      isarIsonetSectionIntervalCVs
        Gauge,

      isarIsonetSectionIntervalTimeStamp
        TimeTicks
    }

isarIsonetSectionIntervalNumber OBJECT-TYPE
    SYNTAX  INTEGER (1..96)
    ACCESS  not-accessible
    STATUS  mandatory
    DESCRIPTION
           "A number between 1 and 96, which identifies the
            interval for which the set of statistics is available.
            The interval identified by 1 is the most recently
            completed 15 minute interval,
            and the interval identified by N is the interval immediately
            preceding the one identified by N-1.
            IAD4700 : the maximum value of n will be used."
    ::= { isarIsonetSectionIntervalEntry  1 }

isarIsonetSectionIntervalESs OBJECT-TYPE
    SYNTAX  Gauge
    ACCESS  read-only
    STATUS  mandatory
    DESCRIPTION
           "The counter associated with the number of
            Errored Seconds encountered
            by a SONET/SDH Section in a
            particular 15-minute interval
            in the past 24 hours."
    ::= { isarIsonetSectionIntervalEntry  2 }

isarIsonetSectionIntervalSESs OBJECT-TYPE
    SYNTAX  Gauge
    ACCESS  read-only
    STATUS  mandatory
    DESCRIPTION
           "The counter associated with the number of
            Severely Errored Seconds
            encountered by a SONET/SDH Section in a
            particular 15-minute interval
            in the past 24 hours."
    ::= { isarIsonetSectionIntervalEntry  3 }

isarIsonetSectionIntervalSEFSs OBJECT-TYPE
    SYNTAX  Gauge
    ACCESS  read-only
    STATUS  mandatory
    DESCRIPTION
           "The counter associated with the number of
            Severely Errored Framing Seconds
            encountered by a SONET/SDH Section in a
            particular 15-minute interval
            in the past 24 hours."
    ::= { isarIsonetSectionIntervalEntry  4 }

isarIsonetSectionIntervalCVs OBJECT-TYPE
    SYNTAX  Gauge
    ACCESS  read-only
    STATUS  mandatory
    DESCRIPTION
           "The counter associated with the number of Coding
            Violations encountered by a
            SONET/SDH Section in a particular 15-minute interval
            in the past 24 hours."
    ::= { isarIsonetSectionIntervalEntry  5 }

isarIsonetSectionIntervalTimeStamp OBJECT-TYPE
    SYNTAX  TimeTicks
    ACCESS  read-only
    STATUS  mandatory
    DESCRIPTION
           "Start of interval."
    ::= { isarIsonetSectionIntervalEntry  6 }


isarIsonetLineCurrentTable OBJECT-TYPE
    SYNTAX  SEQUENCE OF IsarIsonetLineCurrentEntry
    ACCESS  not-accessible
    STATUS  mandatory
    DESCRIPTION
           "The SONET/SDH Line Current table."
    ::= { isarIsonetLine  1 }


-- the SONET/SDH Line group

-- this group consists of 2 tables:
-- - the SONET/SDH Line Current Table
-- - the SONET/SDH Line Interval Table


-- the SONET/SDH Line Current Table

-- The SONET/SDH Line
-- current table contains various statistics
-- being collected for the current 15 minute interval.

isarIsonetLineCurrentEntry OBJECT-TYPE
    SYNTAX  IsarIsonetLineCurrentEntry
    ACCESS  not-accessible
    STATUS  mandatory
    DESCRIPTION
           "An entry in the SONET/SDH Line Current table."
    INDEX   { ifIndex }
    ::= { isarIsonetLineCurrentTable  1 }

IsarIsonetLineCurrentEntry ::=
    SEQUENCE {
      isarIsonetLineCurrentStatus
        INTEGER,

      isarIsonetLineCurrentESs
        Gauge,

      isarIsonetLineCurrentSESs
        Gauge,

      isarIsonetLineCurrentCVs
        Gauge,

      isarIsonetLineCurrentUASs
        Gauge
    }

isarIsonetLineCurrentStatus OBJECT-TYPE
    SYNTAX  INTEGER (1..6)
    ACCESS  read-only
    STATUS  mandatory
    DESCRIPTION
           "This variable indicates the
            status of the interface.
            The isarIsonetLineCurrentStatus
            is a bit map represented
            as a sum, therefore,
            it can represent multiple defects
            simultaneously.
            The sonetLineNoDefect should be
            set if and only if
            no other flag is set.

            The various bit positions are:
             1   sonetLineNoDefect
             2   sonetLineAIS
             4   sonetLineRDI"
    ::= { isarIsonetLineCurrentEntry  1 }

isarIsonetLineCurrentESs OBJECT-TYPE
    SYNTAX  Gauge
    ACCESS  read-only
    STATUS  mandatory
    DESCRIPTION
           "The counter associated with the number of Errored
            Seconds encountered by a SONET/SDH
            Line in the current 15 minute interval."
    ::= { isarIsonetLineCurrentEntry  2 }

isarIsonetLineCurrentSESs OBJECT-TYPE
    SYNTAX  Gauge
    ACCESS  read-only
    STATUS  mandatory
    DESCRIPTION
           "The counter associated with the number of
            Severely Errored Seconds
            encountered by a SONET/SDH Line in the current 15
            minute
            interval."
    ::= { isarIsonetLineCurrentEntry  3 }

isarIsonetLineCurrentCVs OBJECT-TYPE
    SYNTAX  Gauge
    ACCESS  read-only
    STATUS  mandatory
    DESCRIPTION
           "The counter associated with the number of Coding
            Violations encountered by a
            SONET/SDH Line in the current 15 minute interval."
    ::= { isarIsonetLineCurrentEntry  4 }

isarIsonetLineCurrentUASs OBJECT-TYPE
    SYNTAX  Gauge
    ACCESS  read-only
    STATUS  mandatory
    DESCRIPTION
           "The counter associated with the number of
            Unavailable Seconds
            encountered by a SONET/SDH Line in the current 15
            minute
            interval."
    ::= { isarIsonetLineCurrentEntry  5 }

-- the SONET/SDH Line Interval Table

-- The SONET/SDH Line Interval Table
-- contains various statistics
-- collected by each system over a maximum
-- of the previous 24 hours of
-- operation.  The past 24 hours may be broken into 96
-- completed 15 minute intervals.
-- A system is required to store at
-- least 4 completed 15 minute interval.
-- The default value is 32 intervals.
-- IAD4700 : the maximum value of n will be used.

isarIsonetLineIntervalTable OBJECT-TYPE
    SYNTAX  SEQUENCE OF IsarIsonetLineIntervalEntry
    ACCESS  not-accessible
    STATUS  mandatory
    DESCRIPTION
           "The SONET/SDH Line Interval table."
    ::= { isarIsonetLine  2 }

isarIsonetLineIntervalEntry OBJECT-TYPE
    SYNTAX  IsarIsonetLineIntervalEntry
    ACCESS  not-accessible
    STATUS  mandatory
    DESCRIPTION
           "An entry in the SONET/SDH Line Interval table."
    INDEX   { ifIndex,  isarIsonetLineIntervalNumber }
    ::= { isarIsonetLineIntervalTable  1 }

IsarIsonetLineIntervalEntry ::=
    SEQUENCE {
      isarIsonetLineIntervalNumber
        INTEGER,

      isarIsonetLineIntervalESs
        Gauge,

      isarIsonetLineIntervalSESs
        Gauge,

      isarIsonetLineIntervalCVs
        Gauge,

      isarIsonetLineIntervalUASs
        Gauge,

      isarIsonetLineIntervalTimeStamp
        TimeTicks
    }

isarIsonetLineIntervalNumber OBJECT-TYPE
    SYNTAX  INTEGER (1..96)
    ACCESS  not-accessible
    STATUS  mandatory
    DESCRIPTION
           "A number between 1 and 96, which identifies the
            interval for which the set of statistics is available.
            The interval identified by 1 is the most recently
            completed 15 minute interval,
            and the interval identified
            by N is the interval immediately preceding the
            one identified
            by N-1.
            IAD4700 : the maximum value of n will be used."
    ::= { isarIsonetLineIntervalEntry  1 }

isarIsonetLineIntervalESs OBJECT-TYPE
    SYNTAX  Gauge
    ACCESS  read-only
    STATUS  mandatory
    DESCRIPTION
           "The counter associated with the number of
            Errored Seconds encountered
            by a SONET/SDH Line in a
            particular 15-minute interval
            in the past 24 hours."
    ::= { isarIsonetLineIntervalEntry  2 }

isarIsonetLineIntervalSESs OBJECT-TYPE
    SYNTAX  Gauge
    ACCESS  read-only
    STATUS  mandatory
    DESCRIPTION
           "The counter associated with the number of
            Severely Errored Seconds
            encountered by a SONET/SDH Line in a
            particular 15-minute interval
            in the past 24 hours."
    ::= { isarIsonetLineIntervalEntry  3 }

isarIsonetLineIntervalCVs OBJECT-TYPE
    SYNTAX  Gauge
    ACCESS  read-only
    STATUS  mandatory
    DESCRIPTION
           "The counter associated with the number of Coding
            Violations encountered by a
            SONET/SDH Line in a
            particular 15-minute interval
            in the past 24 hours."
    ::= { isarIsonetLineIntervalEntry  4 }

isarIsonetLineIntervalUASs OBJECT-TYPE
    SYNTAX  Gauge
    ACCESS  read-only
    STATUS  mandatory
    DESCRIPTION
           "The counter associated with the
            number of Unavailable Seconds
            encountered by a SONET/SDH Line in
            a particular 15-minute interval
            in the past 24 hours."
    ::= { isarIsonetLineIntervalEntry  5 }

isarIsonetLineIntervalTimeStamp OBJECT-TYPE
    SYNTAX  TimeTicks
    ACCESS  read-only
    STATUS  mandatory
    DESCRIPTION
           "Start of interval."
    ::= { isarIsonetLineIntervalEntry  6 }


-- The SONET/SDH Far End Line group.
-- This group may only be implemented by SONET/SDH (LTEs)
-- systems that provide for a far end block error (FEBE)
-- information at the SONET/SDH Line Layer.

-- This group consists of two tables:
--    SONET/SDH Far End Line Current Table
--    SONET/SDH Far End Line Interval Table



-- The SONET/SDH Far End Line Current Table

-- The SONET/SDH Far End Line Current table contains
-- various statistics being
-- collected for the current 15 minute interval.
-- The statistics are collected from the far end
-- block error code (FEBE)
-- within the third Z2 byte of the Line Overhead
-- in Broadband ISDN applications.
-- The definitions are the same as described for
-- the near-end information.

isarIsonetFarEndLineCurrentTable OBJECT-TYPE
    SYNTAX  SEQUENCE OF IsarIsonetFarEndLineCurrentEntry
    ACCESS  not-accessible
    STATUS  mandatory
    DESCRIPTION
           "The SONET/SDH Far End Line Current table."
    ::= { isarIsonetFarEndLine  1 }

isarIsonetFarEndLineCurrentEntry OBJECT-TYPE
    SYNTAX  IsarIsonetFarEndLineCurrentEntry
    ACCESS  not-accessible
    STATUS  mandatory
    DESCRIPTION
           "An entry in the SONET/SDH Far End Line Current table."
    INDEX   { ifIndex }
    ::= { isarIsonetFarEndLineCurrentTable  1 }

IsarIsonetFarEndLineCurrentEntry ::=
    SEQUENCE {
      isarIsonetFarEndLineCurrentESs
        Gauge,

      isarIsonetFarEndLineCurrentSESs
        Gauge,

      isarIsonetFarEndLineCurrentCVs
        Gauge,

      isarIsonetFarEndLineCurrentUASs
        Gauge
    }

isarIsonetFarEndLineCurrentESs OBJECT-TYPE
    SYNTAX  Gauge
    ACCESS  read-only
    STATUS  mandatory
    DESCRIPTION
           "The counter associated with the number of Far
            Far End Errored Seconds encountered by a SONET/SDH
            interface in the current 15 minute interval."
    ::= { isarIsonetFarEndLineCurrentEntry  1 }

isarIsonetFarEndLineCurrentSESs OBJECT-TYPE
    SYNTAX  Gauge
    ACCESS  read-only
    STATUS  mandatory
    DESCRIPTION
           "The counter associated with the number of
            Far End Severely Errored Seconds
            encountered by a SONET/SDH Medium/Section/Line
            interface in the current 15 minute
            interval."
    ::= { isarIsonetFarEndLineCurrentEntry  2 }

isarIsonetFarEndLineCurrentCVs OBJECT-TYPE
    SYNTAX  Gauge
    ACCESS  read-only
    STATUS  mandatory
    DESCRIPTION
           "The counter associated with the number of
            Far End Coding Violations reported via
            the far end block error count
            encountered by a
            SONET/SDH Medium/Section/Line
            interface in the current 15 minute interval."
    ::= { isarIsonetFarEndLineCurrentEntry  3 }

isarIsonetFarEndLineCurrentUASs OBJECT-TYPE
    SYNTAX  Gauge
    ACCESS  read-only
    STATUS  mandatory
    DESCRIPTION
           "The counter associated with the number of
            Far End Unavailable Seconds
            encountered by a
            SONET/SDH Medium/Section/Line
            interface in the current 15 minute interval."
    ::= { isarIsonetFarEndLineCurrentEntry  4 }

-- The SONET/SDH Far End Line Interval Table

-- The SONET/SDH Far End Line Interval Table
-- contains various statistics
-- collected by each system over a maximum
-- of the previous 24 hours of
-- operation.  The past 24 hours may be broken into 96
-- completed 15 minute intervals.
-- A system is required to store at
-- least 4 completed 15 minute interval.
-- The default value is 32 intervals.
-- IAD4700 : the maximum value of n will be used.

isarIsonetFarEndLineIntervalTable OBJECT-TYPE
    SYNTAX  SEQUENCE OF IsarIsonetFarEndLineIntervalEntry
    ACCESS  not-accessible
    STATUS  mandatory
    DESCRIPTION
           "The SONET/SDH Far End Line Interval table."
    ::= { isarIsonetFarEndLine  2 }

isarIsonetFarEndLineIntervalEntry OBJECT-TYPE
    SYNTAX  IsarIsonetFarEndLineIntervalEntry
    ACCESS  not-accessible
    STATUS  mandatory
    DESCRIPTION
           "An entry in the SONET/SDH Far
               End Line Interval table."
    INDEX   { ifIndex,  isarIsonetFarEndLineIntervalNumber }
    ::= { isarIsonetFarEndLineIntervalTable  1 }

IsarIsonetFarEndLineIntervalEntry ::=
    SEQUENCE {
      isarIsonetFarEndLineIntervalNumber
        INTEGER,

      isarIsonetFarEndLineIntervalESs
        Gauge,

      isarIsonetFarEndLineIntervalSESs
        Gauge,

      isarIsonetFarEndLineIntervalCVs
        Gauge,

      isarIsonetFarEndLineIntervalUASs
        Gauge,

      isarIsonetFarEndLineIntervalTimeStamp
        TimeTicks
    }

isarIsonetFarEndLineIntervalNumber OBJECT-TYPE
    SYNTAX  INTEGER (1..96)
    ACCESS  not-accessible
    STATUS  mandatory
    DESCRIPTION
           "A number between 1 and 96, which identifies the
            interval for which the set of statistics is available.
            The interval identified by 1 is the most recently
            completed 15 minute interval,
            and the interval identified
            by N is the interval immediately preceding the
            one identified
            by N-1.
            IAD4700 : the maximum value of n will be used."
    ::= { isarIsonetFarEndLineIntervalEntry  1 }

isarIsonetFarEndLineIntervalESs OBJECT-TYPE
    SYNTAX  Gauge
    ACCESS  read-only
    STATUS  mandatory
    DESCRIPTION
           "The counter associated with the number of
            Far End Errored Seconds encountered
            by a SONET/SDH Line
            interface in a particular 15-minute interval
            in the past 24 hours."
    ::= { isarIsonetFarEndLineIntervalEntry  2 }

isarIsonetFarEndLineIntervalSESs OBJECT-TYPE
    SYNTAX  Gauge
    ACCESS  read-only
    STATUS  mandatory
    DESCRIPTION
           "The counter associated with the number of
            Far End Severely Errored Seconds
            encountered by a SONET/SDH Line
            interface in a particular 15-minute interval
            in the past 24 hours."
    ::= { isarIsonetFarEndLineIntervalEntry  3 }

isarIsonetFarEndLineIntervalCVs OBJECT-TYPE
    SYNTAX  Gauge
    ACCESS  read-only
    STATUS  mandatory
    DESCRIPTION
           "The counter associated with the number of
            Far End Coding Violations reported via
            the far end block error count
            encountered by a
            SONET/SDH Line
            interface in a particular 15-minute interval
            in the past 24 hours."
    ::= { isarIsonetFarEndLineIntervalEntry  4 }

isarIsonetFarEndLineIntervalUASs OBJECT-TYPE
    SYNTAX  Gauge
    ACCESS  read-only
    STATUS  mandatory
    DESCRIPTION
           "The counter associated with the number of
            Far End Unavailable Seconds
            encountered by a
            SONET/SDH Line
            interface in a particular 15-minute interval
            in the past 24 hours."
    ::= { isarIsonetFarEndLineIntervalEntry  5 }

isarIsonetFarEndLineIntervalTimeStamp OBJECT-TYPE
    SYNTAX  TimeTicks
    ACCESS  read-only
    STATUS  mandatory
    DESCRIPTION
           "Start of interval."
    ::= { isarIsonetFarEndLineIntervalEntry  6 }


-- the SONET/SDH Path group

-- this group consists of 2 tables:
-- - the SONET/SDH Path Current Table
-- - the SONET/SDH Path Interval Table


-- the SONET/SDH Path Current Table

-- The SONET/SDH Path
-- current table contains various statistics
-- being collected for the current 15 minute interval.

isarIsonetPathCurrentTable OBJECT-TYPE
    SYNTAX  SEQUENCE OF IsarIsonetPathCurrentEntry
    ACCESS  not-accessible
    STATUS  mandatory
    DESCRIPTION
           "The SONET/SDH Path Current table."
    ::= { isarIsonetPath  1 }

isarIsonetPathCurrentEntry OBJECT-TYPE
    SYNTAX  IsarIsonetPathCurrentEntry
    ACCESS  not-accessible
    STATUS  mandatory
    DESCRIPTION
           "An entry in the SONET/SDH Path Current table."
    INDEX   { ifIndex }
    ::= { isarIsonetPathCurrentTable  1 }

IsarIsonetPathCurrentEntry ::=
    SEQUENCE {
      isarIsonetPathCurrentWidth
        INTEGER,

      isarIsonetPathCurrentStatus
        INTEGER,

      isarIsonetPathCurrentESs
        Gauge,

      isarIsonetPathCurrentSESs
        Gauge,

      isarIsonetPathCurrentCVs
        Gauge,

      isarIsonetPathCurrentUASs
        Gauge
    }

isarIsonetPathCurrentWidth OBJECT-TYPE
    SYNTAX  INTEGER {
                      sts3cSTM1(2)
            }
    ACCESS  read-write
    STATUS  mandatory
    DESCRIPTION
           "A value that indicates the type of the SONET/SDH
            Path.  For SONET, the assigned types are
            the STS-Nc SPEs, where N = 1, 3, 12, 24, and 48.
            STS-1 is equal to 51.84 Mbps.  For SDH, the assigned
            types are the STM-Nc VCs, where N = 1, 4, and 16.
            IAD4700 : only sts3cSTM is possible."
    ::= { isarIsonetPathCurrentEntry  1 }

isarIsonetPathCurrentStatus OBJECT-TYPE
    SYNTAX  INTEGER (1..62)
    ACCESS  read-only
    STATUS  mandatory
    DESCRIPTION
           "This variable indicates the
            status of the interface.
            The isarIsonetPathCurrentStatus
            is a bit map represented
            as a sum, therefore,
            it can represent multiple defects
            simultaneously.
            The sonetPathNoDefect should be
            set if and only if
            no other flag is set.

            The various bit positions are:
              1   sonetPathNoDefect
              2   sonetPathSTSLOP
              4   sonetPathSTSAIS
              8   sonetPathSTSRDI
             16   sonetPathUnequipped
             32   sonetPathSignalLabelMismatch"
    ::= { isarIsonetPathCurrentEntry  2 }

isarIsonetPathCurrentESs OBJECT-TYPE
    SYNTAX  Gauge
    ACCESS  read-only
    STATUS  mandatory
    DESCRIPTION
           "The counter associated with the number of Errored
            Seconds encountered by a SONET/SDH
            Path in the current 15 minute interval."
    ::= { isarIsonetPathCurrentEntry  3 }

isarIsonetPathCurrentSESs OBJECT-TYPE
    SYNTAX  Gauge
    ACCESS  read-only
    STATUS  mandatory
    DESCRIPTION
           "The counter associated with the number of
            Severely Errored Seconds
            encountered by a SONET/SDH Path in the current 15
            minute
            interval."
    ::= { isarIsonetPathCurrentEntry  4 }

isarIsonetPathCurrentCVs OBJECT-TYPE
    SYNTAX  Gauge
    ACCESS  read-only
    STATUS  mandatory
    DESCRIPTION
           "The counter associated with the number of Coding
            Violations encountered by a
            SONET/SDH Path in the current 15 minute interval."
    ::= { isarIsonetPathCurrentEntry  5 }

isarIsonetPathCurrentUASs OBJECT-TYPE
    SYNTAX  Gauge
    ACCESS  read-only
    STATUS  mandatory
    DESCRIPTION
           "The counter associated with the number of
            Unavailable Seconds
            encountered by a Path in the current
            15 minute, interval."
    ::= { isarIsonetPathCurrentEntry  6 }


-- the SONET/SDH Path Interval Table

-- The SONET/SDH Path Interval Table
-- contains various statistics
-- collected by each system over a maximum
-- of the previous 24 hours of
-- operation.  The past 24 hours may be broken into 96
-- completed 15 minute intervals.
-- A system is required to store at
-- least 4 completed 15 minute interval.
-- The default value is 32 intervals.
-- IAD4700 : the maximum value of n will be used.

isarIsonetPathIntervalTable OBJECT-TYPE
    SYNTAX  SEQUENCE OF IsarIsonetPathIntervalEntry
    ACCESS  not-accessible
    STATUS  mandatory
    DESCRIPTION
           "The SONET/SDH Path Interval table."
    ::= { isarIsonetPath  2 }

isarIsonetPathIntervalEntry OBJECT-TYPE
    SYNTAX  IsarIsonetPathIntervalEntry
    ACCESS  not-accessible
    STATUS  mandatory
    DESCRIPTION
           "An entry in the SONET/SDH Path Interval table."
    INDEX   { ifIndex,  isarIsonetPathIntervalNumber }
    ::= { isarIsonetPathIntervalTable  1 }

IsarIsonetPathIntervalEntry ::=
    SEQUENCE {
      isarIsonetPathIntervalNumber
        INTEGER,

      isarIsonetPathIntervalESs
        Gauge,

      isarIsonetPathIntervalSESs
        Gauge,

      isarIsonetPathIntervalCVs
        Gauge,

      isarIsonetPathIntervalUASs
        Gauge,

      isarIsonetPathIntervalTimeStamp
        TimeTicks
    }

isarIsonetPathIntervalNumber OBJECT-TYPE
    SYNTAX  INTEGER (1..96)
    ACCESS  not-accessible
    STATUS  mandatory
    DESCRIPTION
           "A number between 1 and 96, which identifies the
            interval for which the set of statistics is available.
            The interval identified by 1 is the most recently
            completed 15 minute interval,
            and the interval identified
            by N is the interval immediately preceding the
            one identified
            by N-1.
            IAD4700 : the maximum value of n will be used."
    ::= { isarIsonetPathIntervalEntry  1 }

isarIsonetPathIntervalESs OBJECT-TYPE
    SYNTAX  Gauge
    ACCESS  read-only
    STATUS  mandatory
    DESCRIPTION
           "The counter associated with the number of
            Errored Seconds encountered
            by a SONET/SDH Path in a
            particular 15-minute interval
            in the past 24 hours."
    ::= { isarIsonetPathIntervalEntry  2 }

isarIsonetPathIntervalSESs OBJECT-TYPE
    SYNTAX  Gauge
    ACCESS  read-only
    STATUS  mandatory
    DESCRIPTION
           "The counter associated with the number of
            Severely Errored Seconds
            encountered by a SONET/SDH Path in
            a particular 15-minute interval
            in the past 24 hours."
    ::= { isarIsonetPathIntervalEntry  3 }

isarIsonetPathIntervalCVs OBJECT-TYPE
    SYNTAX  Gauge
    ACCESS  read-only
    STATUS  mandatory
    DESCRIPTION
           "The counter associated with the number of Coding
            Violations encountered by a
            SONET/SDH Path in a particular 15-minute interval
            in the past 24 hours."
    ::= { isarIsonetPathIntervalEntry  4 }

isarIsonetPathIntervalUASs OBJECT-TYPE
    SYNTAX  Gauge
    ACCESS  read-only
    STATUS  mandatory
    DESCRIPTION
           "The counter associated with the number of
            Unavailable Seconds
            encountered by a Path in a
            particular 15-minute interval
            in the past 24 hours."
    ::= { isarIsonetPathIntervalEntry  5 }

isarIsonetPathIntervalTimeStamp OBJECT-TYPE
    SYNTAX  TimeTicks
    ACCESS  read-only
    STATUS  mandatory
    DESCRIPTION
           "Start of interval."
    ::= { isarIsonetPathIntervalEntry  6 }


-- The SONET/SDH Far End Path group

-- This group consists of two tables:
--  - SONET/SDH Far End Path Current Table
--  - SONET/SDH Far End Path Interval Table

-- The SONET/SDH Far End Path Current Table

-- The SONET/SDH Far End Path Current table
-- contains various statistics
-- being collected for the current 15 minute interval.
-- The statistics are collected from
-- the far end block error code
-- (FEBE) within the G1 byte of the Path Overhead.
-- The definitions are the same as described for
-- the near-end information.

isarIsonetFarEndPathCurrentTable OBJECT-TYPE
    SYNTAX  SEQUENCE OF IsarIsonetFarEndPathCurrentEntry
    ACCESS  not-accessible
    STATUS  mandatory
    DESCRIPTION
           "The SONET/SDH Far End Path Current table."
    ::= { isarIsonetFarEndPath  1 }

isarIsonetFarEndPathCurrentEntry OBJECT-TYPE
    SYNTAX  IsarIsonetFarEndPathCurrentEntry
    ACCESS  not-accessible
    STATUS  mandatory
    DESCRIPTION
           "An entry in the SONET/SDH Far End Path Current table."
    INDEX   { ifIndex }
    ::= { isarIsonetFarEndPathCurrentTable  1 }

IsarIsonetFarEndPathCurrentEntry ::=
    SEQUENCE {
      isarIsonetFarEndPathCurrentESs
        Gauge,

      isarIsonetFarEndPathCurrentSESs
        Gauge,

      isarIsonetFarEndPathCurrentCVs
        Gauge,

      isarIsonetFarEndPathCurrentUASs
        Gauge
    }

isarIsonetFarEndPathCurrentESs OBJECT-TYPE
    SYNTAX  Gauge
    ACCESS  read-only
    STATUS  mandatory
    DESCRIPTION
           "The counter associated with the number of Far
            Far End Errored Seconds encountered by a SONET/SDH
            interface in the current 15 minute interval."
    ::= { isarIsonetFarEndPathCurrentEntry  1 }

isarIsonetFarEndPathCurrentSESs OBJECT-TYPE
    SYNTAX  Gauge
    ACCESS  read-only
    STATUS  mandatory
    DESCRIPTION
           "The counter associated with the number of
            Far End Severely Errored Seconds
            encountered by a SONET/SDH Path
            interface in the current 15 minute
            interval."
    ::= { isarIsonetFarEndPathCurrentEntry  2 }

isarIsonetFarEndPathCurrentCVs OBJECT-TYPE
    SYNTAX  Gauge
    ACCESS  read-only
    STATUS  mandatory
    DESCRIPTION
           "The counter associated with the number of
            Far End Coding Violations reported via
            the far end block error count
            encountered by a
            SONET/SDH Path interface in
            the current 15 minute interval."
    ::= { isarIsonetFarEndPathCurrentEntry  3 }

isarIsonetFarEndPathCurrentUASs OBJECT-TYPE
    SYNTAX  Gauge
    ACCESS  read-only
    STATUS  mandatory
    DESCRIPTION
           "The counter associated with the number of
            Far End Unavailable Seconds
            encountered by a
            SONET/SDH Path interface in
            the current 15 minute interval."
    ::= { isarIsonetFarEndPathCurrentEntry  4 }


-- The SONET/SDH Far End Path Interval Table

-- The SONET/SDH Far End Path Interval Table
-- contains various statistics
-- collected by each system over a maximum
-- of the previous 24 hours of
-- operation.  The past 24 hours may be broken into 96
-- completed 15 minute intervals.
-- A system is required to store at
-- least 4 completed 15 minute interval.
-- The default value is 32 intervals.
-- IAD4700 : the maximum value of n will be used.

isarIsonetFarEndPathIntervalTable OBJECT-TYPE
    SYNTAX  SEQUENCE OF IsarIsonetFarEndPathIntervalEntry
    ACCESS  not-accessible
    STATUS  mandatory
    DESCRIPTION
           "The SONET/SDH Far End Path Interval table."
    ::= { isarIsonetFarEndPath  2 }

isarIsonetFarEndPathIntervalEntry OBJECT-TYPE
    SYNTAX  IsarIsonetFarEndPathIntervalEntry
    ACCESS  not-accessible
    STATUS  mandatory
    DESCRIPTION
           "An entry in the SONET/SDH Far
            End Path Interval table."
    INDEX   { ifIndex,  isarIsonetFarEndPathIntervalNumber }
    ::= { isarIsonetFarEndPathIntervalTable  1 }

IsarIsonetFarEndPathIntervalEntry ::=
    SEQUENCE {
      isarIsonetFarEndPathIntervalNumber
        INTEGER,

      isarIsonetFarEndPathIntervalESs
        Gauge,

      isarIsonetFarEndPathIntervalSESs
        Gauge,

      isarIsonetFarEndPathIntervalCVs
        Gauge,

      isarIsonetFarEndPathIntervalUASs
        Gauge,

      isarIsonetFarEndPathIntervalTimeStamp
        TimeTicks
    }

isarIsonetFarEndPathIntervalNumber OBJECT-TYPE
    SYNTAX  INTEGER (1..96)
    ACCESS  not-accessible
    STATUS  mandatory
    DESCRIPTION
           "A number between 1 and 96, which identifies the
            interval for which the set of statistics is available.
            The interval identified by 1 is the most recently
            completed 15 minute interval,
            and the interval identified
            by N is the interval immediately preceding the
            one identified
            by N-1."
    ::= { isarIsonetFarEndPathIntervalEntry  1 }

isarIsonetFarEndPathIntervalESs OBJECT-TYPE
    SYNTAX  Gauge
    ACCESS  read-only
    STATUS  mandatory
    DESCRIPTION
           "The counter associated with the number of
            Far End Errored Seconds encountered
            by a SONET/SDH Path interface in a
            particular 15-minute interval
            in the past 24 hours."
    ::= { isarIsonetFarEndPathIntervalEntry  2 }

isarIsonetFarEndPathIntervalSESs OBJECT-TYPE
    SYNTAX  Gauge
    ACCESS  read-only
    STATUS  mandatory
    DESCRIPTION
           "The counter associated with the number of
            Far End Severely Errored Seconds
            encountered by a SONET/SDH Path interface
            in a particular 15-minute interval
            in the past 24 hours."
    ::= { isarIsonetFarEndPathIntervalEntry  3 }

isarIsonetFarEndPathIntervalCVs OBJECT-TYPE
    SYNTAX  Gauge
    ACCESS  read-only
    STATUS  mandatory
    DESCRIPTION
           "The counter associated with the number of
            Far End Coding Violations reported via
            the far end block error count
            encountered by a
            SONET/SDH Path interface
            in a particular 15-minute interval
            in the past 24 hours."
    ::= { isarIsonetFarEndPathIntervalEntry  4 }

isarIsonetFarEndPathIntervalUASs OBJECT-TYPE
    SYNTAX  Gauge
    ACCESS  read-only
    STATUS  mandatory
    DESCRIPTION
           "The counter associated with the number of
            Far End Unavailable Seconds
            encountered by a
            SONET/SDH Path interface in
            a particular 15-minute interval
            in the past 24 hours."
    ::= { isarIsonetFarEndPathIntervalEntry  5 }

isarIsonetFarEndPathIntervalTimeStamp OBJECT-TYPE
    SYNTAX  TimeTicks
    ACCESS  read-only
    STATUS  mandatory
    DESCRIPTION
           "Start of interval."
    ::= { isarIsonetFarEndPathIntervalEntry  6 }


-- The SONET/SDH ATM group

-- This group consists of two tables:
--  - SONET/SDH ATM Current Table
--  - SONET/SDH ATM Interval Table

-- The SONET/SDH ATM Current Table

-- The SONET/SDH ATM Current table
-- contains various statistics
-- being collected for the current 15 minute interval.
-- The statistics are collected from
-- the ATM side.

isarIsonetAtmCurrentTable OBJECT-TYPE
    SYNTAX  SEQUENCE OF IsarIsonetAtmCurrentEntry
    ACCESS  not-accessible
    STATUS  mandatory
    DESCRIPTION
           "The SONET/SDH Atm Current table."
    ::= { isarIsonetAtm  1 }

isarIsonetAtmCurrentEntry OBJECT-TYPE
    SYNTAX  IsarIsonetAtmCurrentEntry
    ACCESS  not-accessible
    STATUS  mandatory
    DESCRIPTION
           "An entry in the SONET/SDH Atm Current table."
    INDEX   { ifIndex }
    ::= { isarIsonetAtmCurrentTable  1 }

IsarIsonetAtmCurrentEntry ::=
    SEQUENCE {
      isarIsonetAtmCurrentStatus
        INTEGER,

      isarIsonetAtmCurrentUncorrectableHeaderErrors
        Gauge,

      isarIsonetAtmCurrentCorrectableHeaderErrors
        Gauge,

      isarIsonetAtmCurrentReceivedCells
        Gauge,

      isarIsonetAtmCurrentTransmittedCells
        Gauge
    }

isarIsonetAtmCurrentStatus OBJECT-TYPE
    SYNTAX  INTEGER (1..1022)
    ACCESS  read-only
    STATUS  mandatory
    DESCRIPTION
           "This variable indicates the
            status of the interface.
            The isarIsonetAtmCurrentStatus
            is a bit map represented
            as a sum, therefore,
            it can represent multiple defects
            simultaneously.
            The sonetPathNoDefect should be
            set if and only if
            no other flag is set.

            The various bit positions are:
              1   sonetAtmNoDefect
              2   sonetAtmRxOCD
              4   sonetAtmRxLCD
              8   sonetAtmRxFOVR
             16   sonetAtmTxFOVR
             32   sonetAtmRROOL
             64   sonetAtmRDOOL
            128   sonetAtmTROOL
            256   sonetLaserRXSD
            512   sonetLaserAlarm"
    ::= { isarIsonetAtmCurrentEntry  1 }

isarIsonetAtmCurrentUncorrectableHeaderErrors OBJECT-TYPE
    SYNTAX  Gauge
    ACCESS  read-only
    STATUS  mandatory
    DESCRIPTION
           "The counter associated with the number of
            ATM Uncorrectable Header Errors
            encountered by a SONET/SDH Path
            interface in the current 15 minute
            interval."
    ::= { isarIsonetAtmCurrentEntry  2 }

isarIsonetAtmCurrentCorrectableHeaderErrors OBJECT-TYPE
    SYNTAX  Gauge
    ACCESS  read-only
    STATUS  mandatory
    DESCRIPTION
           "The counter associated with the number of
            correctable Header Errors
            encountered by a
            SONET/SDH Path interface in
            the current 15 minute interval."
    ::= { isarIsonetAtmCurrentEntry  3 }

isarIsonetAtmCurrentReceivedCells OBJECT-TYPE
    SYNTAX  Gauge
    ACCESS  read-only
    STATUS  mandatory
    DESCRIPTION
           "The counter associated with the number of
            received cells
            encountered by a
            SONET/SDH Path interface in
            the current 15 minute interval."
    ::= { isarIsonetAtmCurrentEntry  4 }

isarIsonetAtmCurrentTransmittedCells OBJECT-TYPE
    SYNTAX  Gauge
    ACCESS  read-only
    STATUS  mandatory
    DESCRIPTION
           "The counter associated with the number of
            transmitted cells
            encountered by a
            SONET/SDH Path interface in
            the current 15 minute interval."
    ::= { isarIsonetAtmCurrentEntry  5 }



-- The SONET/SDH ATM Interval Table

-- The SONET/SDH ATM Interval Table
-- contains various statistics
-- collected by each system over a maximum
-- of the previous 24 hours of
-- operation.  The past 24 hours may be broken into 96
-- completed 15 minute intervals.
-- A system is required to store at
-- least 4 completed 15 minute interval.
-- The default value is 32 intervals.
-- IAD4700 : the maximum value of n will be used.

isarIsonetAtmIntervalTable OBJECT-TYPE
    SYNTAX  SEQUENCE OF IsarIsonetAtmIntervalEntry
    ACCESS  not-accessible
    STATUS  mandatory
    DESCRIPTION
           "The SONET/SDH Atm Interval table."
    ::= { isarIsonetAtm  2 }

isarIsonetAtmIntervalEntry OBJECT-TYPE
    SYNTAX  IsarIsonetAtmIntervalEntry
    ACCESS  not-accessible
    STATUS  mandatory
    DESCRIPTION
           "An entry in the SONET/SDH Atm Interval table."
    INDEX   { ifIndex,  isarIsonetAtmIntervalNumber }
    ::= { isarIsonetAtmIntervalTable  1 }

IsarIsonetAtmIntervalEntry ::=
    SEQUENCE {
      isarIsonetAtmIntervalNumber
        INTEGER,

      isarIsonetAtmIntervalUncorrectableHeaderErrors
        Gauge,

      isarIsonetAtmIntervalCorrectableHeaderErrors
        Gauge,

      isarIsonetAtmIntervalReceivedCells
        Gauge,

      isarIsonetAtmIntervalTransmittedCells
        Gauge,

      isarIsonetAtmIntervalTimeStamp
        TimeTicks
    }

isarIsonetAtmIntervalNumber OBJECT-TYPE
    SYNTAX  INTEGER (1..96)
    ACCESS  not-accessible
    STATUS  mandatory
    DESCRIPTION
           "A number between 1 and 96, which identifies the
            interval for which the set of statistics is available.
            The interval identified by 1 is the most recently
            completed 15 minute interval,
            and the interval identified
            by N is the interval immediately preceding the
            one identified
            by N-1."
    ::= { isarIsonetAtmIntervalEntry  1 }

isarIsonetAtmIntervalUncorrectableHeaderErrors OBJECT-TYPE
    SYNTAX  Gauge
    ACCESS  read-only
    STATUS  mandatory
    DESCRIPTION
           "The counter associated with the number of
            UncorrectableHeaderErrors encountered
            by a SONET/SDH Path interface in a
            particular 15-minute interval
            in the past 24 hours."
    ::= { isarIsonetAtmIntervalEntry  2 }

isarIsonetAtmIntervalCorrectableHeaderErrors OBJECT-TYPE
    SYNTAX  Gauge
    ACCESS  read-only
    STATUS  mandatory
    DESCRIPTION
           "The counter associated with the number of
            CorrectableHeaderErrors Seconds
            encountered by a SONET/SDH Path interface
            in a particular 15-minute interval
            in the past 24 hours."
    ::= { isarIsonetAtmIntervalEntry  3 }

isarIsonetAtmIntervalReceivedCells OBJECT-TYPE
    SYNTAX  Gauge
    ACCESS  read-only
    STATUS  mandatory
    DESCRIPTION
           "The counter associated with the number of
            received cells
            encountered by a SONET/SDH Path interface
            in a particular 15-minute interval
            in the past 24 hours."
    ::= { isarIsonetAtmIntervalEntry  4 }

isarIsonetAtmIntervalTransmittedCells OBJECT-TYPE
    SYNTAX  Gauge
    ACCESS  read-only
    STATUS  mandatory
    DESCRIPTION
           "The counter associated with the number of
            transmitted cells
            encountered by a SONET/SDH Path interface
            in a particular 15-minute interval
            in the past 24 hours."
    ::= { isarIsonetAtmIntervalEntry  5 }

isarIsonetAtmIntervalTimeStamp OBJECT-TYPE
    SYNTAX  TimeTicks
    ACCESS  read-only
    STATUS  mandatory
    DESCRIPTION
           "Start of interval."
    ::= { isarIsonetAtmIntervalEntry  6 }



-- thresholds table for stm1 performance counters

isarIstm1ThresholdTable OBJECT-TYPE
    SYNTAX  SEQUENCE OF IsarIstm1ThresholdEntry
    ACCESS  not-accessible
    STATUS  mandatory
    DESCRIPTION
           "The SONET/SDH threshold table."
    ::= { isarIsonetThresholds  1 }

isarIstm1ThresholdEntry OBJECT-TYPE
    SYNTAX  IsarIstm1ThresholdEntry
    ACCESS  not-accessible
    STATUS  mandatory
    DESCRIPTION
           "An entry in the SONET/SDH threshold table."
    INDEX   { ifIndex }
    ::= { isarIstm1ThresholdTable  1 }

IsarIstm1ThresholdEntry ::=
    SEQUENCE {
      isarIstm1SectionThrshld
        INTEGER,

      isarIstm1LineThrshld
        INTEGER,

      isarIstm1FarEndLineThrshld
        INTEGER,

      isarIstm1PathThrshld
        INTEGER,

      isarIstm1FarEndPathThrshld
        INTEGER
    }


isarIstm1SectionThrshld OBJECT-TYPE
    SYNTAX  INTEGER (1..7500)
    ACCESS  read-write
    STATUS  mandatory
    DESCRIPTION
           "Threshold for Section anomaly values CV, ES, SES, SEFS.
            RSOP # of BIP-8.
            Default = 2400."
    DEFVAL { 2400 }
    ::= { isarIstm1ThresholdEntry  1 }

isarIstm1LineThrshld OBJECT-TYPE
    SYNTAX  INTEGER (1..7500)
    ACCESS  read-write
    STATUS  mandatory
    DESCRIPTION
           "Threshold for Line anomaly values CV, ES, UAS.
            RLOP # of BIP-8-24.
            Default = 2400."
    DEFVAL { 2400 }
    ::= { isarIstm1ThresholdEntry  2 }

isarIstm1FarEndLineThrshld OBJECT-TYPE
    SYNTAX  INTEGER (1..7500)
    ACCESS  read-write
    STATUS  mandatory
    DESCRIPTION
           "Threshold for Far End Line anomaly values CV, ES, UAS.
            RLOP # of FEBE.
            Default = 2400."
    DEFVAL { 2400 }
    ::= { isarIstm1ThresholdEntry  3 }

isarIstm1PathThrshld OBJECT-TYPE
    SYNTAX  INTEGER (1..7500)
    ACCESS  read-write
    STATUS  mandatory
    DESCRIPTION
           "Threshold for Path anomaly values CV, ES, UAS.
            RPOP # of BIP-8.
            Default = 2400."
    DEFVAL { 2400 }
    ::= { isarIstm1ThresholdEntry  4 }

isarIstm1FarEndPathThrshld OBJECT-TYPE
    SYNTAX  INTEGER (1..7500)
    ACCESS  read-write
    STATUS  mandatory
    DESCRIPTION
           "Threshold for Far End Path anomaly values CV, ES, UAS.
            RPOP # of FEBE.
            Default = 2400."
    DEFVAL { 2400 }
    ::= { isarIstm1ThresholdEntry  5 }




--
-- ISAR sonetMIBObjects : end
--  


-- This file cannot be used to create SNMP agent.
-- The file isarOneFile.my has to be used to create the agent.



-- isarIs0MIBObjects OBJECT IDENTIFIER ::= { isar  33 }

--
-- ISAR s0MIBObjects : begin
--  



isarIbriConfigGroup OBJECT IDENTIFIER ::= { isarIs0MIBObjects  1 }

isarIbriConfigTable OBJECT-TYPE
    SYNTAX  SEQUENCE OF IsarIbriConfigEntry
    ACCESS  not-accessible
    STATUS  mandatory
    DESCRIPTION
           "Table containing BRI specific fields and a number
            of S0Port settings (all ports on the DPM have the 
            same settings)
            Rows are created at startup of IAD4700."
    ::= { isarIbriConfigGroup  1 }

isarIbriConfigEntry OBJECT-TYPE
    SYNTAX  IsarIbriConfigEntry
    ACCESS  not-accessible
    STATUS  mandatory
    DESCRIPTION
           "An entry in the BRI config Table."
    INDEX   { isarIphysSlotId }
    ::= { isarIbriConfigTable  1 }

IsarIbriConfigEntry ::=
    SEQUENCE {

    isarIbriConfigNumberS0Ports
        INTEGER,

    isarIbriConfigS0Version
        OCTET STRING,

    isarIbriConfigIfType
        INTEGER,

    isarIbriConfigLineTopology
        INTEGER,

    isarIbriConfigIfMode
        INTEGER,

    isarIbriConfigSignalMode
        INTEGER,

    isarIbriConfigPowerSupplyAvailable
        INTEGER,

    isarIbriConfigClockReferenceSelect
        INTEGER,

    isarIbriConfigNumberPoweredLinesIAD
        INTEGER
    }

isarIbriConfigNumberS0Ports OBJECT-TYPE
    SYNTAX  INTEGER ( 4 | 8 )
    ACCESS  read-only
    STATUS  mandatory
    DESCRIPTION
           "Shows the number of equipped S0 ports for this
            type of DPM:BRI."
    ::= { isarIbriConfigEntry  1 }

isarIbriConfigS0Version OBJECT-TYPE
    SYNTAX  OCTET STRING
    ACCESS  read-only
    STATUS  mandatory
    DESCRIPTION
           "The HW version of the S0 port components equipped on
            this type of DPM:BRI (all S0 ports have the same type
            of HW component)."
    ::= { isarIbriConfigEntry  2 }

isarIbriConfigIfType OBJECT-TYPE
    SYNTAX  INTEGER {
                      isdns(75),
                      isdnu(76)
            }
    ACCESS  read-only
    STATUS  mandatory
    DESCRIPTION
           "The physical interface type. For 'S/T' interfaces,
            also called 'Four-wire Basic Access Interface',
            the value of this object is isdns(75).
            For 'U' interfaces, also called 'Two-wire Basic
            Access Interface', the value of this object is
            isdnu(76).
            IAD4700 is always active on the S/T interface. (There
            is no corresponding entry in the ifTable.)"
    DEFVAL { isdns }
    ::= { isarIbriConfigEntry  3 }

isarIbriConfigLineTopology OBJECT-TYPE
    SYNTAX  INTEGER {
                      pointToPoint(1),
                      pointToMultipoint(2)
            }
    ACCESS  read-only
    STATUS  mandatory
    DESCRIPTION
           "The line topology to be used for this interface.
            Note that setting isarIbriConfigIfType to isdns(75)
            does not necessarily mean a line topology of
            point-to-multipoint.
            For IAD4700 it is always point-to-point:
             1. in case connected to PBX -> p-t-p
             2. in case connected to TE : the IAD4700 is configured
                in nt mode -> p-t-p."
    DEFVAL { pointToPoint }
    ::= { isarIbriConfigEntry  4 }

isarIbriConfigIfMode OBJECT-TYPE
    SYNTAX  INTEGER {
                      te(1),
                      nt(2)
            }
    ACCESS  read-write
    STATUS  mandatory
    DESCRIPTION
           "The physical interface mode. For TE mode, the value
            of this object is te(1). For NT mode, the value
            of this object is nt(2)."
    DEFVAL { te }
    ::= { isarIbriConfigEntry  5 }

isarIbriConfigSignalMode OBJECT-TYPE
    SYNTAX  INTEGER {
                      active(1),
                      inactive(2)
            }
    ACCESS  read-only
    STATUS  mandatory
    DESCRIPTION
           "The signaling channel operational mode for this interface.
            If active(1) there is a signaling channel on this
            interface. If inactive(2) a signaling channel is
            not available.
            For IAD4700, the D channel is always present."
    DEFVAL { active }
    ::= { isarIbriConfigEntry  6 }

isarIbriConfigPowerSupplyAvailable OBJECT-TYPE
    SYNTAX  INTEGER {
                      true(1),
                      false(2)
            }
    ACCESS  read-only
    STATUS  mandatory
    DESCRIPTION
           "Indicates the current status of the Power Supply.
            false: power supply not connected to this DPM
            true: power supply connected to this DPM."
    DEFVAL { false }
    ::= { isarIbriConfigEntry  7 }

isarIbriConfigClockReferenceSelect OBJECT-TYPE
    SYNTAX  INTEGER (0..7)
    ACCESS  read-write
    STATUS  mandatory
    DESCRIPTION
           "If the IAD4700 clock is set to slave on this DPM:BRI (only
            meaningfull if isarIbriConfigIfMode equals 'te'), the clock
            of the indicated S0 channel is used as synchronisation clock."
    DEFVAL { 0 }
    ::= { isarIbriConfigEntry  8 }

isarIbriConfigNumberPoweredLinesIAD OBJECT-TYPE
    SYNTAX  INTEGER
    ACCESS  read-only
    STATUS  mandatory
    DESCRIPTION
           "Integer representing the number of lines for which 'line
            power' is enabled."
    DEFVAL { 0 }
    ::= { isarIbriConfigEntry  9 }




-- S0 configuration


isarIs0ConfigGroup OBJECT IDENTIFIER ::= { isarIs0MIBObjects  2 }

isarIs0ConfigTable OBJECT-TYPE
    SYNTAX  SEQUENCE OF IsarIs0ConfigEntry
    ACCESS  not-accessible
    STATUS  mandatory
    DESCRIPTION
           "Supports configuration parameters of one physical interface.
            Rows are created at startup of IAD4700."
    ::= { isarIs0ConfigGroup  1 }

isarIs0ConfigEntry OBJECT-TYPE
    SYNTAX  IsarIs0ConfigEntry
    ACCESS  not-accessible
    STATUS  mandatory
    DESCRIPTION
           "One row in isarIs0ConfigTable."
    INDEX   { ifIndex }
    ::= { isarIs0ConfigTable  1 }

IsarIs0ConfigEntry ::=
    SEQUENCE {
    isarIs0ConfigLoopMode
        INTEGER,

    isarIs0ConfigLineStatus
        INTEGER,

    isarIs0ConfigPowerSupplyStatus
        INTEGER,

    isarIs0ConfigLinePowering
        INTEGER,

    isarIs0ConfigServiceMode
        INTEGER
    }

isarIs0ConfigLoopMode OBJECT-TYPE
    SYNTAX  INTEGER {
                      noLoop(1),
                      iomAnalogLoop(3)
            }
    ACCESS  read-write
    STATUS  mandatory
    DESCRIPTION
           "This variable represents the desired loopback configuration of
            the S0 interface.  The values mean:
            noLoop : not in the loopback state.  A device that is not
                     capable of performing a loopback on the interface
                     shall allways return this as its value.
            iomAnalogLoop : The iomAnalogLoop will loop back the analog
                            output at the S/T interface to the analog input
                            at the S/T interface, so data is reflected 
                            towards the IOM-2 bus.  In other words, in LT-T
                            mode INFO3 is returned, and in LT-S mode INFO4
                            is returned to the analog input at the S/T
                            interface."
    DEFVAL { noLoop }
    ::= { isarIs0ConfigEntry  1 }

isarIs0ConfigLineStatus OBJECT-TYPE
    SYNTAX  INTEGER {
                      other(1),
                      f3PendingDeactivation(2),
                      f4PendingActivation(3),
                      f5Unsynchronized(4),
                      f6Synchronized(5),
                      f7Activated(6),
                      f8LostFraming(7),
                      g1Deactivated(8),
                      g2Synchronized(9),
                      g3Activated(10),
                      g4PendingDeactivated(11),
                      f0Deactivated(12)
            }
    ACCESS  read-only
    STATUS  mandatory
    DESCRIPTION
           "Line status of this interface."
    ::= { isarIs0ConfigEntry  2 }

isarIs0ConfigPowerSupplyStatus OBJECT-TYPE
    SYNTAX  INTEGER {
                      disabled(1),
                      operational(2),
                      overloaded(3)
            }
    ACCESS  read-only
    STATUS  mandatory
    DESCRIPTION
           "Indicates the current status of the power supply.
            disabled and overloaded: no line powering possible (problems 
                                     with the power supply)
            operational: line powering is possible."
    ::= { isarIs0ConfigEntry  3 }

isarIs0ConfigLinePowering OBJECT-TYPE
    SYNTAX  INTEGER {
                      enabled(1),
                      disabled(2)
            }
    ACCESS  read-write
    STATUS  mandatory
    DESCRIPTION
           "Indicates if 'line powering' for this interface is to be
            enabled/disabled.
            A maximum of 16 S0 interfaces can be line powered in 
            the IAD4700.
            This configuration is only meaningful if the port is 
            configured in 'nt' mode."
    DEFVAL { disabled }
    ::= { isarIs0ConfigEntry  4 }

isarIs0ConfigServiceMode OBJECT-TYPE
    SYNTAX  INTEGER {
                      normalMode(1),
                      transparentMode(2),
                      undefined(3)
            }
    ACCESS  read-only
    STATUS  mandatory
    DESCRIPTION
           "IAD4700 DPM:BRI can be applied in 2 different configurations:
            1. normal mode - as an emulated leased line interface
            2. transparent mode - remote S0 devices
            3. undefined - no service mode specified"
    DEFVAL { undefined }
    ::= { isarIs0ConfigEntry  5 }





-- TRAP

isarIbriTraps OBJECT IDENTIFIER ::= { isarIs0MIBObjects  3 }

isarIbriPowerSupplyDown TRAP-TYPE
    ENTERPRISE  isarIbriTraps
    VARIABLES   { isarIphysSlotId }
    DESCRIPTION
           "Power supply is down.
            isarIphysSlotId indicates on which BRI module the error
            occured."
    ::= 1

isarIbriPowerSupplyUp TRAP-TYPE
    ENTERPRISE  isarIbriTraps
    VARIABLES   { isarIphysSlotId }
    DESCRIPTION
           "Power supply is up.
            isarIphysSlotId indicates on which BRI module the error
            occured."
    ::= 2

isarIbriHwFault TRAP-TYPE
    ENTERPRISE  isarIbriTraps
    VARIABLES   { isarIphysSlotId }
    DESCRIPTION
           "The ISAC-S's don't have the correct version number."
    ::= 3

isarIbriMaxNumberPoweredLinesReached TRAP-TYPE
    ENTERPRISE  isarIbriTraps
    DESCRIPTION
           "The maximum number of powered lines is reached."
    ::= 4



--
-- ISAR atmMIBObjects : end
--  




-- This file cannot be used to create SNMP agent.
-- The file isarOneFile.my has to be used to create the agent.


-- isarIcccMIBObjects      OBJECT IDENTIFIER ::= { isar  34 }


--
-- ISAR cccMIBObjects : begin
--
-- enterprise MIB for ISAR
-- The MIB is written for SNMPv1.

--
-- ISAR Call and Connection Control
--


-- REMARK: the trace selectors are incorparated in the CCC MIB objects
--         and not in the tracing MIB objects because they want to use
--         tracing in a different way.  Output of the trace messages
--         will be done via the trace buffer.



-- GENERAL INFORMATION


-- General configuration objects
-- These objects are used to configure the generic items of the
-- Call and Connection Control subsystem.  It specifies the location of the
-- NE in case of RemoteS0, it specifies the number of voice compression
-- circuits which can be used for the dynamic trunking service.

isarIccGenConfObjects  OBJECT IDENTIFIER ::=  { isarIcccMIBObjects  1 }

isarIccGenConfS0Location OBJECT-TYPE
    SYNTAX  INTEGER {
                      device(1),
                      switch(2)
            }
    ACCESS  read-write
    STATUS  mandatory
    DESCRIPTION
           "Location of IAD4700 for the remote S0 service.
            It is not allowed to change this value when physical port 
            connections are existing.
            Default = device."
    ::= { isarIccGenConfObjects  1 }

isarIccGenConfNrVcs OBJECT-TYPE
    SYNTAX  INTEGER (0..2147483647)
    ACCESS  read-write
    STATUS  mandatory
    DESCRIPTION
           "Number of voice compression circuits for CCC."
    ::= { isarIccGenConfObjects  2 }



-- ATM number objects
-- Objects for configuration of the ATM number of the NE.
-- IAD4700 ATM address is used for automatic configuration to report to
-- other IAD4700s the address the have to use to set up an ATM call.

isarIccGenAtmNumObjects  OBJECT IDENTIFIER ::=  { isarIcccMIBObjects  2 }

isarIccGenAtmNumPlan OBJECT-TYPE
    SYNTAX  INTEGER {
                      e164(1)
            }
    ACCESS  read-only
    STATUS  mandatory
    DESCRIPTION
           "IAD4700 ATM number plan."
    ::= { isarIccGenAtmNumObjects  1 }

isarIccGenAtmNumType OBJECT-TYPE
    SYNTAX  INTEGER {
                      internationalNo(1)
            }
    ACCESS  read-only
    STATUS  mandatory
    DESCRIPTION
           "IAD4700 ATM number type."
    ::= { isarIccGenAtmNumObjects  2 }

isarIccGenAtmNumValue OBJECT-TYPE
    SYNTAX  DisplayString
    ACCESS  read-write
    STATUS  mandatory
    DESCRIPTION
           "IAD4700 ATM number value.
            Default = empty string."
    ::= { isarIccGenAtmNumObjects  3 }



-- Private network objects
-- Objects for configuration of the NE related information of a narrowband
-- (NB) private network.

isarIccGenPnObjects  OBJECT IDENTIFIER ::=  { isarIcccMIBObjects  3 }

isarIccGenPnId OBJECT-TYPE
    SYNTAX  INTEGER
    ACCESS  read-write
    STATUS  mandatory
    DESCRIPTION
           "Represents private network."
    ::= { isarIccGenPnObjects  1 }

isarIccGenPnPrefixInternational OBJECT-TYPE
    SYNTAX  DisplayString
    ACCESS  read-write
    STATUS  mandatory
    DESCRIPTION
           "International prefix digits."
    ::= { isarIccGenPnObjects  2 }

isarIccGenPnPrefixNational OBJECT-TYPE
    SYNTAX  DisplayString
    ACCESS  read-write
    STATUS  mandatory
    DESCRIPTION
           "National prefix digits."
    ::= { isarIccGenPnObjects  3 }

isarIccGenPnPrefixLevel1 OBJECT-TYPE
    SYNTAX  DisplayString
    ACCESS  read-write
    STATUS  mandatory
    DESCRIPTION
           "Level 1 prefix digits."
    ::= { isarIccGenPnObjects  4 }

isarIccGenPnPrefixLevel2 OBJECT-TYPE
    SYNTAX  DisplayString
    ACCESS  read-write
    STATUS  mandatory
    DESCRIPTION
           "Level 2 prefix digits."
    ::= { isarIccGenPnObjects  5 }



-- DSS2 channel objects
-- Objects for configuration of the DSS2 related information of this NE.

isarIccGenDss2Objects  OBJECT IDENTIFIER ::=  { isarIcccMIBObjects  4 }

isarIccGenDss2Vci OBJECT-TYPE
    SYNTAX  INTEGER (5)
    ACCESS  read-only
    STATUS  mandatory
    DESCRIPTION
           "VCI for DSS2 signalling channel (VPI = 0)."
    ::= { isarIccGenDss2Objects  1 }

isarIccGenDss2SscopPollTimer OBJECT-TYPE
    SYNTAX  INTEGER
    ACCESS  read-only
    STATUS  mandatory
    DESCRIPTION
           "SSCOP poll timer value for DSS2 channel.
            UNITS = msec.
            Default = 750 msec."
    ::= { isarIccGenDss2Objects  2 }

isarIccGenDss2SscopKeepAliveTimer OBJECT-TYPE
    SYNTAX  INTEGER
    ACCESS  read-only
    STATUS  mandatory
    DESCRIPTION
           "SSCOP keep alive timer value for DSS2 channel.
            UNITS = msec.
            Default = 2000 msec."
    ::= { isarIccGenDss2Objects  3 }

isarIccGenDss2SscopIdleTimer OBJECT-TYPE
    SYNTAX  INTEGER
    ACCESS  read-only
    STATUS  mandatory
    DESCRIPTION
           "SSCOP idle timer value for DSS2 channel.
            UNITS = msec.
            Default = 15000 msec."
    ::= { isarIccGenDss2Objects  4 }

isarIccGenDss2SscopNoResponseTimer OBJECT-TYPE
    SYNTAX  INTEGER
    ACCESS  read-only
    STATUS  mandatory
    DESCRIPTION
           "SSCOP no response timer value for DSS2 channel.
            UNITS = msec.
            Default = 7000 msec."
    ::= { isarIccGenDss2Objects  5 }

isarIccGenDss2SscopCcTimer OBJECT-TYPE
    SYNTAX  INTEGER
    ACCESS  read-only
    STATUS  mandatory
    DESCRIPTION
           "SSCOP connection control timer value for DSS2 channel.
            UNITS = msec.
            Default = 1000 msec."
    ::= { isarIccGenDss2Objects  6 }

isarIccGenDss2SscopMaxWindowSize OBJECT-TYPE
    SYNTAX  INTEGER
    ACCESS  read-only
    STATUS  mandatory
    DESCRIPTION
           "SSCOP maximum window size for DSS2 channel.
            UNITS = messages.
            Default = 8 messages."
    ::= { isarIccGenDss2Objects  7 }

isarIccGenDss2SscopMaxCc OBJECT-TYPE
    SYNTAX  INTEGER
    ACCESS  read-only
    STATUS  mandatory
    DESCRIPTION
           "SSCOP maximum retries value for DSS2 channel.
            Default = 4."
    ::= { isarIccGenDss2Objects  8 }

isarIccGenDss2SscopMaxPd OBJECT-TYPE
    SYNTAX  INTEGER
    ACCESS  read-only
    STATUS  mandatory
    DESCRIPTION
           "SSCOP maximum poll data value for DSS2 channel.
            Default = 25."
    ::= { isarIccGenDss2Objects  9 }

isarIccGenDss2SscopMaxStat OBJECT-TYPE
    SYNTAX  INTEGER
    ACCESS  read-only
    STATUS  mandatory
    DESCRIPTION
           "SSCOP maximum stat value for DSS2 channel.
            Default = 67."
    ::= { isarIccGenDss2Objects  10 }

isarIccGenDss2SscopPollAfterUstatRetransmit OBJECT-TYPE
    SYNTAX  INTEGER {
                      enabled(1),
                      disabled(2)
            }
    ACCESS  read-only
    STATUS  mandatory
    DESCRIPTION
           "SSCOP poll after retransmit enabled or disabled for DSS2 
            channel."
    ::= { isarIccGenDss2Objects  11 }

isarIccGenDss2SscopRepeatUstat OBJECT-TYPE
    SYNTAX  INTEGER {
                      enabled(1),
                      disabled(2)
            }
    ACCESS  read-only
    STATUS  mandatory
    DESCRIPTION
           "SSCOP repeat Ustat enabled or disabled for DSS2 channel."
    ::= { isarIccGenDss2Objects  12 }

isarIccGenDss2SscopResponseUstat OBJECT-TYPE
    SYNTAX  INTEGER {
                      enabled(1),
                      disabled(2)
            }
    ACCESS  read-only
    STATUS  mandatory
    DESCRIPTION
           "SSCOP response Ustat enabled or disabled for DSS2 channel."
    ::= { isarIccGenDss2Objects  13 }

isarIccGenDss2TraceLayer1 OBJECT-TYPE
    SYNTAX  INTEGER {
                      enabled(1),
                      disabled(2)
            }
    ACCESS  read-write
    STATUS  mandatory
    DESCRIPTION
           "Enable or disable tracing for layer 1 (store and forward 
            function for DSS2 signalling channel) protocol stack."
    ::= { isarIccGenDss2Objects  14 }

isarIccGenDss2TraceLayer2 OBJECT-TYPE
    SYNTAX  INTEGER {
                      enabled(1),
                      disabled(2)
            }
    ACCESS  read-write
    STATUS  mandatory
    DESCRIPTION
           "Enable or disable tracing for layer 2 (SAAL tracing for DSS2 
            signalling channel) protocol stack."
    ::= { isarIccGenDss2Objects  15 }

isarIccGenDss2TraceLayer3 OBJECT-TYPE
    SYNTAX  INTEGER {
                      enabled(1),
                      disabled(2)
            }
    ACCESS  read-write
    STATUS  mandatory
    DESCRIPTION
           "Enable or disable tracing for layer 3 (DSS2 signalling 
            channel) protocol stack."
    ::= { isarIccGenDss2Objects  16 }

isarIccGenDss2OperState OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "Operational state of the DSS2 signalling channel."
    ::= { isarIccGenDss2Objects  17 }

isarIccGenDss2AdminStatus OBJECT-TYPE
    SYNTAX  INTEGER {
                      up(1),
                      down(2)
            }
    ACCESS  read-write
    STATUS  mandatory
    DESCRIPTION
           "The desired adminstrative status of the broadband signalling 
            stack.
            Changing the status to 'up' causes an activation of the 
            broadband signalling stack.
            Changing the status to 'down' causes an deactivation of the 
            broadband signalling stack.  As a consequence all active SVC's
            will be released. No new SVC's can be setup.
            Default = down."
    ::= { isarIccGenDss2Objects  18 }



-- General tracing objects
-- Objects to enable/disable the tracing of the finite state machines,
-- the warnings and the notifications.

isarIccGenTraceObjects  OBJECT IDENTIFIER ::=  { isarIcccMIBObjects  5 }

isarIccGenTraceCcc OBJECT-TYPE
    SYNTAX  INTEGER {
                      enabled(1),
                      disabled(2)
            }
    ACCESS  read-write
    STATUS  mandatory
    DESCRIPTION
           "Enable or disable CCC tracing."
    ::= { isarIccGenTraceObjects  1 }

isarIccGenTraceCccFsm OBJECT-TYPE
    SYNTAX  INTEGER {
                      enabled(1),
                      disabled(2)
            }
    ACCESS  read-write
    STATUS  mandatory
    DESCRIPTION
           "Enable or disable CCC finite state machine tracing."
    ::= { isarIccGenTraceObjects  2 }

isarIccGenTraceCccWarning OBJECT-TYPE
    SYNTAX  INTEGER {
                      enabled(1),
                      disabled(2)
            }
    ACCESS  read-write
    STATUS  mandatory
    DESCRIPTION
           "Enable or disable CCC warning tracing.
            Warnings are messages which indicate a fault but which don't
            have an influence on the correct working of the IAD4700."
    ::= { isarIccGenTraceObjects  3 }

isarIccGenTraceCccNotification OBJECT-TYPE
    SYNTAX  INTEGER {
                      enabled(1),
                      disabled(2)
            }
    ACCESS  read-write
    STATUS  mandatory
    DESCRIPTION
           "Enable or disable CCC notification tracing.
            Notifications are messages that indicate a possible fault.  It 
            can't be defined who is responsible for this fault. E.g. a call
            is received and the IAD4700 can't define the remote node for 
            the received destination address."
    ::= { isarIccGenTraceObjects  4 }



-- Trace criterium table

isarIccGenTraceCriteriumDummy OBJECT-TYPE
    SYNTAX  INTEGER
    ACCESS  read-only
    STATUS  mandatory
    DESCRIPTION
           "Dummy object to protect the trace criterium next index from
            unnecessary increments."
    ::= { isarIccGenTraceObjects  7 }

isarIccTraceCriteriumNextObjects  OBJECT IDENTIFIER ::=  { isarIccGenTraceObjects  8 }

isarIccTraceCriteriumNextIndex OBJECT-TYPE
    SYNTAX  INTEGER (2..2147483647)
    ACCESS  read-only
    STATUS  mandatory
    DESCRIPTION
           "This object is used to assist the manager in
            selecting a value for isarIccTraceCriteriumIndex.  
            The manager has to GET this index before creating a row in 
            isarIccTraceCriteriumTable."
    ::= { isarIccTraceCriteriumNextObjects  1 }


isarIccTraceCriteriumTable OBJECT-TYPE
    SYNTAX  SEQUENCE OF IsarIccTraceCriteriumEntry
    ACCESS  not-accessible
    STATUS  mandatory
    DESCRIPTION
           "A trace criterium is used to activate tracing at a specific
            point in the software.
            Adding entries to this table will be on specific request of
            software developer."
    ::= { isarIccGenTraceObjects  6 }

isarIccTraceCriteriumEntry OBJECT-TYPE
    SYNTAX  IsarIccTraceCriteriumEntry
    ACCESS  not-accessible
    STATUS  mandatory
    DESCRIPTION
           "One row in the isarIccTraceCriteriumTable."
    INDEX   { isarIccTraceCriteriumIndex }
    ::= { isarIccTraceCriteriumTable  1 }


IsarIccTraceCriteriumEntry ::=
    SEQUENCE { 
      isarIccTraceCriteriumIndex
        INTEGER,
        
      isarIccTraceCriteriumRowStatus
        INTEGER,
        
      isarIccTraceCriteriumState
        INTEGER,
        
      isarIccTraceCriteriumIdentification
        DisplayString
        
    }


isarIccTraceCriteriumIndex OBJECT-TYPE
    SYNTAX  INTEGER (2..2147483647)
    ACCESS  read-only
    STATUS  mandatory
    DESCRIPTION
           "Index, unique in the system, determined by the
            manager via isarIccTraceCriteriumNextIndex."
    ::= { isarIccTraceCriteriumEntry  1 }

isarIccTraceCriteriumRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIccTraceCriteriumEntry  2 }

isarIccTraceCriteriumState OBJECT-TYPE
    SYNTAX  INTEGER {
                      enabled(1),
                      disabled(2)
            }
    ACCESS  read-write
    STATUS  mandatory
    DESCRIPTION
           "Enable or disable tracing via trace identification."
    DEFVAL  { enabled }
    ::= { isarIccTraceCriteriumEntry  3 }

isarIccTraceCriteriumIdentification OBJECT-TYPE
    SYNTAX  DisplayString
    ACCESS  read-write
    STATUS  mandatory
    DESCRIPTION
           "Trace criterium identification string.

            Modification of this value is not allowed.
            The SNMPv2 MAX-ACCESS is read-(only-)create."
    DEFVAL  { "" }
    ::= { isarIccTraceCriteriumEntry  4 }



-- general statistics objects
-- These objects collect the statistics of the dynamic trunking on system
-- level.

isarIccGenStatsObjects  OBJECT IDENTIFIER ::=  { isarIcccMIBObjects  6 }

isarIccGenStatsDaCallAttempts OBJECT-TYPE
    SYNTAX  Counter
    ACCESS  read-only
    STATUS  mandatory
    DESCRIPTION
           "Number of drop to aggregate call attempts = the number of setup
            messages received from the PBX; with or without a B-channel."
    ::= { isarIccGenStatsObjects  2 }

isarIccGenStatsDaCallNormalClear OBJECT-TYPE
    SYNTAX  Counter
    ACCESS  read-only
    STATUS  mandatory
    DESCRIPTION
           "Number of drop to aggregate normal cleared calls.  Normal call
            clearing = call termination or busy."
    ::= { isarIccGenStatsObjects  3 }

isarIccGenStatsDaCallEstablished OBJECT-TYPE
    SYNTAX  Counter
    ACCESS  read-only
    STATUS  mandatory
    DESCRIPTION
           "Number of drop to aggregate established calls = all the call
            attempts from the drop side to the aggregate side for which 
            a connect message is received; with or without a B-channel."
    ::= { isarIccGenStatsObjects  4 }

isarIccGenStatsDaUserError OBJECT-TYPE
    SYNTAX  Counter
    ACCESS  read-only
    STATUS  mandatory
    DESCRIPTION
           "Number of drop to aggregate user errors.  User error = any
            action by the user who initiated the call and which is the
            reason that the call can't be terminated.  E.g. invalid 
            destination address number."
    ::= { isarIccGenStatsObjects  5 }

isarIccGenStatsAdCallAttempts OBJECT-TYPE
    SYNTAX  Counter
    ACCESS  read-only
    STATUS  mandatory
    DESCRIPTION
           "Number of aggregate to drop call attempts."
    ::= { isarIccGenStatsObjects  6 }

isarIccGenStatsAdCallNormalClear OBJECT-TYPE
    SYNTAX  Counter
    ACCESS  read-only
    STATUS  mandatory
    DESCRIPTION
           "Number of aggregate to drop normal cleared calls.  Normal call
            clearing = call termination or busy."
    ::= { isarIccGenStatsObjects  7 }

isarIccGenStatsAdCallEstablished OBJECT-TYPE
    SYNTAX  Counter
    ACCESS  read-only
    STATUS  mandatory
    DESCRIPTION
           "Number of aggregate to drop established calls."
    ::= { isarIccGenStatsObjects  8 }

isarIccGenStatsCallVCOverflow OBJECT-TYPE
    SYNTAX  Counter
    ACCESS  read-only
    STATUS  mandatory
    DESCRIPTION
           "Number of voice compression overflow."
    ::= { isarIccGenStatsObjects  9 }

isarIccGenStatsCurrentUsedVcs OBJECT-TYPE
    SYNTAX  Gauge
    ACCESS  read-only
    STATUS  mandatory
    DESCRIPTION
           "Current number of used voice compression circuits."
    ::= { isarIccGenStatsObjects  10 }

isarIccGenStatsCallBBusy OBJECT-TYPE
    SYNTAX  Counter
    ACCESS  read-only
    STATUS  mandatory
    DESCRIPTION
           "Number of B-channels BUSY.  A B-channel busy means that a
            B-channel is needed but no idle B-channel on the drop side
            is found."
    ::= { isarIccGenStatsObjects  11 }




-- NARROWBAND LOGICAL PORT OBJECTS

isarIccNbLogPortObjects  OBJECT IDENTIFIER ::=  { isarIcccMIBObjects  7 }

isarIccNbLogPortDummy OBJECT-TYPE
    SYNTAX  INTEGER
    ACCESS  read-only
    STATUS  mandatory
    DESCRIPTION
           "Dummy object to protect the NB logical port next index from
            unnecessary increments."
    ::= { isarIccNbLogPortObjects  1 }

isarIccNbLogPortNextObjects  OBJECT IDENTIFIER ::=  { isarIccNbLogPortObjects  2 }

isarIccNbLogPortNextIndex OBJECT-TYPE
    SYNTAX  INTEGER (2..2147483647)
    ACCESS  read-only
    STATUS  mandatory
    DESCRIPTION
           "This object is used to assist the manager in
            selecting a value for isarIccNbLogPortIndex.  
            The manager has to GET this index before creating a row in 
            isarIccNbLogPortTable."
    ::= { isarIccNbLogPortNextObjects  1 }



-- NB logical port table

isarIccNbLogPortTable OBJECT-TYPE
    SYNTAX  SEQUENCE OF IsarIccNbLogPortEntry
    ACCESS  not-accessible
    STATUS  mandatory
    DESCRIPTION
           "A narrowband logical port represents a logical interface
            between the local NE and the local PABX.  It ca be aswell an
            S0-interface as a E1 interface.  It specifies which B-channels
            are used on its interface for the dynamic trunking service.

            It must be possible to dynamically add and delete entries.
            Addition (or deletion) of an entry will automatically add
            (or delete) a corresponding entry in the 
            isarIccNbLogPortStatsTable and isarIccNbLogPortLocNodeTable.
            
            A row can only be deleted when both admin and oper state are
            down."
    ::= { isarIccNbLogPortObjects  3 }

isarIccNbLogPortEntry OBJECT-TYPE
    SYNTAX  IsarIccNbLogPortEntry
    ACCESS  not-accessible
    STATUS  mandatory
    DESCRIPTION
           "One row in the isarIccNbLogPortTable."
    INDEX   { isarIccNbLogPortIndex }
    ::= { isarIccNbLogPortTable  1 }


IsarIccNbLogPortEntry ::=
    SEQUENCE { 
      isarIccNbLogPortIndex
        INTEGER,
        
      isarIccNbLogPortRowStatus
        INTEGER,
        
      isarIccNbLogPortLowerLayerIfIndex
        INTEGER,
        
      isarIccNbLogPortMap
        INTEGER,
        
      isarIccNbLogPortMapString
        OCTET STRING,
        
      isarIccNbLogPortAdminStatus
        INTEGER,
        
      isarIccNbLogPortShutdownMode
        INTEGER,
        
      isarIccNbLogPortOperStatus
        INTEGER,
        
      isarIccNbLogPortLocNodeIndex
        INTEGER,
        
      isarIccNbLogPortUserOrNetwork
        INTEGER,
        
      isarIccNbLogPortBChannelSelection
        INTEGER,
        
      isarIccNbLogPortLapDWindowSize
        INTEGER,
        
      isarIccNbLogPortLapDT200
        INTEGER,
        
      isarIccNbLogPortLapDN200
        INTEGER,
        
      isarIccNbLogPortLapDT203
        INTEGER,
        
      isarIccNbLogPortLapDN201
        INTEGER,
        
      isarIccNbLogPortTraceLayer1
        INTEGER,
        
      isarIccNbLogPortTraceLayer2
        INTEGER,

      isarIccNbLogPortTraceLayer3
        INTEGER
        
    }


isarIccNbLogPortIndex OBJECT-TYPE
    SYNTAX  INTEGER (2..2147483647)
    ACCESS  read-only
    STATUS  mandatory
    DESCRIPTION
           "Index, unique in the system, determined by the
            manager via isarIccNbLogPortNextIndex."
    ::= { isarIccNbLogPortEntry  1 }

isarIccNbLogPortRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIccNbLogPortEntry  2 }

isarIccNbLogPortLowerLayerIfIndex OBJECT-TYPE
    SYNTAX  INTEGER (1..2147483647)
    ACCESS  read-write
    STATUS  mandatory
    DESCRIPTION
           "The ifIndex value of the E1 or S0 port on which the NbLogPort
            is defined.  The value is determined by the SNMP manager.
            The operator is not allowed to change this value.
            The SNMPv2 MAX-ACCESS is read-(only-)create."
    ::= { isarIccNbLogPortEntry  3 }

isarIccNbLogPortMap OBJECT-TYPE
    SYNTAX  INTEGER
    ACCESS  read-write
    STATUS  mandatory
    DESCRIPTION
           "This is a bitmap that indicates which B-channels are used on
            the lower layer for the dynamic trunking service of Call and
            Connection Control.
            The field is defined as the sum of (2 to the power of 
            ChannelNumber) with ChannelNumber (0..31).
            It is not allowed to select the D-channel.  In case of QSIG and
            a E1 interface, the D-channel is always located at timeslot 16.
            In case of S0 (only 2 bits are allowed):
              B1 channel is the same as ChannelNumber 1 in case of E1
              B2 channel is the same as ChannelNumber 2 in case of E1
            
            REMARK : isarIccNbLogPortMap is not to be used by the 45020
            The agent will refuse a SET that contains a value for both
            isarIccNbLogPortMap and isarIccNbLogPortMapString.

            The SNMPv2 MAX-ACCESS is read-(only-)create."
    ::= { isarIccNbLogPortEntry  4 }

isarIccNbLogPortMapString OBJECT-TYPE
    SYNTAX  OCTET STRING (SIZE (4))
    ACCESS  read-write
    STATUS  mandatory
    DESCRIPTION
           "This OCTET STRING is for 45020 use only ! (However, the agent
            cannot prevent other management stations to use this object.)
            It contains the same information as isarIccNbLogPortMap.
            
            - isarIccNbLogPortMapString will be converted by the agent into
              isarIccNbLogPortMap at time of SET (of the string).
            - isarIccNbLogPortMap will be converted by the agent into
              isarIccNbLogPortMapString at time of GET (of the string).
              
            The agent will refuse a SET that contains a value for both
            isarIccNbLogPortMap and isarIccNbLogPortMapString.
            
            The SNMPv2 MAX-ACCESS is read-(only-)create."
    ::= { isarIccNbLogPortEntry  5 }

isarIccNbLogPortAdminStatus OBJECT-TYPE
    SYNTAX  INTEGER {
                      up(1),
                      down(2)
            }
    ACCESS  read-write
    STATUS  mandatory
    DESCRIPTION
           "The desired administrative status of the NbLogPort.
            
            The SNMPv2 MAX-ACCESS is read-create."
    ::= { isarIccNbLogPortEntry  6 }

isarIccNbLogPortShutdownMode OBJECT-TYPE
    SYNTAX  INTEGER {
                      forced(1),
                      notForced(2)
            }
    ACCESS  read-write
    STATUS  mandatory
    DESCRIPTION
           "The desired shutdown mode of the NbLogPort.
           
            forced: all active calls are released
            notForced: new calls are not accepted; existing calls stay
                       active till they are released according the normal
                       procedure
            
            The shutdown mode is linked with the admin status.
            If admin status = up: changing of this field has no effect.
            If admin status is changed from up to down: active calls will
                                     be released according to this field.
            If admin status = down: changing of this field from notForced
                                    to forced will cause the release of the
                                    active calls.  Changing from forced to
                                    notForced has no effect."
    DEFVAL  { notForced }
    ::= { isarIccNbLogPortEntry  7 }

isarIccNbLogPortOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "This object indicates the current operational status of the
            layer-3 protocol stack.  The status of the layer-3 protocol
            stack also reflects the status of the lower layers.
            The oper status = dormant as long as the peer-to-peer layer 3
            connection is still under construction.  If this construction
            fails, the oper status is set to lowerLayerDown."
    ::= { isarIccNbLogPortEntry  8 }

isarIccNbLogPortLocNodeIndex OBJECT-TYPE
    SYNTAX  INTEGER (2..2147483647)
    ACCESS  read-write
    STATUS  mandatory
    DESCRIPTION
           "Index to an entry in the isarIccLocNodeTable.
            
            Modification of this value is not allowed.
            The SNMPv2 MAX-ACCESS is read-(only-)create."
    ::= { isarIccNbLogPortEntry  9 }

isarIccNbLogPortUserOrNetwork OBJECT-TYPE
    SYNTAX  INTEGER {
                      user(1),
                      network(2)
            }
    ACCESS  read-write
    STATUS  mandatory
    DESCRIPTION
           "User or network flag.
            
            Modification of this value is not allowed.
            The SNMPv2 MAX-ACCESS is read-create."
    DEFVAL  { user }
    ::= { isarIccNbLogPortEntry  10 }

isarIccNbLogPortBChannelSelection OBJECT-TYPE
    SYNTAX  INTEGER {
                      bottomUp(1),
                      topDown(2)
            }
    ACCESS  read-write
    STATUS  mandatory
    DESCRIPTION
           "B Channel selection direction.
            
            Modification of this value is allowed even when the operational
            status is not down.
            The SNMPv2 MAX-ACCESS is read-create."
    DEFVAL  { bottomUp }
    ::= { isarIccNbLogPortEntry  11 }

isarIccNbLogPortLapDWindowSize OBJECT-TYPE
    SYNTAX  INTEGER
    ACCESS  read-only
    STATUS  mandatory
    DESCRIPTION
           "LapD window size."
    ::= { isarIccNbLogPortEntry  12 }

isarIccNbLogPortLapDT200 OBJECT-TYPE
    SYNTAX  INTEGER
    ACCESS  read-only
    STATUS  mandatory
    DESCRIPTION
           "LapD T200 duration.
            UNITS = msec."
    ::= { isarIccNbLogPortEntry  13 }

isarIccNbLogPortLapDN200 OBJECT-TYPE
    SYNTAX  INTEGER
    ACCESS  read-only
    STATUS  mandatory
    DESCRIPTION
           "LapD N200 retransmission."
    ::= { isarIccNbLogPortEntry  14 }

isarIccNbLogPortLapDT203 OBJECT-TYPE
    SYNTAX  INTEGER
    ACCESS  read-only
    STATUS  mandatory
    DESCRIPTION
           "LapD T203 duration.
            UNITS = msec."
    ::= { isarIccNbLogPortEntry  15 }

isarIccNbLogPortLapDN201 OBJECT-TYPE
    SYNTAX  INTEGER
    ACCESS  read-only
    STATUS  mandatory
    DESCRIPTION
           "LapD N201 length."
    ::= { isarIccNbLogPortEntry  16 }

isarIccNbLogPortTraceLayer1 OBJECT-TYPE
    SYNTAX  INTEGER {
                      enabled(1),
                      disabled(2)
            }
    ACCESS  read-write
    STATUS  mandatory
    DESCRIPTION
           "Enable or disable tracing for layer-1 (signalling D-channel)
            protocol stack.
            
            Modification of this value is allowed even when the operational
            status is not down.
            The SNMPv2 MAX-ACCESS is read-create"
    ::= { isarIccNbLogPortEntry  17 }

isarIccNbLogPortTraceLayer2 OBJECT-TYPE
    SYNTAX  INTEGER {
                      enabled(1),
                      disabled(2)
            }
    ACCESS  read-write
    STATUS  mandatory
    DESCRIPTION
           "Enable or disable tracing for layer-2 (LapD)
            protocol stack.
            
            Modification of this value is allowed even when the operational
            status is not down.
            The SNMPv2 MAX-ACCESS is read-create"
    ::= { isarIccNbLogPortEntry  18 }

isarIccNbLogPortTraceLayer3 OBJECT-TYPE
    SYNTAX  INTEGER {
                      enabled(1),
                      disabled(2)
            }
    ACCESS  read-write
    STATUS  mandatory
    DESCRIPTION
           "Enable or disable tracing for layer-3 (Qsig)
            protocol stack.
            
            Modification of this value is allowed even when the operational
            status is not down.
            The SNMPv2 MAX-ACCESS is read-create"
    ::= { isarIccNbLogPortEntry  19 }


-- NB logical port statistics

isarIccNbLogPortStatsTable OBJECT-TYPE
    SYNTAX  SEQUENCE OF IsarIccNbLogPortStatsEntry
    ACCESS  not-accessible
    STATUS  mandatory
    DESCRIPTION
           "Statistics concerning a narrowband logical port.
            Rows are created/deleted by IAD4700 at the moment of row 
            creation/deletion in isarIccNbLogPortTable."
    ::= { isarIccNbLogPortObjects  4 }

isarIccNbLogPortStatsEntry OBJECT-TYPE
    SYNTAX  IsarIccNbLogPortStatsEntry
    ACCESS  not-accessible
    STATUS  mandatory
    DESCRIPTION
           "One row in the isarIccNbLogPortStatsTable."
    INDEX   { isarIccNbLogPortIndex }
    ::= { isarIccNbLogPortStatsTable  1 }


IsarIccNbLogPortStatsEntry ::=
    SEQUENCE { 
      isarIccNbLogPortStatsBusyMap
        INTEGER,
        
      isarIccNbLogPortStatsNoLldState
        Counter
        
    }


isarIccNbLogPortStatsBusyMap OBJECT-TYPE
    SYNTAX  INTEGER
    ACCESS  read-only
    STATUS  mandatory
    DESCRIPTION
           "Bitmap that indicates the current busy B-channels."
    ::= { isarIccNbLogPortStatsEntry  2 }

isarIccNbLogPortStatsNoLldState OBJECT-TYPE
    SYNTAX  Counter
    ACCESS  read-only
    STATUS  mandatory
    DESCRIPTION
           "Number of times the NbLogPort goes to the lowerLayerDown 
            state."
    ::= { isarIccNbLogPortStatsEntry  3 }



-- Local node usage table

isarIccNbLogPortLocNodeTable OBJECT-TYPE
    SYNTAX  SEQUENCE OF IsarIccNbLogPortLocNodeEntry
    ACCESS  not-accessible
    STATUS  mandatory
    DESCRIPTION
           "This table gives an list of all NB logical ports that have
            a link to a certain local node.
            
            Rows are created/deleted by IAD4700 at the moment that rows
            are created/deleted in the isarINbLogPortTable.
            
            It gives the management stations an easy way to find out which
            NB logical ports are linked with the local port."
    ::= { isarIccNbLogPortObjects  5 }

isarIccNbLogPortLocNodeEntry OBJECT-TYPE
    SYNTAX  IsarIccNbLogPortLocNodeEntry
    ACCESS  not-accessible
    STATUS  mandatory
    DESCRIPTION
           "One row in the isarIccNbLogPortLocNodeTable."
    INDEX   { isarIccLocNodeIndex, isarIccNbLogPortLocNodeNbLPIndex }
    ::= { isarIccNbLogPortLocNodeTable  1 }


IsarIccNbLogPortLocNodeEntry ::=
    SEQUENCE { 
      isarIccNbLogPortLocNodeNbLPIndex
        INTEGER
        
    }


isarIccNbLogPortLocNodeNbLPIndex OBJECT-TYPE
    SYNTAX  INTEGER (2..2147483647)
    ACCESS  read-only
    STATUS  mandatory
    DESCRIPTION
           "Index of a NB logical port that has a link to the 
            local node identified via isarIccLocNodeIndex."
    ::= { isarIccNbLogPortLocNodeEntry  1 }



-- LOCAL NODE OBJECTS

isarIccLocNodeObjects  OBJECT IDENTIFIER ::=  { isarIcccMIBObjects  8 }

isarIccLocNodeDummy OBJECT-TYPE
    SYNTAX  INTEGER
    ACCESS  read-only
    STATUS  mandatory
    DESCRIPTION
           "Dummy object to protect the local node next index from
            unnecessary increments."
    ::= { isarIccLocNodeObjects  1 }

isarIccLocNodeNextObjects  OBJECT IDENTIFIER ::=  { isarIccLocNodeObjects  2 }

isarIccLocNodeNextIndex OBJECT-TYPE
    SYNTAX  INTEGER (2..2147483647)
    ACCESS  read-only
    STATUS  mandatory
    DESCRIPTION
           "This object is used to assist the manager in
            selecting a value for isarIccLocNodeIndex.  
            The manager has to GET this index before creating a row in 
            isarIccLocNodeTable."
    ::= { isarIccLocNodeNextObjects  1 }



-- Local node table

isarIccLocNodeTable OBJECT-TYPE
    SYNTAX  SEQUENCE OF IsarIccLocNodeEntry
    ACCESS  not-accessible
    STATUS  mandatory
    DESCRIPTION
           "A local node serves to specify the dynamic trunking 
            configuration.  It specifies the kind of protocol which has to
            be used on the interfaces towards the local PABX.
            
            For each PABX there will be an entry in this table.

            It must be possible to dynamically add and delete entries.
            Addition (or deletion) of an entry will automatically add
            (or delete) a corresponding entry in the 
            isarIccLocNodeStatsTable.
            
            A row can only be deleted when all contained NbLogPorts are 
            deleted.
            Before deleting a row in this table, the management station 
            must delete the containing NB logical ports (= all NB logical
            ports that have a reference to this local node).  To find these
            NB logical ports, the isarIccNbLogPortLocNodeTable can be used.
            
            
            IAD4700 R2.0 : only one local PABX = only one local node
                           supported."
    ::= { isarIccLocNodeObjects  3 }

isarIccLocNodeEntry OBJECT-TYPE
    SYNTAX  IsarIccLocNodeEntry
    ACCESS  not-accessible
    STATUS  mandatory
    DESCRIPTION
           "One row in the isarIccLocNodeTable."
    INDEX   { isarIccLocNodeIndex }
    ::= { isarIccLocNodeTable  1 }


IsarIccLocNodeEntry ::=
    SEQUENCE { 
      isarIccLocNodeIndex
        INTEGER,
        
      isarIccLocNodeRowStatus
        INTEGER,
        
      isarIccLocNodeName
        DisplayString,
        
      isarIccLocNodeServiceType
        INTEGER,
        
      isarIccLocNodeProtocol
        INTEGER,
        
      isarIccLocNodeConnectionIndication
        INTEGER
        
    }


isarIccLocNodeIndex OBJECT-TYPE
    SYNTAX  INTEGER (2..2147483647)
    ACCESS  read-only
    STATUS  mandatory
    DESCRIPTION
           "Index, unique in the system, determined by the
            manager via isarIccLocNodeNextIndex."
    ::= { isarIccLocNodeEntry  1 }

isarIccLocNodeRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIccLocNodeEntry  2 }

isarIccLocNodeName OBJECT-TYPE
    SYNTAX  DisplayString
    ACCESS  read-write
    STATUS  mandatory
    DESCRIPTION
           "Operator given local node name.
            Modification is allowed.
            The SNMPv2 MAX-ACCESS is read-create."
    ::= { isarIccLocNodeEntry  3 }

isarIccLocNodeServiceType OBJECT-TYPE
    SYNTAX  INTEGER { 
                      dynamicTrunking(1),
                      grooming(2)
            }
    ACCESS  read-only
    STATUS  mandatory
    DESCRIPTION
           "Type of service used for the local node.
            IAD4700 R2.0 : only dynamic trunking is supported."
    DEFVAL  { dynamicTrunking }
    ::= { isarIccLocNodeEntry  4 }

isarIccLocNodeProtocol OBJECT-TYPE
    SYNTAX  INTEGER { 
                      qsig(1),
                      dss1(2)
            }
    ACCESS  read-only
    STATUS  mandatory
    DESCRIPTION
           "Protocol.
            IAD4700 R2.0 : only qsig is supported."
    DEFVAL  { qsig }
    ::= { isarIccLocNodeEntry  5 }

isarIccLocNodeConnectionIndication OBJECT-TYPE
    SYNTAX  INTEGER { 
                      inUse(1),
                      free(2)
            }
    ACCESS  read-only
    STATUS  mandatory
    DESCRIPTION
           "This object is used to indicate whether the Local node is in
            use by one or more NB logical ports.
            The value of this object is set to inUse after an associated
            entry in the isarIccNbLogPortTable has been created.  It has to
            be set back to free when all associated entries in  the
            isarIccNbLogPortTable have been deleted."
    DEFVAL  { free }
    ::= { isarIccLocNodeEntry  6 }


-- Local node statistics table

isarIccLocNodeStatsTable OBJECT-TYPE
    SYNTAX  SEQUENCE OF IsarIccLocNodeStatsEntry
    ACCESS  not-accessible
    STATUS  mandatory
    DESCRIPTION
           "This table collects the statistics on local node level.
            
            Rows are created/deleted by IAD4700 at the moment that rows
            are created/deleted in the isarILocNodeTable."
    ::= { isarIccLocNodeObjects  4 }

isarIccLocNodeStatsEntry OBJECT-TYPE
    SYNTAX  IsarIccLocNodeStatsEntry
    ACCESS  not-accessible
    STATUS  mandatory
    DESCRIPTION
           "One row in the isarIccLocNodeStatsTable."
    INDEX   { isarIccLocNodeIndex }
    ::= { isarIccLocNodeStatsTable  1 }


IsarIccLocNodeStatsEntry ::=
    SEQUENCE { 
      isarIccLocNodeStatsIcAttempts
        Counter,
        
      isarIccLocNodeStatsIcNormalClear
        Counter,
        
      isarIccLocNodeStatsIcEstablished
        Counter,
        
      isarIccLocNodeStatsOgAttempts
        Counter,
        
      isarIccLocNodeStatsOgNormalClear
        Counter,
        
      isarIccLocNodeStatsOgEstablished
        Counter,
        
      isarIccLocNodeStatsBChannelAttempts
        Counter,
        
      isarIccLocNodeStatsCallBBusy
        Counter
        
    }


isarIccLocNodeStatsIcAttempts OBJECT-TYPE
    SYNTAX  Counter
    ACCESS  read-only
    STATUS  mandatory
    DESCRIPTION
           "Number of incoming call attempts."
    ::= { isarIccLocNodeStatsEntry  2 }

isarIccLocNodeStatsIcNormalClear OBJECT-TYPE
    SYNTAX  Counter
    ACCESS  read-only
    STATUS  mandatory
    DESCRIPTION
           "Number of incoming normal cleared calls.  Normal call
            clearing = call termination or busy."
    ::= { isarIccLocNodeStatsEntry  3 }

isarIccLocNodeStatsIcEstablished OBJECT-TYPE
    SYNTAX  Counter
    ACCESS  read-only
    STATUS  mandatory
    DESCRIPTION
           "Number of incoming established calls."
    ::= { isarIccLocNodeStatsEntry  4 }

isarIccLocNodeStatsOgAttempts OBJECT-TYPE
    SYNTAX  Counter
    ACCESS  read-only
    STATUS  mandatory
    DESCRIPTION
           "Number of outgoing call attempts."
    ::= { isarIccLocNodeStatsEntry  5 }

isarIccLocNodeStatsOgNormalClear OBJECT-TYPE
    SYNTAX  Counter
    ACCESS  read-only
    STATUS  mandatory
    DESCRIPTION
           "Number of outgoing normal cleared calls.  Normal call
            clearing = call termination or busy."
    ::= { isarIccLocNodeStatsEntry  6 }

isarIccLocNodeStatsOgEstablished OBJECT-TYPE
    SYNTAX  Counter
    ACCESS  read-only
    STATUS  mandatory
    DESCRIPTION
           "Number of outgoing established calls."
    ::= { isarIccLocNodeStatsEntry  7 }

isarIccLocNodeStatsBChannelAttempts OBJECT-TYPE
    SYNTAX  Counter
    ACCESS  read-only
    STATUS  mandatory
    DESCRIPTION
           "Number of B-channel attempts."
    ::= { isarIccLocNodeStatsEntry  8 }

isarIccLocNodeStatsCallBBusy OBJECT-TYPE
    SYNTAX  Counter
    ACCESS  read-only
    STATUS  mandatory
    DESCRIPTION
           "Number of B-channels BUSY."
    ::= { isarIccLocNodeStatsEntry  9 }



-- REMOTE NODE OBJECTS

isarIccRemNodeObjects  OBJECT IDENTIFIER ::=  { isarIcccMIBObjects  9 }

isarIccRemNodeDummy OBJECT-TYPE
    SYNTAX  INTEGER
    ACCESS  read-only
    STATUS  mandatory
    DESCRIPTION
           "Dummy object to protect the remote node next index from
            unnecessary increments."
    ::= { isarIccRemNodeObjects  1 }

isarIccRemNodeNextObjects  OBJECT IDENTIFIER ::=  { isarIccRemNodeObjects  2 }

isarIccRemNodeNextIndex OBJECT-TYPE
    SYNTAX  INTEGER (2..2147483647)
    ACCESS  read-only
    STATUS  mandatory
    DESCRIPTION
           "This object is used to assist the manager in
            selecting a value for isarIccRemNodeIndex.  
            The manager has to GET this index before creating a row in 
            isarIccRemNodeTable."
    ::= { isarIccRemNodeNextObjects  1 }



-- Remote node table

isarIccRemNodeTable OBJECT-TYPE
    SYNTAX  SEQUENCE OF IsarIccRemNodeEntry
    ACCESS  not-accessible
    STATUS  mandatory
    DESCRIPTION
           "A remote node serves to specify the configuration of the remote
            NE.  It specifies the ATM number, the VPI, the VCI and the 
            traffic descriptor used for the IWF-IWF signalling channel and
            the Qos parameters necessary to setup an AAL1 interworking
            switched connection with the remote IAD4700.
            
            It must be possible to dynamically add and delete entries.
            Addition (or deletion) of an entry will automatically add
            (or delete) a corresponding entry in the 
            isarIccRemNodeStatsTable.
            
            A row can only be deleted when both admin and oper state are
            down and when all contained NbRouting and 
            PhysicalPortConnections are deleted."
    ::= { isarIccRemNodeObjects  3 }

isarIccRemNodeEntry OBJECT-TYPE
    SYNTAX  IsarIccRemNodeEntry
    ACCESS  not-accessible
    STATUS  mandatory
    DESCRIPTION
           "One row in the isarIccRemNodeTable."
    INDEX   { isarIccRemNodeIndex }
    ::= { isarIccRemNodeTable  1 }


IsarIccRemNodeEntry ::=
    SEQUENCE { 
      isarIccRemNodeIndex
        INTEGER,
        
      isarIccRemNodeRowStatus
        INTEGER,
        
      isarIccRemNodeAdminStatus
        INTEGER,
        
      isarIccRemNodeShutdownMode
        INTEGER,
        
      isarIccRemNodeOperStatus
        INTEGER,
        
      isarIccRemNodeName
        DisplayString,
        
      isarIccRemNodeMaxConnections
        INTEGER,
        
      isarIccRemNodeAtmNumPlan
        INTEGER,
        
      isarIccRemNodeAtmNumType
        INTEGER,
        
      isarIccRemNodeAtmNumValue
        DisplayString,
        
      isarIccRemNodeSigChanMode
        INTEGER,
        
      isarIccRemNodeSigDownTime
        INTEGER,
        
      isarIccRemNodeAtmLayerIfIndex
        INTEGER,
        
      isarIccRemNodeVpi
        INTEGER,
        
      isarIccRemNodeVci
        INTEGER,
        
      isarIccRemNodeVoiceCompr
        INTEGER,
        
      isarIccRemNodePackingFactor
        INTEGER,
        
      isarIccRemNodeOutputGain
        INTEGER,
        
      isarIccRemNodeEnableHighPassFilter
        INTEGER,
        
      isarIccRemNodeEnablePostFilter
        INTEGER,
        
      isarIccRemNodeEnableEchoCancel
        INTEGER,
        
      isarIccRemNodeEnableSilenceCompression
        INTEGER,
        
      isarIccRemNodeInputGain
        INTEGER,
        
      isarIccRemNodePartialFill
        INTEGER,
        
      isarIccRemNodeMaxCellDelay
        INTEGER,
        
      isarIccRemNodeUserDefSigCode1
        INTEGER,
        
      isarIccRemNodeUserDefSigCode2
        INTEGER,
        
      isarIccRemNodeTCEnabled
        INTEGER,
        
      isarIccRemNodeIiscTrafCat
        INTEGER,
        
      isarIccRemNodeIiscPeakCellRate
        INTEGER,
        
      isarIccRemNodeIiscSustCellRate
        INTEGER,
        
      isarIccRemNodeIiscMaxBurstSize
        INTEGER,
        
      isarIccRemNodeIiscCellDelay
        INTEGER,
        
      isarIccRemNodeIiscMinCellRate
        INTEGER,
        
      isarIccRemNodeSscopPollTimer
        INTEGER,
        
      isarIccRemNodeSscopKeepAliveTimer
        INTEGER,
        
      isarIccRemNodeSscopIdleTimer
        INTEGER,
        
      isarIccRemNodeSscopNoResponseTimer
        INTEGER,
        
      isarIccRemNodeSscopCcTimer
        INTEGER,
        
      isarIccRemNodeSscopMaxWindowSize
        INTEGER,
        
      isarIccRemNodeSscopMaxCc
        INTEGER,
        
      isarIccRemNodeSscopMaxPd
        INTEGER,
        
      isarIccRemNodeSscopMaxStat
        INTEGER,
        
      isarIccRemNodeSscopPollAfterUstatRetransmit
        INTEGER,
        
      isarIccRemNodeSscopRepeatUstat
        INTEGER,
        
      isarIccRemNodeSscopResponseUstat
        INTEGER,
        
      isarIccRemNodeNBConnectionIndication
        INTEGER,
        
      isarIccRemNodePhyConnectionIndication
        INTEGER,
        
      isarIccRemNodeTraceLayer1
        INTEGER,
        
      isarIccRemNodeTraceLayer2
        INTEGER,
        
      isarIccRemNodeTraceLayer3
        INTEGER
        
    }


isarIccRemNodeIndex OBJECT-TYPE
    SYNTAX  INTEGER (2..2147483647)
    ACCESS  read-only
    STATUS  mandatory
    DESCRIPTION
           "Index, unique in the system, determined by the
            manager via isarIccRemNodeNextIndex."
    ::= { isarIccRemNodeEntry  1 }

isarIccRemNodeRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIccRemNodeEntry  2 }

isarIccRemNodeAdminStatus OBJECT-TYPE
    SYNTAX  INTEGER {
                      up(1),
                      down(2)
            }
    ACCESS  read-write
    STATUS  mandatory
    DESCRIPTION
           "The desired administrative status of the NbLogPort.
            
            The SNMPv2 MAX-ACCESS is read-create."
    ::= { isarIccRemNodeEntry  3 }

isarIccRemNodeShutdownMode OBJECT-TYPE
    SYNTAX  INTEGER {
                      forced(1),
                      notForced(2)
            }
    ACCESS  read-write
    STATUS  mandatory
    DESCRIPTION
           "The desired shutdown mode of the NbLogPort.
           
            forced: all active calls are released
            notForced: new calls are not accepted; existing calls stay
                       active till they are released according the normal
                       procedure
            
            The shutdown mode is linked with the admin status.
            If admin status = up: changing of this field has no effect.
            If admin status is changed from up to down: active calls will
                                     be released according to this field.
            If admin status = down: changing of this field from notForced
                                    to forced will cause the release of the
                                    active calls.  Changing from forced to
                                    notForced has no effect.
                                    
            Modification of this object is always allowed."
    DEFVAL  { notForced }
    ::= { isarIccRemNodeEntry  4 }

isarIccRemNodeOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "This object indicates the current operational status of the
            layer-3 protocol stack.  The status of the layer-3 protocol
            stack also reflects the status of the lower layers."
    ::= { isarIccRemNodeEntry  5 }

isarIccRemNodeName OBJECT-TYPE
    SYNTAX  DisplayString
    ACCESS  read-write
    STATUS  mandatory
    DESCRIPTION
           "Remote IAD4700 name.
            Modification of this object is always allowed."
    ::= { isarIccRemNodeEntry  6 }

isarIccRemNodeMaxConnections OBJECT-TYPE
    SYNTAX  INTEGER (0..255)
    ACCESS  read-write
    STATUS  mandatory
    DESCRIPTION
           "Maximum simultaneous connections.
            Modification of this object is always allowed."
    ::= { isarIccRemNodeEntry  7 }

isarIccRemNodeAtmNumPlan OBJECT-TYPE
    SYNTAX  INTEGER {
                      e164(1)
            }
    ACCESS  read-only
    STATUS  mandatory
    DESCRIPTION
           "IAD4700 ATM number plan.
            Part of ATM address used by IAD4700 to seet up an ATM call to
            a remote IAD4700/3614x."
    ::= { isarIccRemNodeEntry  8 }

isarIccRemNodeAtmNumType OBJECT-TYPE
    SYNTAX  INTEGER {
                      internationalNumber(1)
            }
    ACCESS  read-only
    STATUS  mandatory
    DESCRIPTION
           "IAD4700 ATM number type.
            Part of ATM address used by IAD4700 to seet up an ATM call to
            a remote IAD4700/3614x."
    ::= { isarIccRemNodeEntry  9 }

isarIccRemNodeAtmNumValue OBJECT-TYPE
    SYNTAX  DisplayString
    ACCESS  read-write
    STATUS  mandatory
    DESCRIPTION
           "IAD4700 ATM number value.
            Part of ATM address used by IAD4700 to seet up an ATM call to
            a remote IAD4700/3614x."
    DEFVAL  { "" }
    ::= { isarIccRemNodeEntry  10 }

isarIccRemNodeSigChanMode OBJECT-TYPE
    SYNTAX  INTEGER {
                      pvc(1),
                      svcAlwaysUp(2),
                      svcOnDemand(3)
            }
    ACCESS  read-only
    STATUS  mandatory
    DESCRIPTION
           "Signalling channel mode.
            IAD4700 R2.0: only pvc supported."
    DEFVAL  { pvc }
    ::= { isarIccRemNodeEntry  11 }

isarIccRemNodeSigDownTime OBJECT-TYPE
    SYNTAX  INTEGER (1..86400)
    ACCESS  read-only
    STATUS  mandatory
    DESCRIPTION
           "Signalling channel downtime (only for SVC on demand).
            UNITS = sec.
            IAD4700 R2.0: not used because only PVC supported."
    ::= { isarIccRemNodeEntry  12 }

isarIccRemNodeAtmLayerIfIndex OBJECT-TYPE
    SYNTAX  INTEGER
    ACCESS  read-write
    STATUS  mandatory
    DESCRIPTION
           "IfIndex of the ATM layer.
            The ACCESS is read-write when the signalling channel mode is
            set to pvc, read-only in all the other cases.
            Modification of this value is not allowed.
            The SNMPv2 MAX-ACCESS is read-(only-)create."
    ::= { isarIccRemNodeEntry  13 }

isarIccRemNodeVpi OBJECT-TYPE
    SYNTAX  INTEGER (0..255)
    ACCESS  read-write
    STATUS  mandatory
    DESCRIPTION
           "VPI.
            The ACCESS is read-write when the signalling channel mode is
            set to pvc, read-only in all the other cases.
            Modification of this value is not allowed.
            The SNMPv2 MAX-ACCESS is read-(only-)create."
    ::= { isarIccRemNodeEntry  14 }

isarIccRemNodeVci OBJECT-TYPE
    SYNTAX  INTEGER (32..1024)
    ACCESS  read-write
    STATUS  mandatory
    DESCRIPTION
           "VPI.
            The ACCESS is read-write when the signalling channel mode is
            set to pvc, read-only in all the other cases.
            Modification of this value is not allowed.
            The SNMPv2 MAX-ACCESS is read-(only-)create."
    ::= { isarIccRemNodeEntry  15 }

isarIccRemNodeVoiceCompr OBJECT-TYPE
    SYNTAX  INTEGER {
                      none(1),
                      g723Lo(2),
                      g723Hi(3),
                      g729(4)
            }
    ACCESS  read-write
    STATUS  mandatory
    DESCRIPTION
           "Voice compression algorithm.
            The parameter is only used when a bearer call is
            set up.
            Modification of this object is always allowed."
    ::= { isarIccRemNodeEntry  16 }

isarIccRemNodePackingFactor OBJECT-TYPE
    SYNTAX  INTEGER (1..2)
    ACCESS  read-write
    STATUS  mandatory

    DESCRIPTION
           "Packing factor for voice compression.
            The parameter is only used when a bearer call is
            set up with voice compression.
            Depending on isarIccRemNodeVoiceCompr this value can 
            be :
                 for g729 the value can be 1 to 2
                 for g723lo and g723hi it must be 1
            Modification of this object is always allowed."
    ::= { isarIccRemNodeEntry  17 }

isarIccRemNodeOutputGain OBJECT-TYPE 
    SYNTAX  INTEGER (-31..31) 
    ACCESS  read-write 
    STATUS  mandatory 
    DESCRIPTION 
           "The voice output gain in db for voice compression. 
            The parameter is only used when a bearer call is 
            set up with voice compression. 
            Modification of this object is always allowed." 
    DEFVAL { 0 } 
    ::= { isarIccRemNodeEntry  18 } 

isarIccRemNodeEnableHighPassFilter OBJECT-TYPE 
    SYNTAX  INTEGER { 
                      true(1), 
                      false(2) 
            } 
    ACCESS  read-write 
    STATUS  mandatory 
    DESCRIPTION 
           "EnableHighPassFilter for voice compression. 
            The parameter is only used when a bearer call is 
            set up with voice compression. 
            Modification of this object is always allowed." 
    DEFVAL { true } 
    ::= { isarIccRemNodeEntry  19 } 

isarIccRemNodeEnablePostFilter OBJECT-TYPE 
    SYNTAX  INTEGER { 
                      true(1), 
                      false(2) 
            } 
    ACCESS  read-write 
    STATUS  mandatory 
    DESCRIPTION 
           "EnablePostFilter for voice compression. 
            The parameter is only used when a bearer call is 
            set up with voice compression. 
            Modification of this object is always allowed." 
    DEFVAL { true } 
    ::= { isarIccRemNodeEntry  20 } 

isarIccRemNodeEnableEchoCancel OBJECT-TYPE 
    SYNTAX  INTEGER { 
                      true(1), 
                      false(2) 
            } 
    ACCESS  read-write 
    STATUS  mandatory 
    DESCRIPTION 
           "Enable echo cancellation for voice compression. 
            The parameter is only used when a bearer call is 
            set up with voice compression. 
            Modification of this object is always allowed." 
    DEFVAL { true } 
    ::= { isarIccRemNodeEntry  21 } 

isarIccRemNodeEnableSilenceCompression OBJECT-TYPE 
    SYNTAX  INTEGER { 
                      true(1), 
                      false(2) 
            } 
    ACCESS  read-write 
    STATUS  mandatory 
    DESCRIPTION 
           "Enable silence compression for voice compression. 
            The parameter is only used when a bearer call is 
            set up with voice compression. 
            Modification of this object is always allowed." 
    DEFVAL { false } 
    ::= { isarIccRemNodeEntry  22 } 

isarIccRemNodeInputGain OBJECT-TYPE 
    SYNTAX  INTEGER (-31..31) 
    ACCESS  read-write 
    STATUS  mandatory 
    DESCRIPTION 
           "The voice input gain in db for voice compression. 
            The parameter is only used when a bearer call is 
            set up with voice compression. 
            Modification of this object is always allowed." 
    DEFVAL { 0 } 
    ::= { isarIccRemNodeEntry  23 } 

isarIccRemNodePartialFill OBJECT-TYPE
    SYNTAX  INTEGER (0 | 4..47)
    ACCESS  read-write
    STATUS  mandatory
    DESCRIPTION
           "AAL1 partial fill.
            The parameter is only used when a 64 KBit/sec bearer call is
            set up.
            Modification of this object is always allowed."
    DEFVAL  { 0 }
    ::= { isarIccRemNodeEntry  24 }

isarIccRemNodeMaxCellDelay OBJECT-TYPE
    SYNTAX  INTEGER (1..65535)
    ACCESS  read-write
    STATUS  mandatory
    DESCRIPTION
           "Maximum cell delay var tolerance.
            UNITS = 10 microsec.
            Modification of this object is always allowed."
    DEFVAL  { 250 }
    ::= { isarIccRemNodeEntry  25 }

isarIccRemNodeUserDefSigCode1 OBJECT-TYPE
    SYNTAX  INTEGER (0..15)
    ACCESS  read-write
    STATUS  obsolete
    DESCRIPTION
           "CCC: no 64 KBit/sec bearer call is set up."
    DEFVAL { 0 }
    ::= { isarIccRemNodeEntry  26 }

isarIccRemNodeUserDefSigCode2 OBJECT-TYPE
    SYNTAX  INTEGER (0..15)
    ACCESS  read-write
    STATUS  obsolete
    DESCRIPTION
           "CCC: no 64 KBit/sec bearer call is set up."
    DEFVAL { 15 }
    ::= { isarIccRemNodeEntry  27 }


isarIccRemNodeTCEnabled OBJECT-TYPE
    SYNTAX  INTEGER {
                      true(1),
                      false(2)
            }
    ACCESS  read-write
    STATUS  obsolete
    DESCRIPTION
           "CCC: no 64 KBit/sec bearer call is set up."
    DEFVAL { false }
    ::= { isarIccRemNodeEntry  28 }

isarIccRemNodeIiscTrafCat OBJECT-TYPE
    SYNTAX  INTEGER {
                      nrtVbr(1),
                      ubr(2),
                      ubrPlus(3)
            }
    ACCESS  read-write
    STATUS  mandatory
    DESCRIPTION
           "IISC traffic category.
            IISC traffic category in combination with IISC peak cell rate,
            IISC sust cell rate, IISC max burst size, IISC cell delay var
            tolerance, IISC min cell rate, is used to set up the signalling 
            connection.
            Modification of this value is not allowed.
            The SNMPv2 MAX-ACCESS is read-(only-)create."
    DEFVAL  { ubr }
    ::= { isarIccRemNodeEntry  29 }

isarIccRemNodeIiscPeakCellRate OBJECT-TYPE
    SYNTAX  INTEGER (1..65535)
    ACCESS  read-write
    STATUS  mandatory
    DESCRIPTION
           "IISC peak cell rate.
            IISC peak cell rate in combination with IISC traffic category,
            IISC sust cell rate, IISC max burst size, IISC cell delay var
            tolerance, IISC min cell rate, is used to set up the signalling 
            connection.
            Modification of this value is not allowed.
            The SNMPv2 MAX-ACCESS is read-(only-)create."
    DEFVAL  { 167 }
    ::= { isarIccRemNodeEntry  30 }

isarIccRemNodeIiscSustCellRate OBJECT-TYPE
    SYNTAX  INTEGER (1..65535)
    ACCESS  read-write
    STATUS  mandatory
    DESCRIPTION
           "IISC sustainable cell rate.
            IISC sust cell rate in combination with IISC traffic category,
            IISC peak cell rate, IISC max burst size, IISC cell delay var
            tolerance, IISC min cell rate, is used to set up the signalling 
            connection.
            Modification of this value is not allowed.
            The SNMPv2 MAX-ACCESS is read-(only-)create."
    DEFVAL  { 16 }
    ::= { isarIccRemNodeEntry  31 }

isarIccRemNodeIiscMaxBurstSize OBJECT-TYPE
    SYNTAX  INTEGER (1..65535)
    ACCESS  read-write
    STATUS  mandatory
    DESCRIPTION
           "IISC maximum burst size.
            IISC max burst size in combination with IISC traffic category,
            IISC peak cell rate, IISC sust cell rate, IISC cell delay var
            tolerance, IISC min cell rate, is used to set up the signalling 
            connection.
            Modification of this value is not allowed.
            The SNMPv2 MAX-ACCESS is read-(only-)create."
    DEFVAL  { 12 }
    ::= { isarIccRemNodeEntry  32 }

isarIccRemNodeIiscCellDelay OBJECT-TYPE
    SYNTAX  INTEGER (1..65535)
    ACCESS  read-write
    STATUS  mandatory
    DESCRIPTION
           "IISC cell delay var tolerance.
            UNITS = 10 microsec.
            IISC cell delay var tolerance in combination with IISC traffic
            category, IISC peak cell rate, IISC sust cell rate, IISC max
            burst size, IISC min cell rate, is used to set up the signalling
            connection.
            Modification of this value is not allowed.
            The SNMPv2 MAX-ACCESS is read-(only-)create."
    DEFVAL  { 250 }
    ::= { isarIccRemNodeEntry  33 }

isarIccRemNodeIiscMinCellRate OBJECT-TYPE
    SYNTAX  INTEGER (0..65535)
    ACCESS  read-write
    STATUS  mandatory
    DESCRIPTION
           "IISC minimum cell rate.
            IISC min cell rate in combination with IISC traffic category,
            IISC peak cell rate, IISC sust cell rate, IISC max burst size,
            IISC cell delay var tolerance, is used to set up the signalling
            connection.
            Modification of this value is not allowed.
            The SNMPv2 MAX-ACCESS is read-(only-)create."
    DEFVAL  { 0 }
    ::= { isarIccRemNodeEntry  34 }

isarIccRemNodeSscopPollTimer OBJECT-TYPE
    SYNTAX  INTEGER
    ACCESS  read-only
    STATUS  mandatory
    DESCRIPTION
           "SSCOP poll timer value for IISC.
            UNITS = msec.
            Default = 750 msec."
    ::= { isarIccRemNodeEntry  35 }

isarIccRemNodeSscopKeepAliveTimer OBJECT-TYPE
    SYNTAX  INTEGER
    ACCESS  read-only
    STATUS  mandatory
    DESCRIPTION
           "SSCOP keep alive timer value for IISC.
            UNITS = msec.
            Default = 2000 msec."
    ::= { isarIccRemNodeEntry  36 }

isarIccRemNodeSscopIdleTimer OBJECT-TYPE
    SYNTAX  INTEGER
    ACCESS  read-only
    STATUS  mandatory
    DESCRIPTION
           "SSCOP idle timer value for IISC.
            UNITS = msec.
            Default = 15000 msec."
    ::= { isarIccRemNodeEntry  37 }

isarIccRemNodeSscopNoResponseTimer OBJECT-TYPE
    SYNTAX  INTEGER
    ACCESS  read-only
    STATUS  mandatory
    DESCRIPTION
           "SSCOP no response timer value for IISC.
            UNITS = msec.
            Default = 7000 msec."
    ::= { isarIccRemNodeEntry  38 }

isarIccRemNodeSscopCcTimer OBJECT-TYPE
    SYNTAX  INTEGER
    ACCESS  read-only
    STATUS  mandatory
    DESCRIPTION
           "SSCOP connection control timer value for IISC.
            UNITS = msec.
            Default = 1000 msec."
    ::= { isarIccRemNodeEntry  39 }

isarIccRemNodeSscopMaxWindowSize OBJECT-TYPE
    SYNTAX  INTEGER
    ACCESS  read-only
    STATUS  mandatory
    DESCRIPTION
           "SSCOP maximum window size for IISC.
            UNITS = messages.
            Default = 8 messages."
    ::= { isarIccRemNodeEntry  40 }

isarIccRemNodeSscopMaxCc OBJECT-TYPE
    SYNTAX  INTEGER
    ACCESS  read-only
    STATUS  mandatory
    DESCRIPTION
           "SSCOP maximum retries value for IISC.
            Default = 4."
    ::= { isarIccRemNodeEntry  41 }

isarIccRemNodeSscopMaxPd OBJECT-TYPE
    SYNTAX  INTEGER
    ACCESS  read-only
    STATUS  mandatory
    DESCRIPTION
           "SSCOP maximum poll data value for IISC.
            Default = 25."
    ::= { isarIccRemNodeEntry  42 }

isarIccRemNodeSscopMaxStat OBJECT-TYPE
    SYNTAX  INTEGER
    ACCESS  read-only
    STATUS  mandatory
    DESCRIPTION
           "SSCOP maximumStat value for IISC.
            Default = 67."
    ::= { isarIccRemNodeEntry  43 }

isarIccRemNodeSscopPollAfterUstatRetransmit OBJECT-TYPE
    SYNTAX  INTEGER {
                      enabled(1),
                      disabled(2)
            }
    ACCESS  read-only
    STATUS  mandatory
    DESCRIPTION
           "SSCOP poll after retransmit enabled or disabled for IISC."
    ::= { isarIccRemNodeEntry  44 }

isarIccRemNodeSscopRepeatUstat OBJECT-TYPE
    SYNTAX  INTEGER {
                      enabled(1),
                      disabled(2)
            }
    ACCESS  read-only
    STATUS  mandatory
    DESCRIPTION
           "SSCOP repeat Ustat enabled or disabled for IISC."
    ::= { isarIccRemNodeEntry  45 }

isarIccRemNodeSscopResponseUstat OBJECT-TYPE
    SYNTAX  INTEGER {
                      enabled(1),
                      disabled(2)
            }
    ACCESS  read-only
    STATUS  mandatory
    DESCRIPTION
           "SSCOP response Ustat enabled or disabled for IISC."
    ::= { isarIccRemNodeEntry  46 }

isarIccRemNodeNBConnectionIndication OBJECT-TYPE
    SYNTAX  INTEGER { 
                      inUse(1),
                      free(2)
            }
    ACCESS  read-only
    STATUS  mandatory
    DESCRIPTION
           "This object is used to indicate whether the remote node is in
            use by one or more NB routings.
            The value of this object is set to inUse after an associated
            entry in the isarIccNbRoutingTable has been created.  It has to
            be set back to free when all associated entries in the 
            isarIccNbRoutingTable have been deleted."
    DEFVAL  { free }
    ::= { isarIccRemNodeEntry  47 }

isarIccRemNodePhyConnectionIndication OBJECT-TYPE
    SYNTAX  INTEGER { 
                      inUse(1),
                      free(2)
            }
    ACCESS  read-only
    STATUS  mandatory
    DESCRIPTION
           "This object is used to indicate whether the remote node is in
            use by one or more physical port connections.
            The value of this object is set to inUse after an associated
            entry in the isarIccPhyPortConnTable has been created.  It has
            to be set back to free when all associated entries in the 
            isarIccPhyPortConnTable have been deleted."
    DEFVAL  { free }
    ::= { isarIccRemNodeEntry  48 }

isarIccRemNodeTraceLayer1 OBJECT-TYPE
    SYNTAX  INTEGER {
                      enabled(1),
                      disabled(2)
            }
    ACCESS  read-write
    STATUS  mandatory
    DESCRIPTION
           "Enable or disable tracing for layer-1 (store and forward for
            signalling channel) protocol stack.
            
            Modification of this value is allowed even when the operational
            status is not down.
            The SNMPv2 MAX-ACCESS is read-create"
    DEFVAL  { disabled }
    ::= { isarIccRemNodeEntry  49 }

isarIccRemNodeTraceLayer2 OBJECT-TYPE
    SYNTAX  INTEGER {
                      enabled(1),
                      disabled(2)
            }
    ACCESS  read-write
    STATUS  mandatory
    DESCRIPTION
           "Enable or disable tracing for layer-2 (SAAL) protocol stack.
            
            Modification of this value is allowed even when the operational
            status is not down.
            The SNMPv2 MAX-ACCESS is read-create"
    DEFVAL  { disabled }
    ::= { isarIccRemNodeEntry  50 }

isarIccRemNodeTraceLayer3 OBJECT-TYPE
    SYNTAX  INTEGER {
                      enabled(1),
                      disabled(2)
            }
    ACCESS  read-write
    STATUS  mandatory
    DESCRIPTION
           "Enable or disable tracing for layer-3 (Qsig) protocol stack.
            
            Modification of this value is allowed even when the operational
            status is not down.
            The SNMPv2 MAX-ACCESS is read-create"
    DEFVAL  { disabled }
    ::= { isarIccRemNodeEntry  51 }


-- Remote node statistics table

isarIccRemNodeStatsTable OBJECT-TYPE
    SYNTAX  SEQUENCE OF IsarIccRemNodeStatsEntry
    ACCESS  not-accessible
    STATUS  mandatory
    DESCRIPTION
           "Statistics concerning a remote node.
            Rows are created/deleted by IAD4700 at the moment of row 
            creation/deletion in isarIccRemNodeTable."
    ::= { isarIccRemNodeObjects  4 }

isarIccRemNodeStatsEntry OBJECT-TYPE
    SYNTAX  IsarIccRemNodeStatsEntry
    ACCESS  not-accessible
    STATUS  mandatory
    DESCRIPTION
           "One row in the isarIccRemNodeStatsTable."
    INDEX   { isarIccRemNodeIndex }
    ::= { isarIccRemNodeStatsTable  1 }


IsarIccRemNodeStatsEntry ::=
    SEQUENCE { 
      isarIccRemNodeStatsNumCalls
        Gauge,
        
      isarIccRemNodeStatsIcBearAttempts
        Counter,
        
      isarIccRemNodeStatsIcBearNormalClear
        Counter,
        
      isarIccRemNodeStatsIcBearEstablished
        Counter,
        
      isarIccRemNodeStatsIcBearAtmBusy
        Counter,
        
      isarIccRemNodeStatsIcSigAttempts
        Counter,
        
      isarIccRemNodeStatsIcSigNormalClear
        Counter,
        
      isarIccRemNodeStatsIcSigEstablished
        Counter,
        
      isarIccRemNodeStatsOgBearAttempts
        Counter,
        
      isarIccRemNodeStatsOgBearNormalClear
        Counter,
        
      isarIccRemNodeStatsOgBearEstablished
        Counter,
        
      isarIccRemNodeStatsOgBearAtmBusy
        Counter,
        
      isarIccRemNodeStatsOgSigAttempts
        Counter,
        
      isarIccRemNodeStatsOgSigNormalClear
        Counter,
        
      isarIccRemNodeStatsOgSigEstablished
        Counter
        
    }


isarIccRemNodeStatsNumCalls OBJECT-TYPE
    SYNTAX  Gauge
    ACCESS  read-only
    STATUS  mandatory
    DESCRIPTION
           "Current number of active calls with B-channel = current
            number of SVCs."
    ::= { isarIccRemNodeStatsEntry  2 }

isarIccRemNodeStatsIcBearAttempts OBJECT-TYPE
    SYNTAX  Counter
    ACCESS  read-only
    STATUS  mandatory
    DESCRIPTION
           "Number of incoming bearer call attempts = the number of times
            a broadband setup message is received.  This broadband call is
            used to transport the B-channel information. Only the broadband
            calls for which a remote node is defined are counted here."
    ::= { isarIccRemNodeStatsEntry  3 }

isarIccRemNodeStatsIcBearNormalClear OBJECT-TYPE
    SYNTAX  Counter
    ACCESS  read-only
    STATUS  mandatory
    DESCRIPTION
           "Number of incoming bearer normal cleared calls.  Normal call
            clearing = call termination or busy."
    ::= { isarIccRemNodeStatsEntry  4 }

isarIccRemNodeStatsIcBearEstablished OBJECT-TYPE
    SYNTAX  Counter
    ACCESS  read-only
    STATUS  mandatory
    DESCRIPTION
           "Number of incoming bearer established calls = the number of 
            broadband that goes to the connected state.  These calls are 
            able to transport the narrowband B-channel information."
    ::= { isarIccRemNodeStatsEntry  5 }

isarIccRemNodeStatsIcBearAtmBusy OBJECT-TYPE
    SYNTAX  Counter
    ACCESS  read-only
    STATUS  mandatory
    DESCRIPTION
           "Number of incoming bearer ATM BUSY.  Overflow in the ATM
            network: no bandwidth available to setup the call."
    ::= { isarIccRemNodeStatsEntry  6 }

isarIccRemNodeStatsIcSigAttempts OBJECT-TYPE
    SYNTAX  Counter
    ACCESS  read-only
    STATUS  mandatory
    DESCRIPTION
           "Number of incoming signalling call attempts = the number of 
            narrowband setup messages sent over the IWF-IWF signalling
            channel."
    ::= { isarIccRemNodeStatsEntry  7 }

isarIccRemNodeStatsIcSigNormalClear OBJECT-TYPE
    SYNTAX  Counter
    ACCESS  read-only
    STATUS  mandatory
    DESCRIPTION
           "Number of incoming signalling normal cleared calls.  Normal call
            clearing = call termination or busy."
    ::= { isarIccRemNodeStatsEntry  8 }

isarIccRemNodeStatsIcSigEstablished OBJECT-TYPE
    SYNTAX  Counter
    ACCESS  read-only
    STATUS  mandatory
    DESCRIPTION
           "Number of incoming signalling established calls."
    ::= { isarIccRemNodeStatsEntry  9 }

isarIccRemNodeStatsOgBearAttempts OBJECT-TYPE
    SYNTAX  Counter
    ACCESS  read-only
    STATUS  mandatory
    DESCRIPTION
           "Number of outgoing bearer call attempts."
    ::= { isarIccRemNodeStatsEntry  10 }

isarIccRemNodeStatsOgBearNormalClear OBJECT-TYPE
    SYNTAX  Counter
    ACCESS  read-only
    STATUS  mandatory
    DESCRIPTION
           "Number of outgoing bearer normal cleared calls.  Normal call
            clearing = call termination or busy."
    ::= { isarIccRemNodeStatsEntry  11 }

isarIccRemNodeStatsOgBearEstablished OBJECT-TYPE
    SYNTAX  Counter
    ACCESS  read-only
    STATUS  mandatory
    DESCRIPTION
           "Number of outgoing bearer established calls."
    ::= { isarIccRemNodeStatsEntry  12 }

isarIccRemNodeStatsOgBearAtmBusy OBJECT-TYPE
    SYNTAX  Counter
    ACCESS  read-only
    STATUS  mandatory
    DESCRIPTION
           "Number of outgoing bearer ATM BUSY.  Overflow in the ATM
            network: no bandwidth available to setup the call."
    ::= { isarIccRemNodeStatsEntry  13 }

isarIccRemNodeStatsOgSigAttempts OBJECT-TYPE
    SYNTAX  Counter
    ACCESS  read-only
    STATUS  mandatory
    DESCRIPTION
           "Number of outgoing signalling call attempts."
    ::= { isarIccRemNodeStatsEntry  14 }

isarIccRemNodeStatsOgSigNormalClear OBJECT-TYPE
    SYNTAX  Counter
    ACCESS  read-only
    STATUS  mandatory
    DESCRIPTION
           "Number of outgoing signalling normal cleared calls.  Normal call
            clearing = call termination or busy."
    ::= { isarIccRemNodeStatsEntry  15 }

isarIccRemNodeStatsOgSigEstablished OBJECT-TYPE
    SYNTAX  Counter
    ACCESS  read-only
    STATUS  mandatory
    DESCRIPTION
           "Number of outgoing signalling established calls."
    ::= { isarIccRemNodeStatsEntry  16 }

        

-- NARROWBAND ROUTING OBJECTS

isarIccNbRoutingObjects  OBJECT IDENTIFIER ::=  { isarIcccMIBObjects  10 }

isarIccNbRoutingDummy OBJECT-TYPE
    SYNTAX  INTEGER
    ACCESS  read-only
    STATUS  mandatory
    DESCRIPTION
           "Dummy object to protect the NB Routing next index from
            unnecessary increments."
    ::= { isarIccNbRoutingObjects  1 }

isarIccNbRoutingNextObjects  OBJECT IDENTIFIER ::=  { isarIccNbRoutingObjects  2 }

isarIccNbRoutingNextIndex OBJECT-TYPE
    SYNTAX  INTEGER (2..2147483647)
    ACCESS  read-only
    STATUS  mandatory
    DESCRIPTION
           "This object is used to assist the manager in
            selecting a value for isarIccNbRoutingIndex.  
            The manager has to GET this index before creating a row in 
            isarIccNbRoutingTable."
    ::= { isarIccNbRoutingNextObjects  1 }



-- NB Routing table

isarIccNbRoutingTable OBJECT-TYPE
    SYNTAX  SEQUENCE OF IsarIccNbRoutingEntry
    ACCESS  not-accessible
    STATUS  mandatory
    DESCRIPTION
           "Narrowband routing.

            It must be possible to dynamically add and delete entries.
            Addition (or deletion) of an entry will automatically add
            (or delete) a corresponding entry in the 
            isarIccNbRoutingRemNodeTable."
    ::= { isarIccNbRoutingObjects  3 }

isarIccNbRoutingEntry OBJECT-TYPE
    SYNTAX  IsarIccNbRoutingEntry
    ACCESS  not-accessible
    STATUS  mandatory
    DESCRIPTION
           "One row in the isarIccNbRoutingTable."
    INDEX   { isarIccNbRoutingIndex }
    ::= { isarIccNbRoutingTable  1 }


IsarIccNbRoutingEntry ::=
    SEQUENCE { 
      isarIccNbRoutingIndex
        INTEGER,
        
      isarIccNbRoutingRowStatus
        INTEGER,
        
      isarIccNbRoutingNbAddress
        DisplayString,
        
      isarIccNbRoutingRemNodeIndex
        INTEGER
        
    }


isarIccNbRoutingIndex OBJECT-TYPE
    SYNTAX  INTEGER (2..2147483647)
    ACCESS  read-only
    STATUS  mandatory
    DESCRIPTION
           "Index, unique in the system, determined by the
            manager via isarIccNbRoutingNextIndex."
    ::= { isarIccNbRoutingEntry  1 }

isarIccNbRoutingRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIccNbRoutingEntry  2 }

isarIccNbRoutingNbAddress OBJECT-TYPE
    SYNTAX  DisplayString
    ACCESS  read-write
    STATUS  mandatory
    DESCRIPTION
           "Narrowband address.
            Modification of this value is not allowed.
            The SNMPv2 MAX-ACCESS is read-create."
    ::= { isarIccNbRoutingEntry  3 }

isarIccNbRoutingRemNodeIndex OBJECT-TYPE
    SYNTAX  INTEGER
    ACCESS  read-write
    STATUS  mandatory
    DESCRIPTION
           "Index to the associated remote node.
            Modification of this value is not allowed.
            The SNMPv2 MAX-ACCESS is read-create."
    ::= { isarIccNbRoutingEntry  4 }


-- NB Routing remote node usage table

isarIccNbRoutingRemNodeTable OBJECT-TYPE
    SYNTAX  SEQUENCE OF IsarIccNbRoutingRemNodeEntry
    ACCESS  not-accessible
    STATUS  mandatory
    DESCRIPTION
           "This table gives an list of all NB routings that have
            a link to a certain remote node.
            
            Rows are created/deleted by IAD4700 at the moment that rows
            are created/deleted in the isarINbRoutingTable.
            
            It gives the management stations an easy way to find out which
            remote nodes are linked with a NB routing."
    ::= { isarIccNbRoutingObjects  4 }

isarIccNbRoutingRemNodeEntry OBJECT-TYPE
    SYNTAX  IsarIccNbRoutingRemNodeEntry
    ACCESS  not-accessible
    STATUS  mandatory
    DESCRIPTION
           "One row in the isarIccNbRoutingRemNodeTable."
    INDEX   { isarIccRemNodeIndex, isarIccNbRoutingRemoteNodeIndex }
    ::= { isarIccNbRoutingRemNodeTable  1 }


IsarIccNbRoutingRemNodeEntry ::=
    SEQUENCE { 
      isarIccNbRoutingRemoteNodeIndex
        INTEGER
        
    }


isarIccNbRoutingRemoteNodeIndex OBJECT-TYPE
    SYNTAX  INTEGER (2..2147483647)
    ACCESS  read-only
    STATUS  mandatory
    DESCRIPTION
           "Index of a NB route that has a link to the 
            remote node identified via isarIccRemNodeIndex."
    ::= { isarIccNbRoutingRemNodeEntry  1 }



-- PHYSICAL PORT CONNECTION OBJECTS

isarIccPhyPortConnObjects  OBJECT IDENTIFIER ::=  { isarIcccMIBObjects  11 }

isarIccPhyPortConnDummy OBJECT-TYPE
    SYNTAX  INTEGER
    ACCESS  read-only
    STATUS  mandatory
    DESCRIPTION
           "Dummy object to protect the physical port connection next index
            from unnecessary increments."
    ::= { isarIccPhyPortConnObjects  1 }

isarIccPhyPortConnNextObjects  OBJECT IDENTIFIER ::=  { isarIccPhyPortConnObjects  2 }

isarIccPhyPortConnNextIndex OBJECT-TYPE
    SYNTAX  INTEGER (2..2147483647)
    ACCESS  read-only
    STATUS  mandatory
    DESCRIPTION
           "This object is used to assist the manager in
            selecting a value for isarIccPhyPortConnIndex.  
            The manager has to GET this index before creating a row in 
            isarIccPhyPortConnTable."
    ::= { isarIccPhyPortConnNextObjects  1 }



-- Physical port connection table

isarIccPhyPortConnTable OBJECT-TYPE
    SYNTAX  SEQUENCE OF IsarIccPhyPortConnEntry
    ACCESS  not-accessible
    STATUS  mandatory
    DESCRIPTION
           "The pysical port connection serves to specify the S0-S0
            configuration.  It specifies the relation between an S0-
            interface and a logical peer address.

            It must be possible to dynamically add and delete entries.
            Addition (or deletion) of an entry will automatically add
            (or delete) a corresponding entry in the 
            isarIccPhyPortConnStatsTable and isarIccPhyPortConnRemNodeTable.
            
            A row can only be deleted when both admin and oper state are
            down."
    ::= { isarIccPhyPortConnObjects  3 }

isarIccPhyPortConnEntry OBJECT-TYPE
    SYNTAX  IsarIccPhyPortConnEntry
    ACCESS  not-accessible
    STATUS  mandatory
    DESCRIPTION
           "One row in the isarIccPhyPortConnTable."
    INDEX   { isarIccPhyPortConnIndex }
    ::= { isarIccPhyPortConnTable  1 }


IsarIccPhyPortConnEntry ::=
    SEQUENCE { 
      isarIccPhyPortConnIndex
        INTEGER,
        
      isarIccPhyPortConnRowStatus
        INTEGER,
        
      isarIccPhyPortConnAdminStatus
        INTEGER,
        
      isarIccPhyPortConnOperStatus
        INTEGER,
        
      isarIccPhyPortConnLowerLayerIfIndex
        INTEGER,
        
      isarIccPhyPortConnRemoteNodeIndex
        INTEGER,
        
      isarIccPhyPortConnLogPeerAddr
        INTEGER,
        
      isarIccPhyPortConnTrace
        INTEGER,
        
      isarIccPhyPortConnDataLinkSupervision
        INTEGER
        
    }


isarIccPhyPortConnIndex OBJECT-TYPE
    SYNTAX  INTEGER (2..2147483647)
    ACCESS  read-only
    STATUS  mandatory
    DESCRIPTION
           "Index, unique in the system, determined by the
            manager via isarIccPhyPortConnIndex."
    ::= { isarIccPhyPortConnEntry  1 }

isarIccPhyPortConnRowStatus OBJECT-TYPE
    SYNTAX  INTEGER {
                      -- the following two values are states:
                      -- these values may be read or written
                      active(1),
                      notInService(2),

                      -- the following value is a state:
                      -- this value may be read, but not written
                      notReady(3),

                      -- the following three values are
                      -- actions: these values may be written,
                      --   but are never read
                      createAndGo(4),
                      createAndWait(5),
                      destroy(6)
            }
    ACCESS  read-write
    STATUS  mandatory
    DESCRIPTION
           "This object is used to create and delete rows in
            this table.
            The SNMPv2 MAX-ACCESS is read-create."
    ::= { isarIccPhyPortConnEntry  2 }

isarIccPhyPortConnAdminStatus OBJECT-TYPE
    SYNTAX  INTEGER {
                      up(1),
                      down(2)
            }
    ACCESS  read-write
    STATUS  mandatory
    DESCRIPTION
           "The desired administrative status of the physical port
            connection.
            
            The SNMPv2 MAX-ACCESS is read-create."
    ::= { isarIccPhyPortConnEntry  3 }

isarIccPhyPortConnOperStatus OBJECT-TYPE
    SYNTAX  INTEGER {
                      up(1),        -- ready to pass packets
                      down(2),
                      testing(3),   -- in some test mode
                      unknown(4),   -- status can not be determined
                                    -- for some reason.
                      dormant(5),
                      notPresent(6),    -- some component is missing
                      lowerLayerDown(7) -- down due to state of
                                        -- lower-layer interface(s)
            }
    ACCESS  read-only
    STATUS  mandatory
    DESCRIPTION
           "This object indicates the current operational status."
    ::= { isarIccPhyPortConnEntry  4 }

isarIccPhyPortConnLowerLayerIfIndex OBJECT-TYPE
    SYNTAX  INTEGER (0..2147483647)
    ACCESS  read-write
    STATUS  mandatory
    DESCRIPTION
           "Lower layer ifIndex = ifIndex of S0 port on which the physical connection
            is defined."
    ::= { isarIccPhyPortConnEntry  5 }

isarIccPhyPortConnRemoteNodeIndex OBJECT-TYPE
    SYNTAX  INTEGER
    ACCESS  read-write
    STATUS  mandatory
    DESCRIPTION
           "Index to a remote node = index to an entry in 
            isarIccRemNodeTable.
            
            Modification of this value is not allowed.
            The SNMPv2 MAX-ACCESS is read-(only-)create."
    ::= { isarIccPhyPortConnEntry  6 }

isarIccPhyPortConnLogPeerAddr OBJECT-TYPE
    SYNTAX  INTEGER (0..8175)
    ACCESS  read-write
    STATUS  mandatory
    DESCRIPTION
           "Logical peer address.
            
            Modification of this value is not allowed.
            The SNMPv2 MAX-ACCESS is read-(only-)create."
    ::= { isarIccPhyPortConnEntry  7 }

isarIccPhyPortConnTrace OBJECT-TYPE
    SYNTAX  INTEGER {
                      enabled(1),
                      disabled(2)
            }
    ACCESS  read-write
    STATUS  mandatory
    DESCRIPTION
           "Enable or disable D-channel messages tracing .
            
            Modification of this value is always allowed.
            The SNMPv2 MAX-ACCESS is read-create."
    DEFVAL  { disabled }
    ::= { isarIccPhyPortConnEntry  8 }


isarIccPhyPortConnDataLinkSupervision OBJECT-TYPE
    SYNTAX  INTEGER {
                      enabled(1),
                      disabled(2)
            }
    ACCESS  read-write
    STATUS  mandatory
    DESCRIPTION
           "This field is used to enable or disable the datalink 
            supervision.
            When enabled, the broadband connection is released when the
            datalink goes unexpectedly down.  When disabled, the datalink
            layer isn't checked and the broadband connection stays up till
            the remote S0 connection is released.
            
            Modification of this value is always allowed.
            The SNMPv2 MAX-ACCESS is read-create."
    DEFVAL  { disabled }
    ::= { isarIccPhyPortConnEntry  9 }

-- Physical port connection statistics table

isarIccPhyPortConnStatsTable OBJECT-TYPE
    SYNTAX  SEQUENCE OF IsarIccPhyPortConnStatsEntry
    ACCESS  not-accessible
    STATUS  mandatory
    DESCRIPTION
           "Statistics concerning a physical port connections.
            Rows are created/deleted by IAD4700 at the moment of row 
            creation/deletion in isarIccPhyPortConnTable."
    ::= { isarIccPhyPortConnObjects  4 }

isarIccPhyPortConnStatsEntry OBJECT-TYPE
    SYNTAX  IsarIccPhyPortConnStatsEntry
    ACCESS  not-accessible
    STATUS  mandatory
    DESCRIPTION
           "One row in the isarIccPhyPortConnStatsTable."
    INDEX   { isarIccPhyPortConnIndex }
    ::= { isarIccPhyPortConnStatsTable  1 }


IsarIccPhyPortConnStatsEntry ::=
    SEQUENCE { 
      isarIccPhyPortConnStatsBusyMap
        INTEGER,
        
      isarIccPhyPortConnStatsAttempts
        Counter

    }


isarIccPhyPortConnStatsBusyMap OBJECT-TYPE
    SYNTAX  INTEGER
    ACCESS  read-only
    STATUS  mandatory
    DESCRIPTION
           "Current BUSY B-channel map."
    ::= { isarIccPhyPortConnStatsEntry  2 }

isarIccPhyPortConnStatsAttempts OBJECT-TYPE
    SYNTAX  Counter
    ACCESS  read-only
    STATUS  mandatory
    DESCRIPTION
           "Number of B-channel attempts."
    ::= { isarIccPhyPortConnStatsEntry  3 }



-- Physical port connection remote node usage table

isarIccPhyPortConnRemNodeTable OBJECT-TYPE
    SYNTAX  SEQUENCE OF IsarIccPhyPortConnRemNodeEntry
    ACCESS  not-accessible
    STATUS  mandatory
    DESCRIPTION
           "This table gives an list of all physical port connections that
            have a link to a certain remote node.
            
            Rows are created/deleted by IAD4700 at the moment that rows
            are created/deleted in the isarIPhyPortConnTable.
            
            It gives the management stations an easy way to find out which
            remote nodes are linked with a physical port connection."
    ::= { isarIccPhyPortConnObjects  5 }

isarIccPhyPortConnRemNodeEntry OBJECT-TYPE
    SYNTAX  IsarIccPhyPortConnRemNodeEntry
    ACCESS  not-accessible
    STATUS  mandatory
    DESCRIPTION
           "One row in the isarIccPhyPortConnRemNodeTable."
    INDEX   { isarIccRemNodeIndex, isarIccPhyPortConnRemNodeIndex }
    ::= { isarIccPhyPortConnRemNodeTable  1 }


IsarIccPhyPortConnRemNodeEntry ::=
    SEQUENCE { 
      isarIccPhyPortConnRemNodeIndex
        INTEGER
        
    }


isarIccPhyPortConnRemNodeIndex OBJECT-TYPE
    SYNTAX  INTEGER (2..2147483647)
    ACCESS  read-only
    STATUS  mandatory
    DESCRIPTION
           "Index of a physical port connection that has a link to the 
            remote node identified via isarIccRemNodeIndex."
    ::= { isarIccPhyPortConnRemNodeEntry  1 }




-- TRAPS
isarIccTraps OBJECT IDENTIFIER   ::= { isarIcccMIBObjects 12 }


isarIccNbLogPortStatusChange TRAP-TYPE
    ENTERPRISE  isarIccTraps
    VARIABLES   { isarIccNbLogPortIndex, 
                  isarIccNbLogPortAdminStatus,
                  isarIccNbLogPortAdminStatus,
                  isarIccNbLogPortOperStatus,
                  isarIccNbLogPortOperStatus
                 }
    DESCRIPTION
           "An indication that the operational status of this NB log
            port has changed.
            A status change is given when :
            1. isarIccNbLogPortAdminStatus is 'up' and 
               isarIccNbLogPortOperStatus is going from 'dormant' or 'up'
               to 'lowerLayerDown' = set alarm
            2. when isarIccNbLogPortOperStatus is going from 'lowerLayerDown'
               to 'up' = clear alarm 
            3. when isarIccNbLogPortOperStatus is going from 'lowerLayerDown'
               to 'down' = clear alarm (isarIccNbLogPortAdminStatus = down)
               
            The first isarIccNbLogPortOperStatus is the previous state,
            the second isarIccNbLogPortOperStatus is the new state."
    ::= 1

isarIccRemNodeStatusChange TRAP-TYPE
    ENTERPRISE  isarIccTraps
    VARIABLES   { isarIccRemNodeIndex,
                  isarIccRemNodeName,
                  isarIccRemNodeAdminStatus,
                  isarIccRemNodeAdminStatus,
                  isarIccRemNodeOperStatus,
                  isarIccRemNodeOperStatus
                 }
    DESCRIPTION
           "An indication that the operational status of this remote
            node has changed.
            A status change is given when :
            1. isarIccRemNodeAdminStatus is 'up' and 
               isarIccRemNodeOperStatus is going from 'dormant' or 'up'
               to 'lowerLayerDown' = set alarm
            2. when isarIccRemNodeOperStatus is going from 'lowerLayerDown'
               to 'up' = clear alarm 
            3. when isarIccRemNodeOperStatus is going from 'lowerLayerDown'
               to 'down' = clear alarm (isarIccNbLogPortAdminStatus = down)
               
            The first isarIccRemNodeOperStatus is the previous state,
            the second isarIccRemNodeOperStatus is the new state."
    ::= 2

isarIccDss2StatusChange TRAP-TYPE
    ENTERPRISE  isarIccTraps
    VARIABLES   { isarIccGenDss2OperState,
                  isarIccGenDss2OperState
                 }
    DESCRIPTION
           "An indication that the operational status of the DSS2 
            signalling channel has changed.
            A status change is given when :
            1. isarIccGenDss2OperState is going from 'up'
               to 'lowerLayerDown' = set alarm
            2. when isarIccGenDss2OperState is going from 'lowerLayerDown'
               to 'up' = clear alarm 
               
            The first isarIccGenDss2OperState is the previous state,
            the second isarIccGenDss2OperState is the new state."
    ::= 3


--
-- ISAR cccMIBObjects : end
--  




-- This file cannot be used to create SNMP agent.
-- The file isarOneFile.my has to be used to create the agent.



-- isarIsdslMIBObjects OBJECT IDENTIFIER ::= { isar  36 }

--
-- ISAR sdslMIBObjects : begin
--  


-- --------------------------------------------------------------
--                 TLM SDSL central PPTP Table
-- --------------------------------------------------------------
 
-- This managed entity represents the extension for the PPTP at
-- the SDSL central interface. It includes additional attributes to
-- configure the SDSL link.
--
 
isarIsdslSdcPPTPTable OBJECT-TYPE
    SYNTAX  SEQUENCE OF IsarIsdslSdcPPTPEntry
    ACCESS  not-accessible
    STATUS  mandatory
    DESCRIPTION
           "The physical path termination point table for ADSL C. "
    ::= { isarIsdslMIBObjects 1 }
 
isarIsdslSdcPPTPEntry OBJECT-TYPE
    SYNTAX  IsarIsdslSdcPPTPEntry
    ACCESS  not-accessible
    STATUS  mandatory
    DESCRIPTION
           "An entry describing a termination point in the PPTP table.
            The ifIndex is the ifIndex of the port."
    INDEX  { ifIndex }
    ::= { isarIsdslSdcPPTPTable 1 }
 
IsarIsdslSdcPPTPEntry ::=
    SEQUENCE { 
      isarIsdslSdcRateCfg
        INTEGER,

      isarIsdslSdcXdslServiceTypeCfg
        INTEGER,

      isarIsdslSdcRate
        INTEGER,

      isarIsdslSdcMarginDn
        INTEGER,

      isarIsdslSdcMarginUp
        INTEGER,

      isarIsdslSdcAttenuationDn
        INTEGER,

      isarIsdslSdcAttenuationUp
        INTEGER,              

      isarIsdslSdcConnectMode
        INTEGER,

      isarIsdslSdcTimingRecovery
        INTEGER,

      isarIsdslSdcOperationMode
        INTEGER,

      isarIsdslSdcLoopMode
        INTEGER,

      isarIsdslSdcOperatingState
        INTEGER,

      isarIsdslSdcLineStatus
        INTEGER,

      isarIsdslSdcTimeElapsed
        INTEGER,

      isarIsdslSdcValidIntervals
        INTEGER,

      isarIsdslSdcFixBitStatus
        INTEGER,

      isarIsdslSdcDSPVersion
        INTEGER,

      isarIsdslSdcPowerScaleAdj
        INTEGER,

      isarIsdslSdcXmitPower
        INTEGER,

      isarIsdslSdcTipRingStatus
        INTEGER,

      isarIsdslSdcPam16Latency
        INTEGER,

      isarIsdslSdcPam16CountryCode
        INTEGER,

      isarIsdslSdcPam16ProviderCode
        INTEGER,

      isarIsdslSdcPam16VendorData1
        INTEGER,

      isarIsdslSdcPam16VendorData2
        INTEGER,

      isarIsdslSdcPam16RemoteCountryCode
        INTEGER,

      isarIsdslSdcPam16RemoteProviderCode
        INTEGER,

      isarIsdslSdcPam16RemoteVendorData1
        INTEGER,

      isarIsdslSdcPam16RemoteVendorData2
        INTEGER,

      isarIsdslSdcPam16RemoteShdslVersion
        INTEGER,

      isarIsdslSdcPam16RemoteEncoderA
        INTEGER,

      isarIsdslSdcPam16RemoteEncoderB
        INTEGER,

      isarIsdslSdcPam16RemoteStuffBitStatus
        INTEGER,

      isarIsdslSdcPam16MinLineRate
        INTEGER,

      isarIsdslSdcPam16MaxLineRate
        INTEGER,

      isarIsdslSdcPam16CurrentLineRate
        INTEGER,

      isarIsdslSdcPam16Region
        INTEGER

    }
 
isarIsdslSdcRateCfg OBJECT-TYPE
    SYNTAX  INTEGER {
                      rate144Kbps(1),     -- not supported when using NTR
                      rate160Kbps(2),     -- not supported when using NTR
                      rate192Kbps(3),     -- not supported when using NTR
                      rate208Kbps(4),
                      rate224Kbps(5),     -- not supported when using NTR
                      rate272Kbps(6),     -- not supported when using NTR
                      rate320Kbps(7),     -- not supported when using NTR
                      rate400Kbps(8),
                      rate416Kbps(9),     -- not supported when using NTR
                      rate528Kbps(10),    -- not supported when using NTR
                      rate784Kbps(11),
                      rate1040Kbps(12),   -- not supported when using NTR
                      rate1168Kbps(13),
                      rate1552Kbps(14),
                      rate1568Kbps(15),   -- not supported when using NTR
                      rate2320Kbps(16)
            }
    ACCESS  read-write
    STATUS  mandatory
    DESCRIPTION
           "The desired line rate.   
     	    Note: this field is only applicable when 2B1Q line coding is
     	    selected."
    ::= { isarIsdslSdcPPTPEntry 1 }

isarIsdslSdcXdslServiceTypeCfg OBJECT-TYPE
    SYNTAX  INTEGER {
                      dlcc2B1Q(1),
                      dlccPAM16(2)
            }
    ACCESS  read-write
    STATUS  mandatory
    DESCRIPTION
           "The configured service mode (line coding) for SDSL line. "
    ::= { isarIsdslSdcPPTPEntry 2 }
 
isarIsdslSdcRate OBJECT-TYPE
    SYNTAX  INTEGER {
                      rate144Kbps(1),
                      rate160Kbps(2),
                      rate192Kbps(3),
                      rate208Kbps(4),
                      rate224Kbps(5),
                      rate272Kbps(6),
                      rate320Kbps(7),
                      rate400Kbps(8),
                      rate416Kbps(9),
                      rate528Kbps(10),
                      rate784Kbps(11),
                      rate1040Kbps(12),
                      rate1168Kbps(13),
                      rate1552Kbps(14),
                      rate1568Kbps(15),
                      rate2320Kbps(16)
            }
    ACCESS  read-only
    STATUS  mandatory
    DESCRIPTION
           "The current downstream line rate.
     	    Note: this field is only applicable when 2B1Q line coding is
     	    selected."
    ::= { isarIsdslSdcPPTPEntry 3 }
 
isarIsdslSdcMarginDn OBJECT-TYPE
    SYNTAX  INTEGER (0..255)
    ACCESS  read-only
    STATUS  mandatory
    DESCRIPTION
           "The current downstream margin in units of dB."
    ::= { isarIsdslSdcPPTPEntry 4 }
 
isarIsdslSdcMarginUp OBJECT-TYPE
    SYNTAX  INTEGER (0..255)
    ACCESS  read-only
    STATUS  mandatory
    DESCRIPTION
           "The current upstream margin in units of dB."
    ::= { isarIsdslSdcPPTPEntry 5 }
 
isarIsdslSdcAttenuationDn OBJECT-TYPE
    SYNTAX  INTEGER (0..255)
    ACCESS  read-only
    STATUS  mandatory
    DESCRIPTION
           "The current downstream attenuation in units of dB."
    ::= { isarIsdslSdcPPTPEntry 6 }
 
isarIsdslSdcAttenuationUp OBJECT-TYPE
    SYNTAX  INTEGER (0..255)
    ACCESS  read-only
    STATUS  mandatory
    DESCRIPTION
           "The current upstream attenuation in units of dB."
    ::= { isarIsdslSdcPPTPEntry 7 }
 
isarIsdslSdcConnectMode OBJECT-TYPE
    SYNTAX  INTEGER {
                      basic(1),
                      rateNegotiation(2),
                      copperMountain(3),
                      flowPoint(4)    
            }
    ACCESS  read-write
    STATUS  mandatory
    DESCRIPTION
           "This variable indicates the operating mode in
            conjunction with other equipment.  
     	    Note: this field is only applicable when 2B1Q line coding is
     	    selected. "
    DEFVAL  { flowPoint }
    ::= { isarIsdslSdcPPTPEntry 8 }

isarIsdslSdcTimingRecovery OBJECT-TYPE
    SYNTAX  INTEGER {
                      enabled(1),
                      disabled(2)
            }
    ACCESS  read-only
    STATUS  mandatory
    DESCRIPTION
           "This variable indicates if network timing recovery
            should be enabled."    
    DEFVAL  { enabled }
    ::= { isarIsdslSdcPPTPEntry 9 }

isarIsdslSdcOperationMode OBJECT-TYPE
    SYNTAX  INTEGER {
                      co(1),
                      cp(2)
            }
    ACCESS  read-write
    STATUS  mandatory
    DESCRIPTION
           "This variable indicates which operation mode should be used."    
    DEFVAL  { cp }
    ::= { isarIsdslSdcPPTPEntry 10 }

isarIsdslSdcLoopMode OBJECT-TYPE
    SYNTAX  INTEGER {
                      noLoop(1),
                      coreLoop(2),
                      analogLoop(3),
                      digitalLoop(4)
            }
    ACCESS  read-write
    STATUS  mandatory
    DESCRIPTION
           "This variable indicates which loop mode should be used.
              coreLoop creates a loopback in the downstream direction, 
              analogLoop and digitalLoop create a loopback in the upstream
              direction
            For test purposes only."    
    DEFVAL  { noLoop }
    ::= { isarIsdslSdcPPTPEntry 11 }

isarIsdslSdcOperatingState OBJECT-TYPE
    SYNTAX  INTEGER {
                      idleMode(1),
                      trainingMode(2),
                      testMode(3),
                      dataMode(4)
            }
    ACCESS  read-only
    STATUS  mandatory
    DESCRIPTION
           "This variable indicates the operating state."    
    ::= { isarIsdslSdcPPTPEntry 12 }

isarIsdslSdcLineStatus OBJECT-TYPE
    SYNTAX  INTEGER (1..2047)
    ACCESS  read-only
    STATUS  mandatory
    DESCRIPTION
           "This variable indicates the Line Status of the
            interface.  It contains failure, received 'alarm' 
            and transmitted 'alarms' information.

            The isarIsdslSdcLineStatus is a bit map represented as a
            sum, therefore, it can represent multiple failures
            (alarms) simultaneously.

            sdslNoAlarm must be set if and only if no other
            flag is set.

            The various bit positions are:
           1    sdslNoAlarm           No alarm present
           2    sdslRAI               Remote Alarm Indication
           4    sdslDyingGasp         Power failure from CP side
           8    sdslFramerSyncStatus  Framer Out of sync
          16    sdslWatchDogBarked    HW Watchdog expired
          32    sdslOtherFailure      any line status not defined here
          64    sdslActivating        Waiting for activation event
         128    sdslMarginTooLow      Signal to noice is too low
         256    sdslLCD               Loss of Cell Deliniation
         512    sdslEOCSoftRestart    Restart caused by an EOC command
        1024    sdslEOCLoopCommand    Loopback caused by an EOC command."
       
    ::= { isarIsdslSdcPPTPEntry 13 }

isarIsdslSdcTimeElapsed OBJECT-TYPE
    SYNTAX  INTEGER (1..900)
    ACCESS  read-only
    STATUS  mandatory
    DESCRIPTION
           "The number of seconds, including partial
            seconds, that have elapsed since the beginning of
            the current error-measurement period."
    ::= { isarIsdslSdcPPTPEntry 14 }

isarIsdslSdcValidIntervals OBJECT-TYPE
    SYNTAX  INTEGER (0..96)
    ACCESS  read-only
    STATUS  mandatory
    DESCRIPTION
           "The number of previous intervals for which valid
            data has been stored.  A SDSL device must support
            at least n intervals.
            The minimum value of n is 4.
            The default of n is 32.
            The maximum value of n is 96.
            The value of this object will be n unless
            the device was brought online within the last
            (nx15) minutes, in which case the value will be the
            number of complete 15 minute intervals the device has
            been online.
            IAD4700 : the maximum of n will be used."
    ::= { isarIsdslSdcPPTPEntry 15 }

isarIsdslSdcFixBitStatus OBJECT-TYPE
    SYNTAX  INTEGER {
                      enabled(1),
                      disabled(2)
            }
    ACCESS  read-only
    STATUS  mandatory
    DESCRIPTION
           "This variable indicates the status of the fix-bit feature.
            Note: this field is only applicable when 2B1Q line coding is
  	    selected. "
    ::= { isarIsdslSdcPPTPEntry 16 }

isarIsdslSdcDSPVersion OBJECT-TYPE
    SYNTAX  INTEGER (0..255)
    ACCESS  read-only
    STATUS  mandatory
    DESCRIPTION
           "This variable indicates the version of the DSP Framer."
    ::= { isarIsdslSdcPPTPEntry 17 }

isarIsdslSdcPowerScaleAdj OBJECT-TYPE
    SYNTAX  INTEGER (0..65535)
    ACCESS  read-write
    STATUS  mandatory
    DESCRIPTION
           "This variable indicates the power scale adjustment."
    ::= { isarIsdslSdcPPTPEntry 18 }

isarIsdslSdcXmitPower OBJECT-TYPE
    SYNTAX  INTEGER (0..65535)
    ACCESS  read-only
    STATUS  mandatory
    DESCRIPTION
           "This variable indicates the nominal transmitted power."
    ::= { isarIsdslSdcPPTPEntry 19 }

isarIsdslSdcTipRingStatus OBJECT-TYPE
    SYNTAX  INTEGER {
                      normal(1),
                      reversed(2)
            }
    ACCESS  read-only
    STATUS  mandatory
    DESCRIPTION
           "This variable indicates the tip-ring status."
    ::= { isarIsdslSdcPPTPEntry 20 }

isarIsdslSdcPam16Latency OBJECT-TYPE
    SYNTAX  INTEGER {
                      default(1),
                      deltaLatency20(2),
                      deltaLatency40(3),
                      deltaLatency60(4),
                      deltaLatency80(5)	
            }
    ACCESS  read-write
    STATUS  mandatory
    DESCRIPTION
           "This variable indicates the delay of the datapath (cell delay).
            Note: this field is only applicable when PAM16 line coding is 
            selected. "
    ::= { isarIsdslSdcPPTPEntry 21 }

isarIsdslSdcPam16CountryCode OBJECT-TYPE
    SYNTAX  INTEGER
    ACCESS  read-write
    STATUS  mandatory
    DESCRIPTION
           "This variable indicates the country code of the local node.
            Note: this field is only applicable when PAM16 line coding is 
            selected. "
    ::= { isarIsdslSdcPPTPEntry 22 }

isarIsdslSdcPam16ProviderCode OBJECT-TYPE
    SYNTAX  INTEGER
    ACCESS  read-write
    STATUS  mandatory
    DESCRIPTION
           "This variable indicates the provider code of the local node.
            Note: this field is only applicable when PAM16 line coding is 
            selected. "
    ::= { isarIsdslSdcPPTPEntry 23 }

isarIsdslSdcPam16VendorData1 OBJECT-TYPE
    SYNTAX  INTEGER
    ACCESS  read-write
    STATUS  mandatory
    DESCRIPTION
           "This variable indicates vendor data of the local node.
            Note: this field is only applicable when PAM16 line coding is 
            selected. "
    ::= { isarIsdslSdcPPTPEntry 24 }

isarIsdslSdcPam16VendorData2 OBJECT-TYPE
    SYNTAX  INTEGER
    ACCESS  read-write
    STATUS  mandatory
    DESCRIPTION
           "This variable indicates vendor data of the local node.
            Note: this field is only applicable when PAM16 line coding is 
            selected. "
    ::= { isarIsdslSdcPPTPEntry 25 }

isarIsdslSdcPam16RemoteCountryCode OBJECT-TYPE
    SYNTAX  INTEGER
    ACCESS  read-only
    STATUS  mandatory
    DESCRIPTION
           "This variable indicates the country code of the remote node.
            Note: this field is only applicable when PAM16 line coding is 
            selected. "
    ::= { isarIsdslSdcPPTPEntry 26 }

isarIsdslSdcPam16RemoteProviderCode OBJECT-TYPE
    SYNTAX  INTEGER
    ACCESS  read-only
    STATUS  mandatory
    DESCRIPTION
           "This variable indicates the provider code of the remote node.
            Note: this field is only applicable when PAM16 line coding is 
            selected. "
    ::= { isarIsdslSdcPPTPEntry 27 }

isarIsdslSdcPam16RemoteVendorData1 OBJECT-TYPE
    SYNTAX  INTEGER
    ACCESS  read-only
    STATUS  mandatory
    DESCRIPTION
           "This variable indicates vendor data of the remote node.
            Note: this field is only applicable when PAM16 line coding is 
            selected. "
    ::= { isarIsdslSdcPPTPEntry 28 }

isarIsdslSdcPam16RemoteVendorData2 OBJECT-TYPE
    SYNTAX  INTEGER
    ACCESS  read-only
    STATUS  mandatory
    DESCRIPTION
           "This variable indicates vendor data of the remote node.
            Note: this field is only applicable when PAM16 line coding is 
            selected. "
    ::= { isarIsdslSdcPPTPEntry 29 }

isarIsdslSdcPam16RemoteShdslVersion OBJECT-TYPE
    SYNTAX  INTEGER (0..255)
    ACCESS  read-only
    STATUS  mandatory
    DESCRIPTION
           "This variable indicates the SHDSL version of the remote node.
            Note: this field is only applicable when PAM16 line coding is 
            selected. "
    ::= { isarIsdslSdcPPTPEntry 30 }

isarIsdslSdcPam16RemoteEncoderA OBJECT-TYPE
    SYNTAX  INTEGER
    ACCESS  read-only
    STATUS  mandatory
    DESCRIPTION
           "This variable indicates the encoder coefficient A used at the 
            remote node.
            Note: this field is only applicable when PAM16 line coding is 
            selected. "
    ::= { isarIsdslSdcPPTPEntry 31 }

isarIsdslSdcPam16RemoteEncoderB OBJECT-TYPE
    SYNTAX  INTEGER
    ACCESS  read-only
    STATUS  mandatory
    DESCRIPTION
           "This variable indicates the encoder coefficient B used at the
            remote node.
            Note: this field is only applicable when PAM16 line coding is 
            selected. "
    ::= { isarIsdslSdcPPTPEntry 32 }
      
isarIsdslSdcPam16RemoteStuffBitStatus OBJECT-TYPE
    SYNTAX  INTEGER (0..15)
    ACCESS  read-only
    STATUS  mandatory
    DESCRIPTION
           "This variable indicates the stuff bits at the end of a frame.
            Note: this field is only applicable when PAM16 line coding is 
            selected. "
    ::= { isarIsdslSdcPPTPEntry 33 }

isarIsdslSdcPam16MinLineRate OBJECT-TYPE
    SYNTAX  INTEGER (200..2320)
    ACCESS  read-write
    STATUS  mandatory
    DESCRIPTION
           "This variable indicates the minimum desired line rate.
            The current data rate will be a value between 
            isarIsdslSdcPam16MinLineRate and isarIsdslSdcPam16MaxLineRate
            and can be found in isarIsdslSdcPam16CurrentLineRate.
            A 'fixed data rate' is achieved when setting 
            isarIsdslSdcPam16MinLineRate = isarIsdslSdcPam16MaxLineRate.
            Note: this field is only applicable when PAM16 line coding is 
            selected. "
    ::= { isarIsdslSdcPPTPEntry 34 }

isarIsdslSdcPam16MaxLineRate OBJECT-TYPE
    SYNTAX  INTEGER (200..2320)
    ACCESS  read-write
    STATUS  mandatory
    DESCRIPTION
           "This variable indicates the maximum desired line rate.
            The current data rate will be a value between 
            isarIsdslSdcPam16MinLineRate and isarIsdslSdcPam16MaxLineRate
            and can be found in isarIsdslSdcPam16CurrentLineRate.
            A 'fixed data rate' is achieved when setting 
            isarIsdslSdcPam16MinLineRate = isarIsdslSdcPam16MaxLineRate.
            Note: this field is only applicable when PAM16 line coding is 
            selected. "
    ::= { isarIsdslSdcPPTPEntry 35 }

isarIsdslSdcPam16CurrentLineRate OBJECT-TYPE
    SYNTAX  INTEGER (200..2320)
    ACCESS  read-only
    STATUS  mandatory
    DESCRIPTION
           "The current line rate.
            Note: this field is only applicable when PAM16 line coding is 
            selected."
    ::= { isarIsdslSdcPPTPEntry 36 }

isarIsdslSdcPam16Region OBJECT-TYPE
    SYNTAX  INTEGER {
                      europe(1),
                      northAmerica(2)
            }
    ACCESS  read-write
    STATUS  mandatory
    DESCRIPTION
           "Region where the IAD is used.
            Via this field the Power spectrum Density is selected.
            Refer to annex A and B of G.991.2.
            Note: this field is only applicable when PAM16 line coding is 
            selected. "
    DEFVAL  { europe }
    ::= { isarIsdslSdcPPTPEntry 37 }


--
-- the SDSL Near End Current Table

-- The SDSL Near End current table contains various statistics
-- being collected for the current 15 minute interval.

isarIsdslNearEndCurrentTable OBJECT-TYPE
    SYNTAX  SEQUENCE OF IsarIsdslNearEndCurrentEntry
    ACCESS  not-accessible
    STATUS  mandatory
    DESCRIPTION
           "The SDSL Near End Current table."
    ::= { isarIsdslMIBObjects 2 }

isarIsdslNearEndCurrentEntry OBJECT-TYPE
    SYNTAX  IsarIsdslNearEndCurrentEntry
    ACCESS  not-accessible
    STATUS  mandatory
    DESCRIPTION
           "An entry in the SDSL Near End Current table."
    INDEX   { ifIndex }
    ::= { isarIsdslNearEndCurrentTable  1 }

IsarIsdslNearEndCurrentEntry ::=
    SEQUENCE {   

      isarIsdslNearEndCurrentESs
        Gauge,

      isarIsdslNearEndCurrentSESs
        Gauge,

      isarIsdslNearEndCurrentUASs
        Gauge,

      isarIsdslNearEndCurrentCVs
        Gauge
    }

isarIsdslNearEndCurrentESs OBJECT-TYPE
    SYNTAX  Gauge
    ACCESS  read-only
    STATUS  mandatory
    DESCRIPTION
           "The counter associated with the number of Near End
            Errored Seconds encountered by the SDSL Interface
            in the current 15 minute interval."
    ::= { isarIsdslNearEndCurrentEntry  1 }

isarIsdslNearEndCurrentSESs OBJECT-TYPE
    SYNTAX  Gauge
    ACCESS  read-only
    STATUS  mandatory
    DESCRIPTION
           "The counter associated with the number of Near End
            Severely Errored Seconds encountered by the SDSL Interface
            in the current 15 minute interval."
    ::= { isarIsdslNearEndCurrentEntry  2 }

isarIsdslNearEndCurrentUASs OBJECT-TYPE
    SYNTAX  Gauge
    ACCESS  read-only
    STATUS  mandatory
    DESCRIPTION
           "The counter associated with the number of
            UA Seconds encountered by the SDSL Interface 
            in the current 15 minute interval."
    ::= { isarIsdslNearEndCurrentEntry  3 }

isarIsdslNearEndCurrentCVs OBJECT-TYPE
    SYNTAX  Gauge
    ACCESS  read-only
    STATUS  mandatory
    DESCRIPTION
           "The counter associated with the number of Coding
            Violations encountered by the SDSL Interface 
            in the current 15 minute interval."
    ::= { isarIsdslNearEndCurrentEntry  4 }



-- the SDSL Interface Interval Table

-- The SDSL Interface Interval Table
-- contains various statistics
-- collected by each system over a maximum
-- of the previous 24 hours of
-- operation.  The past 24 hours may be broken into 96
-- completed 15 minute intervals.
-- A system is required to store at
-- least 4 completed 15 minute interval.
-- The default value is 32 intervals.
-- IAD4700 : the maximum of n will be used.

isarIsdslNearEndIntervalTable OBJECT-TYPE
    SYNTAX  SEQUENCE OF IsarIsdslNearEndIntervalEntry
    ACCESS  not-accessible
    STATUS  mandatory
    DESCRIPTION
           "The SDSL Interface NearEndInterval table."
    ::= { isarIsdslMIBObjects 3  }

isarIsdslNearEndIntervalEntry OBJECT-TYPE
    SYNTAX  IsarIsdslNearEndIntervalEntry
    ACCESS  not-accessible
    STATUS  mandatory
    DESCRIPTION
           "An entry in the SDSL Interface Near End Interval table."
    INDEX   { ifIndex,  isarIsdslNearEndIntervalNumber }
    ::= { isarIsdslNearEndIntervalTable  1 }

IsarIsdslNearEndIntervalEntry ::=
    SEQUENCE {
      isarIsdslNearEndIntervalNumber
        INTEGER,

      isarIsdslNearEndIntervalESs
        Gauge,

      isarIsdslNearEndIntervalSESs
        Gauge,

      isarIsdslNearEndIntervalUASs
        Gauge,

      isarIsdslNearEndIntervalCVs
        Gauge,

      isarIsdslNearEndIntervalTimeStamp
        TimeTicks
    }

isarIsdslNearEndIntervalNumber OBJECT-TYPE
    SYNTAX  INTEGER (1..96)
    ACCESS  not-accessible
    STATUS  mandatory
    DESCRIPTION
           "A number between 1 and 96, which identifies the
            interval for which the set of statistics is available.
            The interval identified by 1 is the most recently
            completed 15 minute interval,
            and the interval identified by N is the interval immediately
            preceding the one identified by N-1.
            IAD4700 : the maximum of n will be used."
    ::= { isarIsdslNearEndIntervalEntry  1 }

isarIsdslNearEndIntervalESs OBJECT-TYPE
    SYNTAX  Gauge
    ACCESS  read-only
    STATUS  mandatory
    DESCRIPTION
           "The counter associated with the number of
            Errored Seconds encountered
            by the SDSL Interface in a
            particular 15-minute interval
            in the past 24 hours."
    ::= { isarIsdslNearEndIntervalEntry  2 }

isarIsdslNearEndIntervalSESs OBJECT-TYPE
    SYNTAX  Gauge
    ACCESS  read-only
    STATUS  mandatory
    DESCRIPTION
           "The counter associated with the number of
            Severely Errored Seconds
            encountered by the SDSL Interface in a
            particular 15-minute interval
            in the past 24 hours."
    ::= { isarIsdslNearEndIntervalEntry  3 }

isarIsdslNearEndIntervalUASs OBJECT-TYPE
    SYNTAX  Gauge
    ACCESS  read-only
    STATUS  mandatory
    DESCRIPTION
           "The counter associated with the number of
            UA Seconds
            encountered by the SDSL Interface in a
            particular 15-minute interval
            in the past 24 hours."
    ::= { isarIsdslNearEndIntervalEntry  4 }

isarIsdslNearEndIntervalCVs OBJECT-TYPE
    SYNTAX  Gauge
    ACCESS  read-only
    STATUS  mandatory
    DESCRIPTION
           "The counter associated with the number of Coding
            Violations encountered by the
            SDSL Interface in a particular 15-minute interval
            in the past 24 hours."
    ::= { isarIsdslNearEndIntervalEntry  5 }

isarIsdslNearEndIntervalTimeStamp OBJECT-TYPE
    SYNTAX  TimeTicks
    ACCESS  read-only
    STATUS  mandatory
    DESCRIPTION
           "Start of interval."
    ::= { isarIsdslNearEndIntervalEntry  6 }


--
-- the SDSL Far End Current Table

-- The SDSL Far End current table contains various statistics
-- being collected for the current 15 minute interval.

isarIsdslFarEndCurrentTable OBJECT-TYPE
    SYNTAX  SEQUENCE OF IsarIsdslFarEndCurrentEntry
    ACCESS  not-accessible
    STATUS  mandatory
    DESCRIPTION
           "The SDSL Far End Current table."
    ::= { isarIsdslMIBObjects 4 }

isarIsdslFarEndCurrentEntry OBJECT-TYPE
    SYNTAX  IsarIsdslFarEndCurrentEntry
    ACCESS  not-accessible
    STATUS  mandatory
    DESCRIPTION
           "An entry in the SDSL Far End Current table."
    INDEX   { ifIndex }
    ::= { isarIsdslFarEndCurrentTable  1 }

IsarIsdslFarEndCurrentEntry ::=
    SEQUENCE {   

      isarIsdslFarEndCurrentESs
        Gauge,

      isarIsdslFarEndCurrentSESs
        Gauge,

      isarIsdslFarEndCurrentUASs
        Gauge,

      isarIsdslFarEndCurrentCVs
        Gauge
    }

isarIsdslFarEndCurrentESs OBJECT-TYPE
    SYNTAX  Gauge
    ACCESS  read-only
    STATUS  mandatory
    DESCRIPTION
           "The counter associated with the number of Far End
            Errored Seconds encountered by the SDSL Interface
            in the current 15 minute interval."
    ::= { isarIsdslFarEndCurrentEntry  1 }

isarIsdslFarEndCurrentSESs OBJECT-TYPE
    SYNTAX  Gauge
    ACCESS  read-only
    STATUS  mandatory
    DESCRIPTION
           "The counter associated with the number of Far End
            Severely Errored Seconds encountered by the SDSL Interface
            in the current 15 minute interval."
    ::= { isarIsdslFarEndCurrentEntry  2 }

isarIsdslFarEndCurrentUASs OBJECT-TYPE
    SYNTAX  Gauge
    ACCESS  read-only
    STATUS  mandatory
    DESCRIPTION
           "The counter associated with the number of
            UA Seconds encountered by the SDSL Interface 
            in the current 15 minute interval."
    ::= { isarIsdslFarEndCurrentEntry  3 }

isarIsdslFarEndCurrentCVs OBJECT-TYPE
    SYNTAX  Gauge
    ACCESS  read-only
    STATUS  mandatory
    DESCRIPTION
           "The counter associated with the number of Coding
            Violations encountered by the SDSL Interface 
            in the current 15 minute interval."
    ::= { isarIsdslFarEndCurrentEntry  4 }



-- the SDSL Far End Interval Table

-- The SDSL Far End Interval Table
-- contains various statistics
-- collected by each system over a maximum
-- of the previous 24 hours of
-- operation.  The past 24 hours may be broken into 96
-- completed 15 minute intervals.
-- A system is required to store at
-- least 4 completed 15 minute interval.
-- The default value is 32 intervals.
-- IAD4700 : the maximum of n will be used.

isarIsdslFarEndIntervalTable OBJECT-TYPE
    SYNTAX  SEQUENCE OF IsarIsdslFarEndIntervalEntry
    ACCESS  not-accessible
    STATUS  mandatory
    DESCRIPTION
           "The SDSL Interface Far End Interval table."
    ::= { isarIsdslMIBObjects 5  }

isarIsdslFarEndIntervalEntry OBJECT-TYPE
    SYNTAX  IsarIsdslFarEndIntervalEntry
    ACCESS  not-accessible
    STATUS  mandatory
    DESCRIPTION
           "An entry in the SDSL Interface FarEndInterval table."
    INDEX   { ifIndex,  isarIsdslFarEndIntervalNumber }
    ::= { isarIsdslFarEndIntervalTable  1 }

IsarIsdslFarEndIntervalEntry ::=
    SEQUENCE {
      isarIsdslFarEndIntervalNumber
        INTEGER,

      isarIsdslFarEndIntervalESs
        Gauge,

      isarIsdslFarEndIntervalSESs
        Gauge,

      isarIsdslFarEndIntervalUASs
        Gauge,

      isarIsdslFarEndIntervalCVs
        Gauge,

      isarIsdslFarEndIntervalTimeStamp
        TimeTicks
    }

isarIsdslFarEndIntervalNumber OBJECT-TYPE
    SYNTAX  INTEGER (1..96)
    ACCESS  not-accessible
    STATUS  mandatory
    DESCRIPTION
           "A number between 1 and 96, which identifies the
            interval for which the set of statistics is available.
            The interval identified by 1 is the most recently
            completed 15 minute interval,
            and the interval identified by N is the interval immediately
            preceding the one identified by N-1.
            IAD4700 : the maximum of n will be used."
    ::= { isarIsdslFarEndIntervalEntry  1 }

isarIsdslFarEndIntervalESs OBJECT-TYPE
    SYNTAX  Gauge
    ACCESS  read-only
    STATUS  mandatory
    DESCRIPTION
           "The counter associated with the number of
            Errored Seconds encountered
            by the SDSL Interface in a
            particular 15-minute interval
            in the past 24 hours."
    ::= { isarIsdslFarEndIntervalEntry  2 }

isarIsdslFarEndIntervalSESs OBJECT-TYPE
    SYNTAX  Gauge
    ACCESS  read-only
    STATUS  mandatory
    DESCRIPTION
           "The counter associated with the number of
            Severely Errored Seconds
            encountered by the SDSL Interface in a
            particular 15-minute interval
            in the past 24 hours."
    ::= { isarIsdslFarEndIntervalEntry  3 }

isarIsdslFarEndIntervalUASs OBJECT-TYPE
    SYNTAX  Gauge
    ACCESS  read-only
    STATUS  mandatory
    DESCRIPTION
           "The counter associated with the number of
            UA Seconds
            encountered by the SDSL Interface in a
            particular 15-minute interval
            in the past 24 hours."
    ::= { isarIsdslFarEndIntervalEntry  4 }

isarIsdslFarEndIntervalCVs OBJECT-TYPE
    SYNTAX  Gauge
    ACCESS  read-only
    STATUS  mandatory
    DESCRIPTION
           "The counter associated with the number of Coding
            Violations encountered by the
            SDSL Interface in a particular 15-minute interval
            in the past 24 hours."
    ::= { isarIsdslFarEndIntervalEntry  5 }

isarIsdslFarEndIntervalTimeStamp OBJECT-TYPE
    SYNTAX  TimeTicks
    ACCESS  read-only
    STATUS  mandatory
    DESCRIPTION
           "Start of interval."
    ::= { isarIsdslFarEndIntervalEntry  6 }


-- The SDSL ATM Current table
-- contains various statistics
-- being collected for the current 15 minute interval.
-- The statistics are collected from
-- the ATM side.

isarIsdslAtmCurrentTable OBJECT-TYPE
    SYNTAX  SEQUENCE OF IsarIsdslAtmCurrentEntry
    ACCESS  not-accessible
    STATUS  mandatory
    DESCRIPTION
           "The SDSL Atm Current table."
    ::= { isarIsdslMIBObjects 6  }

isarIsdslAtmCurrentEntry OBJECT-TYPE
    SYNTAX  IsarIsdslAtmCurrentEntry
    ACCESS  not-accessible
    STATUS  mandatory
    DESCRIPTION
           "An entry in the SDSL Atm Current table."
    INDEX   { ifIndex }
    ::= { isarIsdslAtmCurrentTable  1 }

IsarIsdslAtmCurrentEntry ::=
    SEQUENCE {
      isarIsdslAtmCurrentDroppedCells
        Gauge,

      isarIsdslAtmCurrentHECErrors
        Gauge,

      isarIsdslAtmCurrentReceivedCells
        Gauge,

      isarIsdslAtmCurrentTransmittedCells
        Gauge,

      isarIsdslAtmCurrentDriftAlarms
        Gauge,

      isarIsdslAtmCurrentLossOfSyncWords
        Gauge

    }

isarIsdslAtmCurrentDroppedCells OBJECT-TYPE
    SYNTAX  Gauge
    ACCESS  read-only
    STATUS  mandatory
    DESCRIPTION
           "The counter associated with the number of
            Dropped cells due to HEC errors
            encountered by the SDSL
            interface in the current 15 minute
            interval."
    ::= { isarIsdslAtmCurrentEntry  1 }

isarIsdslAtmCurrentHECErrors OBJECT-TYPE
    SYNTAX  Gauge
    ACCESS  read-only
    STATUS  mandatory
    DESCRIPTION
           "The counter associated with the number of
            cells with HEC Errors
            encountered by the
            SDSL interface in
            the current 15 minute interval."
    ::= { isarIsdslAtmCurrentEntry  2 }

isarIsdslAtmCurrentReceivedCells OBJECT-TYPE
    SYNTAX  Gauge
    ACCESS  read-only
    STATUS  mandatory
    DESCRIPTION
           "The counter associated with the number of
            received cells
            encountered by the
            SDSL interface in
            the current 15 minute interval."
    ::= { isarIsdslAtmCurrentEntry  3 }

isarIsdslAtmCurrentTransmittedCells OBJECT-TYPE
    SYNTAX  Gauge
    ACCESS  read-only
    STATUS  mandatory
    DESCRIPTION
           "The counter associated with the number of
            transmitted cells
            encountered by the
            SDSL interface in
            the current 15 minute interval."
    ::= { isarIsdslAtmCurrentEntry  4 }

isarIsdslAtmCurrentDriftAlarms OBJECT-TYPE
    SYNTAX  Gauge
    ACCESS  read-only
    STATUS  mandatory
    DESCRIPTION
           "The counter associated with the number of
            drift alarms (drift alarm: clock offset 
            between external and internal timing is 
            approaching an underflow or overflow situation)
            encountered by the SDSL interface in
            the current 15 minute interval.
	    Note: this field is only applicable when 2B1Q line coding is
	    selected."
    ::= { isarIsdslAtmCurrentEntry  5 }

isarIsdslAtmCurrentLossOfSyncWords OBJECT-TYPE
    SYNTAX  Gauge
    ACCESS  read-only
    STATUS  mandatory
    DESCRIPTION
           "The counter associated with the number of
            loss of sync words encountered by the SDSL interface in
            the current 15 minute interval.
	    Note: this field is only applicable when PAM16 line coding is
	    selected. "
    ::= { isarIsdslAtmCurrentEntry  6 }


-- The SDSL ATM Interval Table

-- The SDSL ATM Interval Table
-- contains various statistics
-- collected by each system over a maximum
-- of the previous 24 hours of
-- operation.  The past 24 hours may be broken into 96
-- completed 15 minute intervals.
-- A system is required to store at
-- least 4 completed 15 minute interval.
-- The default value is 32 intervals.
-- IAD4700 : the maximum of n will be used.

isarIsdslAtmIntervalTable OBJECT-TYPE
    SYNTAX  SEQUENCE OF IsarIsdslAtmIntervalEntry
    ACCESS  not-accessible
    STATUS  mandatory
    DESCRIPTION
           "The SDSL Atm Interval table."
    ::= { isarIsdslMIBObjects 7 }

isarIsdslAtmIntervalEntry OBJECT-TYPE
    SYNTAX  IsarIsdslAtmIntervalEntry
    ACCESS  not-accessible
    STATUS  mandatory
    DESCRIPTION
           "An entry in the SDSL Atm Interval table."
    INDEX   { ifIndex,  isarIsdslAtmIntervalNumber }
    ::= { isarIsdslAtmIntervalTable  1 }

IsarIsdslAtmIntervalEntry ::=
    SEQUENCE {
      isarIsdslAtmIntervalNumber
        INTEGER,

      isarIsdslAtmIntervalDroppedCells
        Gauge,

      isarIsdslAtmIntervalHECErrors
        Gauge,

      isarIsdslAtmIntervalReceivedCells
        Gauge,

      isarIsdslAtmIntervalTransmittedCells
        Gauge,

      isarIsdslAtmIntervalDriftAlarms
        Gauge,

      isarIsdslAtmIntervalTimeStamp
        TimeTicks,

      isarIsdslAtmIntervalLossOfSyncWords
        Gauge
    }

isarIsdslAtmIntervalNumber OBJECT-TYPE
    SYNTAX  INTEGER (1..96)
    ACCESS  not-accessible
    STATUS  mandatory
    DESCRIPTION
           "A number between 1 and 96, which identifies the
            interval for which the set of statistics is available.
            The interval identified by 1 is the most recently
            completed 15 minute interval,
            and the interval identified
            by N is the interval immediately preceding the
            one identified
            by N-1."
    ::= { isarIsdslAtmIntervalEntry  1 }

isarIsdslAtmIntervalDroppedCells OBJECT-TYPE
    SYNTAX  Gauge
    ACCESS  read-only
    STATUS  mandatory
    DESCRIPTION
           "The counter associated with the number of
            Dropped cells due to HEC errors encountered
            by the SDSL interface in a
            particular 15-minute interval
            in the past 24 hours."
    ::= { isarIsdslAtmIntervalEntry  2 }

isarIsdslAtmIntervalHECErrors OBJECT-TYPE
    SYNTAX  Gauge
    ACCESS  read-only
    STATUS  mandatory
    DESCRIPTION
           "The counter associated with the number of
            cells with HEC Errors
            encountered by the SDSL interface
            in a particular 15-minute interval
            in the past 24 hours."
    ::= { isarIsdslAtmIntervalEntry  3 }

isarIsdslAtmIntervalReceivedCells OBJECT-TYPE
    SYNTAX  Gauge
    ACCESS  read-only
    STATUS  mandatory
    DESCRIPTION
           "The counter associated with the number of
            received cells
            encountered by the SDSL interface
            in a particular 15-minute interval
            in the past 24 hours."
    ::= { isarIsdslAtmIntervalEntry  4 }

isarIsdslAtmIntervalTransmittedCells OBJECT-TYPE
    SYNTAX  Gauge
    ACCESS  read-only
    STATUS  mandatory
    DESCRIPTION
           "The counter associated with the number of
            transmitted cells
            encountered by the SDSL interface
            in a particular 15-minute interval
            in the past 24 hours."
    ::= { isarIsdslAtmIntervalEntry  5 }

isarIsdslAtmIntervalDriftAlarms OBJECT-TYPE
    SYNTAX  Gauge
    ACCESS  read-only
    STATUS  mandatory
    DESCRIPTION
           "The counter associated with the number of
            drift alarms (drift alarm: clock offset 
            between external and internal timing is 
            approaching an underflow or overflow situation)
            encountered by the SDSL interface in a 
            particular 15-minute interval in the past 24 hours.
	    Note: this field is only applicable when 2B1Q line coding is
	    selected."
    ::= { isarIsdslAtmIntervalEntry  6 }

isarIsdslAtmIntervalTimeStamp OBJECT-TYPE
    SYNTAX  TimeTicks
    ACCESS  read-only
    STATUS  mandatory
    DESCRIPTION
           "Start of interval."
    ::= { isarIsdslAtmIntervalEntry  7 }

isarIsdslAtmIntervalLossOfSyncWords OBJECT-TYPE
    SYNTAX  Gauge
    ACCESS  read-only
    STATUS  mandatory
    DESCRIPTION
           "The counter associated with the number of
            loss of sync words encountered by the SDSL interface in
            a particular 15-minute interval in the past 24 hours.
	    Note: this field is only applicable when PAM16 line coding is
	    selected. "
    ::= { isarIsdslAtmIntervalEntry  8 }


-- thresholds table for SDLSL performance counters

isarIsdslThresholdTable OBJECT-TYPE
    SYNTAX  SEQUENCE OF IsarIsdslThresholdEntry
    ACCESS  not-accessible
    STATUS  mandatory
    DESCRIPTION
           "The SDSL threshold table."
    ::= { isarIsdslMIBObjects 8 }

isarIsdslThresholdEntry OBJECT-TYPE
    SYNTAX  IsarIsdslThresholdEntry
    ACCESS  not-accessible
    STATUS  mandatory
    DESCRIPTION
           "An entry in the SDSL threshold table."
    INDEX   { ifIndex }
    ::= { isarIsdslThresholdTable  1 }

IsarIsdslThresholdEntry ::=
    SEQUENCE {
      isarIsdslNearEndThrshld
        INTEGER,

      isarIsdslFarEndThrshld
        INTEGER
    }


isarIsdslNearEndThrshld OBJECT-TYPE
    SYNTAX  INTEGER (1..7500)
    ACCESS  read-write
    STATUS  mandatory
    DESCRIPTION
           "Threshold for Section anomaly values ES, SES.
            Default = 2400."
    DEFVAL { 2400 }
    ::= { isarIsdslThresholdEntry  1 }

isarIsdslFarEndThrshld OBJECT-TYPE
    SYNTAX  INTEGER (1..7500)
    ACCESS  read-write
    STATUS  mandatory
    DESCRIPTION
           "Threshold for Line anomaly values ES, SES.
            Default = 2400."
    DEFVAL { 2400 }
    ::= { isarIsdslThresholdEntry  2 }

--
-- ISAR sdslMIBObjects : end
-- 




END
