---------------------------------------------------------
-- SAGEM-DR-DSLAM.MIB
-- MIB generated by MG-SOFT Visual MIB Builder Version 1.5 Build 103
-- Thursday, August 24, 2000 at 17:07:54
---------------------------------------------------------

	SAGEM-DR-DSLAM-MIB DEFINITIONS ::= BEGIN

		IMPORTS 
			sagem-dr			
				FROM SAGEM-DR-MIB			
			MODULE-IDENTITY			
				FROM SNMPv2-SMI;
	
	
		dslam MODULE-IDENTITY
			LAST-UPDATED "190005180000Z"
			ORGANIZATION
				"SAGEM-Tolbiac URD2"
			CONTACT-INFO
				"    "
			DESCRIPTION
				"The MIB module defines sagem-dr/dslam entry"
			::= { sagem-dr 16 }

	
--
-- Node definitions
--
	
	
	END

-----------------------------------------------
-- SAGEM-DR-DSLAM.MIB
-----------------------------------------------
