FRNETSERV-MIB DEFINITIONS ::= BEGIN
  
   IMPORTS
      MODULE-IDENTITY, OBJECT-TYPE,
      Counter32, Integer32					   FROM SNMPv2-SMI
      DisplayString, 
      TimeStamp, RowStatus,
      TEXTUAL-CONVENTION                       FROM SNMPv2-TC
      MODULE-COMPLIANCE, OBJECT-GROUP		   FROM SNMPv2-CONF
      ifIndex, transmission                    FROM RFC1213-MIB;
  
   frnetservMIB MODULE-IDENTITY
        LAST-UPDATED "9311161200Z"
        ORGANIZATION "IETF Frame Relay Network MIB Working Group"
        CONTACT-INFO
              "   Tracy A. Brown
                  Bellcore
                  331 Newman Springs Rd.
                  Red Bank, NJ 07701 USA
  
                  Tel: 1-908-758-2107
                  Fax: 1-908-758-4177
                  E-mail: tacox@mail.bellcore.com."
        DESCRIPTION
                 "The MIB module to describe generic objects for
                 Frame Relay Network Service."
        ::= { transmission 44 }
  
        IfIndex ::= TEXTUAL-CONVENTION
              STATUS  current
              DESCRIPTION
                 "The value of this object identifies the
                 interface for which this entry contains
                 management information.  The value of this
                 object for a particular interface has the same
                 value as the ifIndex object, defined in RFC
                 1213, for the same interface."
              SYNTAX Integer32
  
        frnetservObjects  OBJECT IDENTIFIER ::= { frnetservMIB 1 }
        frnetservTraps    OBJECT IDENTIFIER ::= { frnetservMIB 2 }
  
  
   -- The Frame Relay Service Logical Port Group
  
   --  the Frame Relay Logical Port Group
  
   --  This table is an interface specific addendum
   --  to the generic ifTable from MIB-II.
  
  frLportTable OBJECT-TYPE
   SYNTAX  SEQUENCE OF FrLportEntry
   MAX-ACCESS  not-accessible
   STATUS  current
   DESCRIPTION
           "The Frame Relay Logical Port Information table."
   ::= { frnetservObjects 1 }
  
  frLportEntry OBJECT-TYPE
   SYNTAX  FrLportEntry
   MAX-ACCESS  not-accessible
   STATUS  current
   DESCRIPTION
            "An entry in the Frame Relay Logical Port
            Information table."
   INDEX   { ifIndex }
   ::= { frLportTable 1 }
  
  FrLportEntry ::=
    SEQUENCE {
        frLportNumPlan
            INTEGER,
        frLportContact
            DisplayString,
        frLportLocation
            DisplayString,
        frLportType
            INTEGER,
        frLportAddrDLCILen
            INTEGER,
        frLportVCSigProtocol
            INTEGER,
        frLportVCSigPointer
            OBJECT IDENTIFIER
   }
  
  
   frLportNumPlan OBJECT-TYPE
       SYNTAX  INTEGER {
                 other(1),
                 e164(2),
                 x121(3),
                 none(4)
               }
       MAX-ACCESS  read-only
       STATUS  current
       DESCRIPTION
               "The value of this object identifies the network
               address numbering plan for this UNI/NNI logical
               port. The network address is the object
               ifPhysAddress. The value none implies that there
               is no ifPhysAddress.  The SNMP proxy-agent will
               return an octet string of zero length for
               ifPhysAddress. The value other means that an
               address has been assigned to this interface, but
               the numbering plan is not enumerated here."
       ::= { frLportEntry 1 }
  
   frLportContact OBJECT-TYPE
       SYNTAX  DisplayString (SIZE(0..255))
       MAX-ACCESS  read-only
       STATUS  current
       DESCRIPTION
               "The value of this object identifies the network
               contact for this UNI/NNI logical port."
       ::= { frLportEntry 2 }
  
   frLportLocation OBJECT-TYPE
       SYNTAX  DisplayString (SIZE(0..255))
       MAX-ACCESS  read-only
       STATUS  current
       DESCRIPTION
               "The value of this object identifies the Frame
               Relay network location for this UNI/NNI logical
               port."
       ::= { frLportEntry 3 }
  
   frLportType OBJECT-TYPE
       SYNTAX  INTEGER {
                 uni(1),
                 nni(2)
               }
       MAX-ACCESS  read-write
       STATUS  current
       DESCRIPTION
               "The value of this object identifies the type of
               network interface for this logical port."
       ::= { frLportEntry 4 }
  
   frLportAddrDLCILen OBJECT-TYPE
       SYNTAX  INTEGER {
        twoOctets10Bits(1),
        threeOctets10Bits(2),
        threeOctets16Bits(3),
        fourOctets17Bits(4),
        fourOctets23Bits(5)
      }
       MAX-ACCESS  read-only
       STATUS  current
       DESCRIPTION
               "The value of this object identifies the Q.922
               Address field length and DLCI length for this
               UNI/NNI logical port."
       ::= { frLportEntry 5 }
  
   frLportVCSigProtocol OBJECT-TYPE
       SYNTAX  INTEGER {
                 none(1),
                 lmi(2),
                 ansiT1617D(3),
                 ansiT1617B(4),
                 ccittQ933A(5)
               }
       MAX-ACCESS  read-write
       STATUS  current
       DESCRIPTION
               "The value of this object identifies the Local
               In-Channel Signaling Protocol that is used for
               this frame relay UNI/NNI logical port."
       ::= { frLportEntry 6 }
  
   frLportVCSigPointer OBJECT-TYPE
       SYNTAX  OBJECT IDENTIFIER
       MAX-ACCESS  read-only
       STATUS  current
       DESCRIPTION
               "The value of this object is used as a pointer to
               the table that contains the Local In-Channel
               Signaling Protocol parameters and errors for this
               UNI/NNI logical port.  See the Frame Relay
               Management VC Signaling Parameters and Errors
               Group."
       ::= { frLportEntry 7 }
  
  
   -- the Frame Relay Management VC Signaling Group
  
   -- This Group contains managed objects for the
   -- Local In-Channel Signaling Parameters and
   -- for signaling errors.
  
   frMgtVCSigTable OBJECT-TYPE
       SYNTAX  SEQUENCE OF FrMgtVCSigEntry
       MAX-ACCESS  not-accessible
       STATUS  current
       DESCRIPTION
               "The Frame Relay Management VC Signaling
               Parameters and Errors table."
       ::= { frnetservObjects 2 }
  
   frMgtVCSigEntry OBJECT-TYPE
       SYNTAX  FrMgtVCSigEntry
       MAX-ACCESS  not-accessible
       STATUS  current
       DESCRIPTION
               "An entry in the Frame Relay Management VC
               Signaling Parameters Errors table."
       INDEX   { ifIndex }
       ::= { frMgtVCSigTable 1 }
  
   FrMgtVCSigEntry ::=
       SEQUENCE {
           frMgtVCSigProced
               INTEGER,
           frMgtVCSigUserN391
               INTEGER,
           frMgtVCSigUserN392
               INTEGER,
           frMgtVCSigUserN393
               INTEGER,
           frMgtVCSigUserT391
               INTEGER,
           frMgtVCSigNetN392
               INTEGER,
           frMgtVCSigNetN393
               INTEGER,
           frMgtVCSigNetT392
               INTEGER,
           frMgtVCSigNetnN4
               INTEGER,
           frMgtVCSigNetnT3
               INTEGER,
           frMgtVCSigUserLinkRelErrors
               Counter32,
           frMgtVCSigUserProtErrors
               Counter32,
           frMgtVCSigUserChanInactive
               Counter32,
           frMgtVCSigNetLinkRelErrors
               Counter32,
           frMgtVCSigNetProtErrors
               Counter32,
           frMgtVCSigNetChanInactive
               Counter32
   }
  
  
   frMgtVCSigProced OBJECT-TYPE
       SYNTAX  INTEGER {
                 u2nnet(1),
                 bidirect(2)
               }
       MAX-ACCESS  read-only
       STATUS  current
       DESCRIPTION
               "The value of this object identifies the Local
               In-Channel Signaling Procedure that is used for
               this UNI/NNI logical port.  The UNI/NNI logical
               port can be performing only user-to-network
               network-side procedures or bidirectional
               procedures."
       ::= { frMgtVCSigEntry 1 }
  
   frMgtVCSigUserN391 OBJECT-TYPE
       SYNTAX  INTEGER (1..255)
       MAX-ACCESS  read-write
       STATUS  current
       DESCRIPTION
               "The value of this object identifies the User-side
               N391 full status polling cycle value for this
               UNI/NNI logical port.  If the logical port is not
               performing user-side procedures, then this value
               is equal to noSuchName. This object applies to
               Q.933 Annex A and T1.617 Annex D."
       DEFVAL { 6 }
       ::= { frMgtVCSigEntry 2 }
  
   frMgtVCSigUserN392 OBJECT-TYPE
       SYNTAX  INTEGER (1..10)
       MAX-ACCESS  read-write
       STATUS  current
       DESCRIPTION
               "The value of this object identifies the User-side
               N392 error threshold value for this UNI/NNI
               logical port.  If the logical port is not
               performing user-side procedures, then this value
               is equal to noSuchName. This object applies to
               Q.933 Annex A and T1.617 Annex D."
       DEFVAL { 3 }
       ::= { frMgtVCSigEntry 3 }
  
   frMgtVCSigUserN393 OBJECT-TYPE
       SYNTAX  INTEGER (1..10)
       MAX-ACCESS  read-write
       STATUS  current
       DESCRIPTION
               "The value of this object identifies the User-side
               N393 monitored events count value for this UNI/NNI
               logical port.  If the logical port is not
               performing user-side procedures, then this value
               is equal to noSuchName. This object applies to
               Q.933 Annex A and T1.617 Annex D."
       DEFVAL { 4 }
       ::= { frMgtVCSigEntry 4 }
  
   frMgtVCSigUserT391 OBJECT-TYPE
       SYNTAX  INTEGER (5..30)
       MAX-ACCESS  read-write
       STATUS  current
       DESCRIPTION
               "The value of this object identifies the User-side
               T391 link integrity verification polling timer
               value for this UNI/NNI logical port.  If the
               logical port is not performing user-side
               procedures, then this value is equal to
               noSuchName. This object applies to Q.933 Annex A
               and T1.617 Annex D."
       DEFVAL { 10 }
       ::= { frMgtVCSigEntry 5 }
  
   frMgtVCSigNetN392 OBJECT-TYPE
       SYNTAX  INTEGER (1..10)
       MAX-ACCESS  read-write
       STATUS  current
       DESCRIPTION
               "The value of this object identifies the Network-
               side N392 error threshold value (nN2 for LMI) for
               this UNI/NNI logical port.  If the logical port is
               not performing network-side procedures, then this
               value is equal to noSuchName. This object applies
               to Q.933 Annex A, T1.617 Annex D and LMI."
       DEFVAL { 3 }
       ::= { frMgtVCSigEntry 6 }
  
   frMgtVCSigNetN393 OBJECT-TYPE
       SYNTAX  INTEGER (1..10)
       MAX-ACCESS  read-write
       STATUS  current
       DESCRIPTION
               "The value of this object identifies the Network-
               side N393 monitored events count value (nN3 for
               LMI) for this UNI/NNI logical port.  If the
               logical port is not performing network-side
               procedures, then this value is equal to
               noSuchName. This object applies to Q.933 Annex A,
               T1.617 Annex D and LMI."
       DEFVAL { 4 }
       ::= { frMgtVCSigEntry 7 }
  
   frMgtVCSigNetT392 OBJECT-TYPE
       SYNTAX  INTEGER (5..30)
       MAX-ACCESS  read-write
       STATUS  current
       DESCRIPTION
               "The value of this object identifies the Network-
               side T392 polling verification timer value (nT2
               for LMI)  for this UNI/NNI logical port.  If the
               logical port is not performing network-side
               procedures, then this value is equal to
               noSuchName. This object applies to Q.933 Annex A,
               T1.617 Annex D and LMI."
       DEFVAL { 15 }
       ::= { frMgtVCSigEntry 8 }
  
   frMgtVCSigNetnN4 OBJECT-TYPE
       SYNTAX  INTEGER (5..5)
       MAX-ACCESS  read-write
       STATUS  current
       DESCRIPTION
               "The value of this object identifies the Network-
               side nN4 maximum status enquires received value
               for this UNI/NNI logical port.  If the logical
               port is not performing network-side procedures or
               is not performing LMI procedures, then this value
               is equal to noSuchName. This object applies only
               to LMI and always has a value of 5."
       ::= { frMgtVCSigEntry 9 }
  
   frMgtVCSigNetnT3 OBJECT-TYPE
       SYNTAX  INTEGER (5 | 10 | 15 | 20 | 25 | 30)
       MAX-ACCESS  read-write
       STATUS  current
       DESCRIPTION
               "The value of this object identifies the Network-
               side nT3 timer (for nN4 status enquires received)
               value for this UNI/NNI logical port.  If the
               logical port is not performing network-side
               procedures or is not performing LMI procedures,
               then this value is equal to noSuchName. This
               object applies only to LMI."
       DEFVAL { 20 }
       ::= { frMgtVCSigEntry 10 }
  
   frMgtVCSigUserLinkRelErrors OBJECT-TYPE
       SYNTAX  Counter32
       MAX-ACCESS  read-only
       STATUS  current
       DESCRIPTION
               "The number of user-side local in-channel
               signaling link reliability errors (i.e., non-
               receipt of Status/Status Enquiry messages or
               invalid sequence numbers in a Link Integrity
               Verification Information Element) for this UNI/NNI
               logical port.  If the logical port is not
               performing user-side procedures, then this value
               is equal to noSuchName."
       ::= { frMgtVCSigEntry 11 }
  
   frMgtVCSigUserProtErrors OBJECT-TYPE
       SYNTAX  Counter32
       MAX-ACCESS  read-only
       STATUS  current
       DESCRIPTION
               "The number of user-side local in-channel
               signaling protocol errors (i.e., protocol
               discriminator, message type, call reference, and
               mandatory information element errors) for this
               UNI/NNI logical port.  If the logical port is not
               performing user-side procedures, then this value
               is equal to noSuchName."
       ::= { frMgtVCSigEntry 12 }
  
   frMgtVCSigUserChanInactive OBJECT-TYPE
       SYNTAX  Counter32
       MAX-ACCESS  read-only
       STATUS  current
       DESCRIPTION
               "The number of times the user-side channel was
               declared inactive (i.e., N392 errors in N393
               events) for this UNI/NNI logical port. If the
               logical port is not performing user-side
               procedures, then this value is equal to
               noSuchName."
       ::= { frMgtVCSigEntry 13 }
  
   frMgtVCSigNetLinkRelErrors OBJECT-TYPE
       SYNTAX  Counter32
       MAX-ACCESS  read-only
       STATUS  current
       DESCRIPTION
               "The number of network-side local in-channel
               signaling link reliability errors (i.e., non-
               receipt of Status/Status Enquiry messages or
               invalid sequence numbers in a Link Integrity
               Verification Information Element) for this UNI/NNI
               logical port.  If the logical port is not
               performing network-side procedures, then this
               value is equal to noSuchName."
       ::= { frMgtVCSigEntry 14 }
  
   frMgtVCSigNetProtErrors OBJECT-TYPE
       SYNTAX  Counter32
       MAX-ACCESS  read-only
       STATUS  current
       DESCRIPTION
               "The number of network-side local in-channel
               signaling protocol errors (i.e., protocol
               discriminator, message type, call reference, and
               mandatory information element errors) for this
               UNI/NNI logical port.  If the logical port is not
               performing network-side procedures, then this
               value is equal to noSuchName."
       ::= { frMgtVCSigEntry 15 }
  
   frMgtVCSigNetChanInactive OBJECT-TYPE
       SYNTAX  Counter32
       MAX-ACCESS  read-only
       STATUS  current
       DESCRIPTION
               "The number of times the network-side channel was
               declared inactive (i.e., N392 errors in N393
               events) for this UNI/NNI logical port.  If the
               logical port is not performing network-side
               procedures, then this value is equal to
               noSuchName."
       ::= { frMgtVCSigEntry 16 }
  
  
   -- The Frame Relay PVC End-point Table
  
   frPVCEndptTable OBJECT-TYPE
       SYNTAX  SEQUENCE OF FrPVCEndptEntry
       MAX-ACCESS  not-accessible
       STATUS  current
       DESCRIPTION
               "The Frame Relay PVC End-Point table.  This table
               is used to model a PVC end-point.  This table
               contains the traffic parameters and statistics for
               a PVC end-point."
       ::= { frnetservObjects 3 }
  
   frPVCEndptEntry OBJECT-TYPE
       SYNTAX  FrPVCEndptEntry
       MAX-ACCESS  not-accessible
       STATUS  current
       DESCRIPTION
               "An entry in the Frame Relay PVC Endpoint table."
       INDEX   { ifIndex, frPVCEndptDLCIIndex }
       ::= { frPVCEndptTable 1 }
  
   FrPVCEndptEntry ::=
       SEQUENCE {
           frPVCEndptDLCIIndex
               Integer32,
           frPVCEndptInMaxFrameSize
               Integer32,
           frPVCEndptInBc
               Integer32,
           frPVCEndptInBe
               Integer32,
           frPVCEndptInCIR
              Integer32,
           frPVCEndptOutMaxFrameSize
               Integer32,
           frPVCEndptOutBc
               Integer32,
           frPVCEndptOutBe
               Integer32,
           frPVCEndptOutCIR
               Integer32,
           frPVCEndptConnectIdentifier
               Integer32,
           frPVCEndptRowStatus
               RowStatus,
           frPVCEndptRcvdSigStatus
               INTEGER,
           frPVCEndptInFrames
               Counter32,
           frPVCEndptOutFrames
               Counter32,
           frPVCEndptInDEFrames
               Counter32,
           frPVCEndptInExcessFrames
               Counter32,
           frPVCEndptOutExcessFrames
               Counter32,
           frPVCEndptInDiscards
               Counter32,
           frPVCEndptInOctets
               Counter32,
           frPVCEndptOutOctets
               Counter32
       }
  
  
   frPVCEndptDLCIIndex OBJECT-TYPE
       SYNTAX  Integer32
       MAX-ACCESS  not-accessible
       STATUS  current
       DESCRIPTION
               "The value of this object is equal to the DLCI
               value for this PVC end-point."
       ::= { frPVCEndptEntry 1 }
  
   frPVCEndptInMaxFrameSize OBJECT-TYPE
       SYNTAX  Integer32
       MAX-ACCESS  read-create
       STATUS  current
       DESCRIPTION
               "The value of this object is the size in octets of
               the largest frame relay information field for this
               PVC end-point in the ingress direction (into the
  	           frame relay network).  The value of
               frPVCEndptInMaxFrameSize must be less than or
               equal to the corresponding ifMtu for this Frame
               Relay UNI/NNI logical port."
       ::= { frPVCEndptEntry 2 }
  
   frPVCEndptInBc OBJECT-TYPE
       SYNTAX  Integer32
       MAX-ACCESS  read-create
       STATUS  current
       DESCRIPTION
               "The value of this object is equal to the
               committed burst size (Bc) parameter (measured in
               bits) for this PVC end-point in the ingress
               direction (into the frame relay network)."
       ::= { frPVCEndptEntry 3 }
  
   frPVCEndptInBe OBJECT-TYPE
       SYNTAX  Integer32
       MAX-ACCESS  read-create
       STATUS  current
       DESCRIPTION
               "The value of this object is equal to the excess
               burst size (Be) parameter (measured in bits) for
               this PVC end-point in the ingress direction (into
               the frame relay network)."
       ::= { frPVCEndptEntry 4 }
  
   frPVCEndptInCIR OBJECT-TYPE
       SYNTAX  Integer32
       MAX-ACCESS  read-create
       STATUS  current
       DESCRIPTION
               "The value of this object is equal to the
               committed information rate (CIR) parameter
               (measured in bits per second) for this PVC end-
               point in the ingress direction (into the frame
               relay network)."
       ::= { frPVCEndptEntry 5 }
  
   frPVCEndptOutMaxFrameSize OBJECT-TYPE
       SYNTAX  Integer32
       MAX-ACCESS  read-create
       STATUS  current
       DESCRIPTION
               "The value of this object is the size in octets of
               the largest frame relay information field for this
               PVC end-point in the egress direction (out of the
  	           frame relay network).  The value of
               frPVCEndptOutMaxFrameSize must be less than or
               equal to the corresponding ifMtu for this Frame
               Relay UNI/NNI logical port."
       ::= { frPVCEndptEntry 6 }
  
   frPVCEndptOutBc OBJECT-TYPE
       SYNTAX  Integer32
       MAX-ACCESS  read-create
       STATUS  current
       DESCRIPTION
               "The value of this object is equal to the
               committed burst size (Bc) parameter (measured in
               bits) for this PVC end-point in the egress
               direction (out of the frame relay network)."
       ::= { frPVCEndptEntry 7 }
  
   frPVCEndptOutBe OBJECT-TYPE
       SYNTAX  Integer32
       MAX-ACCESS  read-create
       STATUS  current
       DESCRIPTION
               "The value of this object is equal to the excess
               burst size (Be) parameter (measured in bits) for
               this PVC end-point in the egress direction (out of
               the frame relay network)."
       ::= { frPVCEndptEntry 8 }
  
   frPVCEndptOutCIR OBJECT-TYPE
       SYNTAX  Integer32
       MAX-ACCESS  read-create
       STATUS  current
       DESCRIPTION
               "The value of this object is equal to the
               committed information rate (CIR) parameter
               (measured in bits per second) for this PVC end-
               point in the egress direction (out of the frame
               relay network)."
       ::= { frPVCEndptEntry 9 }
  
   frPVCEndptConnectIdentifier OBJECT-TYPE
       SYNTAX  Integer32
       MAX-ACCESS  read-only
       STATUS  current
       DESCRIPTION
               "This object is used to associate PVC end-points
               as being part of one PVC segment connection.  This
               value of this object is equal to the value of
  	           frPVCConnectIndex, which is used as one of the
               indices into the frPVCConnectTable.  The value of
               this object is provided by the agent, after the
               associated entries in the frPVCConnectTable have
               been created."
       ::= { frPVCEndptEntry 10 }
  
   frPVCEndptRowStatus OBJECT-TYPE
       SYNTAX  RowStatus
       MAX-ACCESS  read-create
       STATUS  current
       DESCRIPTION
               "This object is used to create new rows in this
               table, modify existing rows, and to delete
               existing rows.  To create a new PVC, the entries
               for the PVC segment end-points in the
               frPVCEndptTable must first be created.  Next, the
               frPVCConnectTable is used to associate the Frame
               Relay PVC segment end-points.  In order for the
               manager to have the necessary error diagnostics,
               the frPVCEndptRowStatus object must initially be
               set to `createAndWait'.  While the
               frPVCEndptRowStatus object is in the
               `createAndWait' state, the manager can set each
               columnar object and get the necessary error
               diagnostics.  The frPVCEndptRowStatus object may
               not be set to `active' unless the following
               columnar objects exist in this row:
               frPVCEndptInMaxFrameSize, frPVCEndptInBc,
               frPVCEndptInBe, frPVCEndptInCIR,
               frPVCEndptOutMaxFrameSize, frPVCEndptOutBc,
               frPVCEndptOutBe, and frPVCEndptOutCIR."
       ::= { frPVCEndptEntry 11 }
  
   frPVCEndptRcvdSigStatus OBJECT-TYPE
       SYNTAX  INTEGER {
                 deleted(1),
                 active(2),
                 inactive(3),
                 none(4)
               }
       MAX-ACCESS  read-only
       STATUS  current
       DESCRIPTION
               "The value of this object identifies the PVC
               status received via the local in-channel signaling
               procedures for this PVC end-point.  This object is
               only pertinent for interfaces that perform the
  	           bidirectional procedures.  For user-to-network
               network side procedures, the value of this object
               should be none."
       ::= { frPVCEndptEntry 12 }
  
   frPVCEndptInFrames OBJECT-TYPE
       SYNTAX  Counter32
       MAX-ACCESS  read-only
       STATUS  current
       DESCRIPTION
               "The number of frames received by the network
               (ingress) for this PVC end-point. This includes
               any frames discarded by the network due to
               submitting more than Bc + Be data or due to any
               network congestion recovery procedures."
       ::= { frPVCEndptEntry 13 }
  
   frPVCEndptOutFrames OBJECT-TYPE
       SYNTAX  Counter32
       MAX-ACCESS  read-only
       STATUS  current
       DESCRIPTION
               "The number of frames sent by the network (egress)
               regardless of whether they are Bc or Be frames for
               this PVC end-point."
       ::= { frPVCEndptEntry 14 }
  
   frPVCEndptInDEFrames OBJECT-TYPE
       SYNTAX  Counter32
       MAX-ACCESS  read-only
       STATUS  current
       DESCRIPTION
               "The number of frames received by the network
               (ingress) with the DE bit set to (1) for this PVC
               end-point."
       ::= { frPVCEndptEntry 15 }
  
   frPVCEndptInExcessFrames OBJECT-TYPE
       SYNTAX  Counter32
       MAX-ACCESS  read-only
       STATUS  current
       DESCRIPTION
               "The number of frames received by the network
               (ingress) for this PVC end-point which were
               treated as excess traffic.  Frames which are sent
               to the network with DE set to zero are treated as
               excess when more than Bc bits are submitted to the
               network during the Committed Information Rate
  	           Measurement Interval (Tc).  Excess traffic may or
               may not be discarded at the ingress if more than
               Bc + Be bits are submitted to the network during
               Tc.  Traffic discarded at the ingress is not
               recorded in frPVCEndptInExcessFrames.  Frames
               which are sent to the network with DE set to one
               are also treated as excess traffic."
       ::= { frPVCEndptEntry 16 }
  
   frPVCEndptOutExcessFrames OBJECT-TYPE
       SYNTAX  Counter32
       MAX-ACCESS  read-only
       STATUS  current
       DESCRIPTION
               "The number of frames sent by the network (egress)
               for this PVC end-point which were treated as
               excess traffic.  (The DE bit may be set to one.)"
       ::= { frPVCEndptEntry 17 }
  
   frPVCEndptInDiscards OBJECT-TYPE
       SYNTAX  Counter32
       MAX-ACCESS  read-only
       STATUS  current
       DESCRIPTION
               "The number of frames received by the the network
               (ingress) that were discarded due to traffic
               enforcement for this PVC end-point."
       ::= { frPVCEndptEntry 18 }
  
   frPVCEndptInOctets OBJECT-TYPE
       SYNTAX  Counter32
       MAX-ACCESS  read-only
       STATUS  current
       DESCRIPTION
               "The number of octets received by the network
               (ingress) for this PVC end-point.  This counter
               should only count octets from the beginning of the
               frame relay header field to the end of user data.
               If the network supporting Frame Relay can not
               count octets, then this count should be an
               approximation."
       ::= { frPVCEndptEntry 19 }
  
   frPVCEndptOutOctets OBJECT-TYPE
       SYNTAX  Counter32
       MAX-ACCESS  read-only
       STATUS  current
       DESCRIPTION
               "The number of octets sent by the network (egress)
               for this PVC end-point.  This counter should only
               count octets from the beginning of the frame relay
               header field to the end of user data.  If the
               network supporting Frame Relay can not count
               octets, then this count should be an
               approximation."
       ::= { frPVCEndptEntry 20 }
  
  
  
   frPVCConnectIndexValue OBJECT-TYPE
       SYNTAX  INTEGER (0..2147483647)
       MAX-ACCESS  read-only
       STATUS  current
       DESCRIPTION
               "This object contains an appropriate value to be
               used for frPVCConnectIndex when creating entries
               in the frPVCConnectTable.  The value 0 indicates
               that no unassigned entries are available.  To
               obtain the frPVCConnectIndex value for a new
               entry, the manager issues a management protocol
               retrieval operation to obtain the current value of
               this object.  After each retrieval, the agent
               should modify the value to the next unassigned
               index."
	   ::= { frnetservObjects 4 }

	     
   --  The Frame Relay PVC Connection Table
  
   frPVCConnectTable OBJECT-TYPE
       SYNTAX  SEQUENCE OF FrPVCConnectEntry
       MAX-ACCESS  not-accessible
       STATUS  current
       DESCRIPTION
               "The Frame Relay PVC Connect table.  A bi-
               directional PVC segment is modeled as one entry in
               this table."
       ::= { frnetservObjects 5 }
  
   frPVCConnectEntry OBJECT-TYPE
       SYNTAX  FrPVCConnectEntry
       MAX-ACCESS  not-accessible
       STATUS  current
       DESCRIPTION
               "An entry in the Frame Relay PVC Connect table.
               This entry is used to model a PVC segment in two
               directions."
       INDEX { frPVCConnectIndex,
               frPVCConnectLowIfIndex, frPVCConnectLowDLCIIndex,
               frPVCConnectHighIfIndex, frPVCConnectHighDLCIIndex }
       ::= { frPVCConnectTable 1 }
  
   FrPVCConnectEntry ::=
       SEQUENCE {
           frPVCConnectIndex
               Integer32,
           frPVCConnectLowIfIndex
               IfIndex,
           frPVCConnectLowDLCIIndex
               Integer32,
           frPVCConnectHighIfIndex
               IfIndex,
           frPVCConnectHighDLCIIndex
               Integer32,
           frPVCConnectAdminStatus
               INTEGER,
           frPVCConnectL2hOperStatus
               INTEGER,
           frPVCConnectH2lOperStatus
               INTEGER,
           frPVCConnectL2hLastChange
               TimeStamp,
           frPVCConnectH2lLastChange
               TimeStamp,
           frPVCConnectRowStatus
               RowStatus
   }
  
   frPVCConnectIndex OBJECT-TYPE
       SYNTAX  Integer32
       MAX-ACCESS  not-accessible
       STATUS  current
       DESCRIPTION
               "The value of this object is equal to the
               frPVCConnectIndexValue obtained to uniquely
               identify this PVC segment connection."
       ::= { frPVCConnectEntry 1 }
  
   frPVCConnectLowIfIndex OBJECT-TYPE
       SYNTAX  IfIndex
       MAX-ACCESS  not-accessible
       STATUS  current
       DESCRIPTION
               "The value of this object is equal to MIB II's
               ifIndex value of the UNI/NNI logical port for this
               PVC segment.  The term low implies that this PVC
               segment end-point has the numerically lower
               ifIndex value than the connected/associated PVC
               segment end-point.  If the value is equal to zero,
               then this logical port is not a Frame Relay
               UNI/NNI logical port."
       ::= { frPVCConnectEntry 2 }
  
   frPVCConnectLowDLCIIndex OBJECT-TYPE
       SYNTAX  Integer32
       MAX-ACCESS  not-accessible
       STATUS  current
       DESCRIPTION
               "The value of this object is equal to the DLCI
               value for this end-point of the PVC segment.  If
               the value is equal to zero, then this endpoint of
               the PVC segment is not a Frame Relay connection."
       ::= { frPVCConnectEntry 3 }
  
   frPVCConnectHighIfIndex OBJECT-TYPE
       SYNTAX  IfIndex
       MAX-ACCESS  not-accessible
       STATUS  current
       DESCRIPTION
               "The value of this object is equal to MIB II's
               ifIndex value for the UNI/NNI logical port for
               this PVC segment.  The term high implies that this
               PVC segment end-point has the numerically higher
               ifIndex value than the connected/associated PVC
               segment end-point."
       ::= { frPVCConnectEntry 4 }
  
   frPVCConnectHighDLCIIndex OBJECT-TYPE
       SYNTAX  Integer32
       MAX-ACCESS  not-accessible
       STATUS  current
       DESCRIPTION
               "The value of this object is equal to the egress
               DLCI value for this end-point of the PVC segment."
       ::= { frPVCConnectEntry 5 }
  
   frPVCConnectAdminStatus OBJECT-TYPE
       SYNTAX  INTEGER {
                 active(1),
                 inactive(2),
                 testing(3)
               }
       MAX-ACCESS  read-create
       STATUS  current
       DESCRIPTION
               "The value of this object identifies the desired
               administrative status of this bi-directional PVC
               segment.  The active state means the PVC segment
               is currently operational; the inactive state means
               the PVC segment is currently not operational; the
               testing state means the PVC segment is currently
               undergoing a test.  This state is set by an
               administrative entity.  This value affects the PVC
               status indicated across the ingress NNI/UNI of
               both end-points of the bi-directional PVC segment.
               When a PVC segment connection is created using
               this table, this object is initially set to
               `inactive'.  After the frPVCConnectRowStatus
               object is set to `active' (and the
               corresponding/associated entries in the
               frPVCEndptTable have their frPVCEndptRowStatus
               object set to `active'), the
               frPVCConnectAdminStatus object may be set to
               `active' to turn on the PVC segment connection."
       ::= { frPVCConnectEntry 6 }
  
   frPVCConnectL2hOperStatus OBJECT-TYPE
       SYNTAX  INTEGER {
                 active(1),
                 inactive(2),
                 testing(3),
                 unknown(4)
               }
       MAX-ACCESS  read-only
       STATUS  current
       DESCRIPTION
               "The value of this object identifies the current
               operational status of the PVC segment connection
               in one direction; (i.e., in the low to high
               direction).  The active state means it is
               currently operational; the inactive state means it
               is currently not operational; the testing state
               means it is currently undergoing a test; the
               unknown state means the status of it currently can
               not be determined.  This value affects the PVC
               status indicated across the ingress NNI/UNI (low
               side) of the PVC segment."
       ::= { frPVCConnectEntry 7 }
  
   frPVCConnectH2lOperStatus OBJECT-TYPE
       SYNTAX  INTEGER {
                 active(1),
                 inactive(2),
                 testing(3),
                 unknown(4)
               }
       MAX-ACCESS  read-only
       STATUS  current
       DESCRIPTION
               "The value of this object identifies the current
               operational status of the PVC segment connection
               in one direction; (i.e., in the high to low
               direction).  The active state means it is
               currently operational; the inactive state means it
               is currently not operational; the testing state
               means it is currently undergoing a test; the
               unknown state means the status of it currently can
               not be determined.  This value affects the PVC
               status indicated across the ingress NNI/UNI (high
               side) of the PVC segment."
       ::= { frPVCConnectEntry 8 }
  
   frPVCConnectL2hLastChange OBJECT-TYPE
       SYNTAX  TimeStamp
       MAX-ACCESS  read-only
       STATUS  current
       DESCRIPTION
               "The value of MIB II's sysUpTime object at the
               time this PVC segment entered its current
               operational state in the low to high direction.
               If the current state was entered prior to the last
               re-initialization of the proxy-agent, then this
               object contains a zero value."
       ::= { frPVCConnectEntry 9 }
  
   frPVCConnectH2lLastChange OBJECT-TYPE
       SYNTAX  TimeStamp
       MAX-ACCESS  read-only
       STATUS  current
       DESCRIPTION
               "The value of MIB II's sysUpTime object at the
               time this PVC segment entered its current
               operational state in the high to low direction.
               If the current state was entered prior to the last
               re-initialization of the proxy-agent, then this
               object contains a zero value."
       ::= { frPVCConnectEntry 10 }
  
   frPVCConnectRowStatus OBJECT-TYPE
       SYNTAX  RowStatus
       MAX-ACCESS  read-create
       STATUS  current
       DESCRIPTION
               "The status of this entry in the
               frPVCConnectTable.  This variable is used to
               create new connections for the PVC end-points and
               to change existing connections of the PVC end-
               points.  This object must be initially set to
               `createAndWait'.  In this state, the agent checks
               the parameters in the associated entries in the
               frPVCEndptTable to verify that the PVC end-points
               can be connected (i.e., the In parameters for one
               PVC end-point are equal to the Out parameters for
               the other PVC end-point).  This object can not be
               set to `active' unless the following columnar
               object exist in this row: frPVCConnectAdminStatus.
               The agent also supplies the associated value of
               frPVCConnectIndex for the frPVCEndptConnectIdentifier
               instances.  To turn on a PVC segment connection, the
               frPVCConnectAdminStatus is set to `active'."
       ::= { frPVCConnectEntry 11 }
  
   -- The Frame Relay Accounting Groups
  
   frAccountPVCTable OBJECT-TYPE
       SYNTAX  SEQUENCE OF FrAccountPVCEntry
       MAX-ACCESS  not-accessible
       STATUS  current
       DESCRIPTION
               "The Frame Relay Accounting PVC table.  This table
               is used to perform accounting on a PVC segment
               end-point basis."
       ::= { frnetservObjects 6 }
  
   frAccountPVCEntry OBJECT-TYPE
       SYNTAX  FrAccountPVCEntry
       MAX-ACCESS  not-accessible
       STATUS  current
       DESCRIPTION
               "An entry in the Frame Relay Accounting PVC
               table."
       INDEX   { ifIndex, frAccountPVCDLCIIndex }
       ::= { frAccountPVCTable 1 }
  
   FrAccountPVCEntry ::=
       SEQUENCE {
           frAccountPVCDLCIIndex
               Integer32,
           frAccountPVCSegmentSize
               Integer32,
           frAccountPVCInSegments
               Counter32,
           frAccountPVCOutSegments
               Counter32
       }
  
  
   frAccountPVCDLCIIndex OBJECT-TYPE
       SYNTAX  Integer32
       MAX-ACCESS  not-accessible
       STATUS  current
       DESCRIPTION
               "The value of this object is equal to the DLCI
               value for this PVC segment end-point."
       ::= { frAccountPVCEntry 1 }
  
   frAccountPVCSegmentSize OBJECT-TYPE
       SYNTAX  Integer32
       MAX-ACCESS  read-only
       STATUS  current
       DESCRIPTION
               "The value of this object is equal to the Segment
               Size for this PVC segment end-point."
       ::= { frAccountPVCEntry 2 }
  
   frAccountPVCInSegments OBJECT-TYPE
       SYNTAX  Counter32
       MAX-ACCESS  read-only
       STATUS  current
       DESCRIPTION
               "The value of this object is equal to the number
               of segments received by this PVC segment end-
               point."
       ::= { frAccountPVCEntry 3 }
  
    frAccountPVCOutSegments OBJECT-TYPE
       SYNTAX  Counter32
       MAX-ACCESS  read-only
       STATUS  current
       DESCRIPTION
               "The value of this object is equal to the number
               of segments sent by this PVC segment end-point."
       ::= { frAccountPVCEntry 4 }
  
  
   -- The Accounting on a Frame Relay Logical Port basis Group
  
  
   frAccountLportTable OBJECT-TYPE
       SYNTAX  SEQUENCE OF FrAccountLportEntry
       MAX-ACCESS  not-accessible
       STATUS  current
       DESCRIPTION
               "The Frame Relay Accounting Logical Port table.
               This table is used to perform accounting on a
               UNI/NNI Logical Port basis."
       ::= { frnetservObjects 7 }
  
   frAccountLportEntry OBJECT-TYPE
       SYNTAX  FrAccountLportEntry
       MAX-ACCESS  not-accessible
       STATUS  current
       DESCRIPTION
               "An entry in the Frame Relay Accounting Logical
               Port table."
       INDEX   { ifIndex }
       ::= { frAccountLportTable 1 }
  
   FrAccountLportEntry ::=
       SEQUENCE {
           frAccountLportSegmentSize
               Integer32,
           frAccountLportInSegments
               Counter32,
           frAccountLportOutSegments
               Counter32
       }
  
  
   frAccountLportSegmentSize OBJECT-TYPE
       SYNTAX  Integer32
       MAX-ACCESS  read-only
       STATUS  current
       DESCRIPTION
               "The value of this object is equal to the Segment
               Size for this UNI/NNI logical port."
       ::= { frAccountLportEntry 1 }
  
   frAccountLportInSegments OBJECT-TYPE
       SYNTAX  Counter32
       MAX-ACCESS  read-only
       STATUS  current
       DESCRIPTION
               "The value of this object is equal to the number
               of segments received by this UNI/NNI logical
               port."
       ::= { frAccountLportEntry 2 }
  
   frAccountLportOutSegments OBJECT-TYPE
       SYNTAX  Counter32
       MAX-ACCESS  read-only
       STATUS  current
       DESCRIPTION
               "The value of this object is equal to the number
               of segments sent by this UNI/NNI logical port."
       ::= { frAccountLportEntry 3 }
  

   -- Frame Relay Network Service TRAPS
  
  -- frPVCConnectStatusChange  NOTIFICATION-TYPE
  --     OBJECTS { frPVCConnectIndex,
  --               frPVCConnectLowIfIndex, frPVCConnectLowDLCIIndex,
  --               frPVCConnectHighIfIndex, frPVCConnectHighDLCIIndex,
  --               frPVCConnectL2hOperStatus, frPVCConnectH2lOperStatus,
  --               frPVCEndptRcvdSigStatus }
  --     STATUS  current
  --     DESCRIPTION
  --             "This trap indicates that the indicated PVC has
  --             changed state.  This trap is not sent if an FR-UNI
  --             changes state; a linkDown or linkUp trap should be
  --             sent instead."
  --     ::= { frnetservTraps 1 }
  
  
   -- Conformance Information
  
   frnetservConformance  OBJECT IDENTIFIER ::= { frnetservMIB 3 }
  
   frnetservGroups       OBJECT IDENTIFIER ::= { frnetservConformance 1 }
   frnetservCompliances  OBJECT IDENTIFIER ::= { frnetservConformance 2 }
  
   -- Compliance Statements
  
   frnetservCompliance MODULE-COMPLIANCE
         STATUS  current
         DESCRIPTION
           "The compliance statement for SNMPv2 entities
           which have Frame Relay Network Service Interfaces."
  
         MODULE -- this module
             MANDATORY-GROUPS { frnetservLportGroup,
                                frnetservMgtVCSigGroup,
                                frnetservPVCEndptGroup,
                                frnetservPVCConnectGroup }
  
             GROUP       frnetservAccountPVCGroup
             DESCRIPTION
                   "This group is optional for Frame Relay interfaces.
                   It is
                   mandatory if and only if accounting is performed
                   on a PVC
                   basis this
                   Frame Relay interface."
  
             GROUP       frnetservAccountLportGroup
             DESCRIPTION
                   "This group is optional for Frame Relay interfaces.
                   It is
                   mandatory if and only if accounting is
                   performed on a
                   logical port basis this
                   Frame Relay interface."
  
             OBJECT      frPVCEndptInMaxFrameSize
             SYNTAX      Integer32
             MIN-ACCESS  read-only
             DESCRIPTION
                   "Write access is not required."
  
             OBJECT      frPVCEndptInBc
             SYNTAX      Integer32
             MIN-ACCESS  read-only
             DESCRIPTION
                   "Write access is not required."
  
             OBJECT      frPVCEndptInBe
             SYNTAX      Integer32
             MIN-ACCESS  read-only
             DESCRIPTION
                   "Write access is not required."
  
             OBJECT      frPVCEndptInCIR
             SYNTAX      Integer32
             MIN-ACCESS  read-only
             DESCRIPTION
                   "Write access is not required."
  
             OBJECT      frPVCEndptOutMaxFrameSize
             SYNTAX      Integer32
             MIN-ACCESS  read-only
             DESCRIPTION
                   "Write access is not required."
  
             OBJECT      frPVCEndptOutBc
             SYNTAX      Integer32
             MIN-ACCESS  read-only
             DESCRIPTION
                   "Write access is not required."
  
             OBJECT      frPVCEndptOutBe
             SYNTAX      Integer32
             MIN-ACCESS  read-only
             DESCRIPTION
                   "Write access is not required."
  
             OBJECT      frPVCEndptOutCIR
             SYNTAX      Integer32
             MIN-ACCESS  read-only
             DESCRIPTION
                   "Write access is not required."
  
             OBJECT      frPVCEndptConnectIdentifier
             SYNTAX      Integer32
             MIN-ACCESS  read-only
             DESCRIPTION
                   "Write access is not required."
  
             OBJECT      frPVCEndptRowStatus
             SYNTAX      INTEGER { active(1) }  -- subset of RowStatus
             MIN-ACCESS  read-only
             DESCRIPTION
                   "Write access is not required, and only one of the
                   six enumerated values for the RowStatus textual
                   convention need be supported, specifically:
                   active(1)."
  
             OBJECT      frPVCConnectAdminStatus
             SYNTAX      INTEGER {
                           active(1),
                           inactive(2),
                           testing(3)
                          }
             MIN-ACCESS  read-only
             DESCRIPTION
                   "Write access is not required."
  
             OBJECT      frPVCConnectRowStatus
             SYNTAX      INTEGER { active(1) }  -- subset of RowStatus
             MIN-ACCESS  read-only
             DESCRIPTION
                   "Write access is not required."
  
             OBJECT      frPVCConnectRowStatus
             SYNTAX      INTEGER { active(1) }  -- subset of RowStatus
             MIN-ACCESS  read-only
             DESCRIPTION
                   "Write access is not required, and only one of the
                   six enumerated values for the RowStatus textual
                   convention need be supported, specifically:
                   active(1)."
         ::= { frnetservCompliances 1 }
   
      -- Units of Conformance
  
   frnetservLportGroup  OBJECT-GROUP
         OBJECTS { frLportNumPlan, frLportContact, frLportLocation,
                   frLportType,
                   frLportAddrDLCILen, frLportVCSigProtocol,
                   frLportVCSigPointer }
         STATUS  current
         DESCRIPTION
               "A collection of objects providing information applicable
               to a Frame Relay Logical Port."
         ::= { frnetservGroups 1 }
  
   frnetservMgtVCSigGroup  OBJECT-GROUP
         OBJECTS { frMgtVCSigProced,
                   frMgtVCSigUserN391,
                   frMgtVCSigUserN392,
                   frMgtVCSigUserN393,
                   frMgtVCSigUserT391,
                   frMgtVCSigNetN392,
                   frMgtVCSigNetN393,
                   frMgtVCSigNetT392,
                   frMgtVCSigNetnN4,
                   frMgtVCSigNetnT3,
                   frMgtVCSigUserLinkRelErrors,
                   frMgtVCSigUserProtErrors,
                   frMgtVCSigUserChanInactive,
                   frMgtVCSigNetLinkRelErrors,
                   frMgtVCSigNetProtErrors,
                   frMgtVCSigNetChanInactive }
         STATUS  current
         DESCRIPTION
               "A collection of objects providing information
               applicable to the
               Local In-Channel Signaling Procedures used for a
               UNI/NNI logical port."
         ::= { frnetservGroups 2 }
  
   frnetservPVCEndptGroup  OBJECT-GROUP
         OBJECTS { frPVCConnectIndexValue,
                   frPVCEndptInMaxFrameSize, frPVCEndptInBc,
                   frPVCEndptInBe, frPVCEndptInCIR,
                   frPVCEndptOutMaxFrameSize, frPVCEndptOutBc,
                   frPVCEndptOutBe, frPVCEndptOutCIR,
                   frPVCEndptConnectIdentifier, frPVCEndptRowStatus,
                   frPVCEndptRcvdSigStatus, frPVCEndptInFrames,
                   frPVCEndptOutFrames, frPVCEndptInDEFrames,
                   frPVCEndptInExcessFrames, frPVCEndptOutExcessFrames,
                   frPVCEndptInDiscards,
                   frPVCEndptInOctets, frPVCEndptOutOctets }
         STATUS  current
         DESCRIPTION
               "A collection of objects providing information application
               to a Frame Relay PVC end-point."
         ::= { frnetservGroups 3 }
  
   frnetservPVCConnectGroup  OBJECT-GROUP
         OBJECTS { frPVCConnectAdminStatus, frPVCConnectL2hOperStatus,
                   frPVCConnectH2lOperStatus, frPVCConnectL2hLastChange,
                   frPVCConnectH2lLastChange,
                   frPVCConnectRowStatus }
         STATUS  current
         DESCRIPTION
               "A collection of objects providing information applicable
               to a Frame Relay PVC connection."
         ::= { frnetservGroups 4 }
  
   frnetservAccountPVCGroup  OBJECT-GROUP
         OBJECTS { frAccountPVCSegmentSize, frAccountPVCInSegments,
                   frAccountPVCOutSegments }
         STATUS  current
         DESCRIPTION
               "A collection of objects providing accounting
               information application
               to a Frame Relay PVC end-point."
         ::= { frnetservGroups 5 }
  
   frnetservAccountLportGroup  OBJECT-GROUP
         OBJECTS { frAccountLportSegmentSize, frAccountLportInSegments,
                   frAccountLportOutSegments }
         STATUS  current
         DESCRIPTION
               "A collection of objects providing accounting
               information application
               to a Frame Relay logical port."
         ::= { frnetservGroups 6 }
  
  
   END
