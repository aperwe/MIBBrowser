-- ***************************************************************
         --  *************************************************************
         --   *********************************************************** 
         --                       SIEMENS AG   OEN AN
         --
         --           This mib is the entry point in the SMI for
         --               Siemens OEN AN SNMP based products
         --   *********************************************************** 
         --  *************************************************************
         -- ***************************************************************
         --
         --
         AN-MIB DEFINITIONS ::= BEGIN

         IMPORTS
             enterprises
                    FROM RFC1155-SMI
 
             OBJECT-TYPE
                   FROM RFC-1212;


         --  LAST-UPDATED "971215, Version 1.0"
         --  ORGANIZATION "Siemens AG, OEN AN BE"
         --  CONTACT-INFO
         --  "      Angelika Svoboda
         --         OEN AN BE 12
         --         Tel.: +49 89 722 48063
         --
         --         Thomas Vetter
         --         OEN AN BE 12
         --         Tel.: +49 89 722 44323
         --
         --         Reinhard Schleimer
         --         Fa. MC-RATIO GmbH
         --         c/o OEN AN BE 12
         --         Tel.: +49 89 722 24131 "


         -- **************************************************************
         --                      Versions and Revisions
         -- **************************************************************
         --
         -- ---------|--------|----------------------------|--------|-----
         -- 97-12-15 |/main/1 | First draft                |        |
         -- ---------|--------|----------------------------|--------|-----
         -- 98-03-31 |/main/2 | Move attributes /          |OK000444| WKop
         --          |        | xldSnmMibVersion           |        |
         --          |        | AgentVersion to an.mib     |        |
         -- ---------|--------|----------------------------|--------|-----
         -- **************************************************************
         --         PLEASE CHANGE THE DATE OF LAST-UPDATE ABOVE !!!
         -- **************************************************************

         --
         -- Types
         --
 
         -- The textual convention like SNMPv2-TC. See rfc1903.
         --
         DisplayString ::= OCTET STRING (SIZE (0..255))


         --
         --
         --
         -- Definition of main groups of the XLD an.mib
         --
         --
         --


         sni               OBJECT IDENTIFIER ::= { enterprises 231 }

         siemensUnits      OBJECT IDENTIFIER ::= { sni 7 }

         oenProductMibs    OBJECT IDENTIFIER ::= { siemensUnits 1 }

         --
         -- This is the OEN AN entry point
         --
         an                OBJECT IDENTIFIER ::= { oenProductMibs 2 }

         test                OBJECT IDENTIFIER ::= { oenProductMibs 3 }

         --
         -- These are the nodes for current OEN AN products
         --
         -- 1. XPressLink D
         --    A node to hold management information about fiber optic
         --    based ATM multiplexer systems with ADSL technology.
         --
         xld               OBJECT IDENTIFIER ::= { an 1 }

         onu               OBJECT IDENTIFIER ::= { xld 1 }

         olt               OBJECT IDENTIFIER ::= { xld 2 }






         xldOnuSnmVersion OBJECT IDENTIFIER ::= { onu 100 }
 
         -- xldOnuSnmVersionMib OBJECT-TYPE   ===>>>> Version > V1.0
         xldSnmMibVersion OBJECT-TYPE
            SYNTAX        DisplayString (SIZE (0..10))
            ACCESS        read-only
            STATUS        mandatory
            DESCRIPTION
                 " Version of ONU SNMP MIB. The string is 'V1.0'. "
 
            --DEFAULT next-function-async     fsnOnuSnmVersionNext
            --DEFAULT get-function-async      fsnOnuSnmVersionGet
 
            ::= { xldOnuSnmVersion 1 }
 
         -- xldOnuSnmVersionAgent OBJECT-TYPE   ===>>>> Version > V1.0
         xldSnmAgentVersion OBJECT-TYPE
            SYNTAX        DisplayString (SIZE (0..10))
            ACCESS        read-only
            STATUS        mandatory
            DESCRIPTION
                 " Version of ONU SNMP agent. The string is 'V1.0'. "
 
            --DEFAULT next-function-async     fsnOnuSnmVersionNext
            --DEFAULT get-function-async      fsnOnuSnmVersionGet
 
            ::= { xldOnuSnmVersion 2 }

  
         END
