--  *************************************************************
             --   ***********************************************************
             --    *********************************************************
             --    **                                                     **
             --    **  The ICN WN BA E12 SNMP-Team proudly presents:      **
             --    **                                                     **
             --    **                  The XLDV11 MIB                     **
             --    **                                                     **
             --    *********************************************************
             --   ***********************************************************
             --  *************************************************************
             -- ***************************************************************
             --
             --

                 


             -- The XLDV11-MIB comprises managed entities for different versions of XLD
             -- starting from XLDV1.1U.
             -- The snmpAgent of the ONU implements the features of the XLD version.
             -- Therefore the MIB objects are labeled with the corresponding XLD Version.
             -- Managed objects with no labels are objects which have been already defined
             -- in the xldv1.mib. The labels are the following :
             --      XLDV1.1U  
             --      XLDV1.1L (relevant for the Ethernet NT)
             --      XLDV1.2A or XLDV1.2B (formerly XLDV1.0.3)
             --      XLDV1.3A or XLDV1.3B 
             --      XLDV1.x  (formerly XLDV1.1,late feature not yet supported).
             --      XLDV1.3N SNMP IF for TMN45020

             --
             -- include header files needed by the method routines
             --

             --FORCE-INCLUDE <csnnopo1.h>
             --FORCE-INCLUDE <asn1.h>
             --FORCE-INCLUDE <mib.h>
             --FORCE-INCLUDE <snmpdefs.h>
             --FORCE-INCLUDE <snmpstat.h>
             --FORCE-INCLUDE <csnnopo2.h>
             --FORCE-INCLUDE <mibleaf.h>
             --FORCE-INCLUDE <mibhand.h>

             -- DEFAULT test-function-async     null_test_async
             -- DEFAULT next-function-async     null_next_async
             -- DEFAULT set-function-async      null_set_async
             -- DEFAULT get-function-async      null_get_async


          XLDV11-MIB DEFINITIONS ::= BEGIN


             IMPORTS
                 IpAddress, TimeTicks
                       FROM RFC1155-SMI
                 OBJECT-TYPE
                       FROM RFC-1212
                 TRAP-TYPE
                       FROM RFC-1215
                 onu 
                    FROM AN-MIB;


       -- ***************
       -- Ip Addres is defined as: 
       -- IpAddress ::=                    ( in network byte order )
       -- [APPLICATION 0]
       -- IMPLICIT OCTET STRING ( SIZE (4) )
       -- ************


             --  VERSION XLDV1.1U and following
             --  ORGANIZATION "Siemens AG, OEN AN BE"
             --  CONTACT-INFO
             --  "      Angelika Svoboda
             --         OEN AN BE 12
             --         Tel.: +49 89 722 48063
             --
             --         Thomas Vetter
             --         OEN AN BE 12
             --         Tel.: +49 89 722 44323
             --
             --         Rolf Kuckelkorn
             --         OEN AN BE 16
             --         Tel.: +49 89 722 57287
             --
             -- **************************************************************
             --                      Versions and Revisions
             -- **************************************************************
             -- Date      Changes                                    MR/Author
             -- --------------------------------------------------------------
             -- 98-01-29  First Issue
             -- --------------------------------------------------------------
             --  all comments about changes between deleted,
             -- -------------------------------------------------------------
             -- 99-02-01  CHG: rename SnmTmnEventFlowControl to           V13N asvo 
             --                SnmTrapFlowControl, 
             --                analog SnmLctEventFlowControl
             --           ADD: SnmTmnMaxNumber, SnmTmnSpecificIndex,
             --                SnmAlarmTrapPollingFlag, SnmLctSessionPollingFlag
             --                TmnTable
	     --           ADD: xldv11xxxControlReqResult attributes
	     --           CHG: xldv11E3nTrailTraceReceive to ro
	     --           CHG: following tables are ro (no download) :
	     --                AtmCrossConnectTable, VplTpTable, VpcTpTable,
	     --                VccTpTable, VcCrossConnectTable, VclTpTable,
	     --                ContinuityCheckVplTpTable,
	     --                ContinuityCheckVclTpTable, HwEquipHolderTable
             --           ADD: xldv11TrxxxControlReqResult traps,
	     --                xldv11TrControlStatusBusy
	     --           ADD: value requestBusy, setDataFailed in
	     --                type Xldv11ControlReq (reject reasons)
	     --           ADD: Xldv11DbmControlReqResultLocal
	     --           ADD: Xldv11DbmControlReqResultRemote
	     --           ADD: xldv11TvRestoreResult, xldv11TrDbRestore
	     --           ADD: for configuration of inband Vpi/Vci :
	     --                xldv11InbandTmn,
	     --                for inband configureation command :
	     --                xldv11ActInbandVpi, xldv11ActInbandVci,
	     --                new values for xldv11ActControlReq :
	     --                configInbandTmn, configInbandTmnFailed,
	     --                inbandVpiExists, inbandVciExists
             -- -------------------------------------------------------------
             -- 99-02-09  CHG: new value hwuOk in xldv11HwuControlResult MR1166 asvo
             --           CHG: correct some info-LEAF text for 
	     --                xldv11ExtAlarm.. attributes
	     --           CHG: change default value for all Callp-attributes MR1179
             --                for PeakCellRateDownstream to 2Mega
             -- -------------------------------------------------------------
             -- 99-02-18  CHG: correct defaults for IbmAISOnLos,     MR 1183 V12b asvo 
             --                AdcAISOnLOS, AdcAISOnACT MR 1184
	 -- 
	 --           CHG: Sec Telnet control group:             MR 1196        
	 --                del AccessRight attribute
	 -- -------------------------------------------------------------
	 -- 99-02-18 CHG: remove information traps               review V13N asvo
	 --               xldv11TrControlStatusBusy,
	 --               xldv11TrxxxControlReqResult
	 -- -------------------------------------------------------------
	 -- 99-02-23 ADD: new sw upgrade command sucUpgrEndRequest MR 1209 V13H asvo
	 --               new result values for Xldv11SucResult,
	 --               new traps xldv11TrUpgradeEndRequestResult,
	 --               xldv11TrUnitUpgradeNotRequested
	 -- -------------------------------------------------------------
	 -- 99-02-23 CHG: syntax of ExternalTime to TimeTicks    MR 1202 V12b asvo
	 -- -------------------------------------------------------------
	 -- 99-03-01 CHG: review XLDV1.3N                                V13N asvo
	 -- -------------------------------------------------------------
	 -- 99-03-04 ADD: review XLDV1.3N : add attribute                V13N asvo
	 --               xldv11DbmPathAndFileName
	 --               replace all : "NIC" with "CPE" "nic" with "cpe"
	 -- -------------------------------------------------------------
	 -- 99-03-10 CHG: remove xldv11TmnAlarmTrapPollingFlag           V13N asvo
	 --               remove xldv11VplAISAlarm, xldv11VplLOSAlarm
	 --               remove xldv11VclAISAlarm, xldv11VclLOSAlarm
	 --               remove xldv11VccLOCAlarm, 
	 --               rename xldv11VpcLOSAlarm to xldv11VpcRDIAlarm
	 --               rename xldv11VccLOSAlarm to xldv11VccRDIAlarm
	 --          CHG: access of VplAlarmSeverityIndex is read-write
	 --               istead of not-accessible
	 -- -------------------------------------------------------------
	 -- 99-03-15 CHG: range of xldv11TmnIndex is 1..11               V13N asvo
	 --          CHG: comment in xldv11TvSnmLctSession
	 --          CHG: define Xldv11TerminalType, Xldv11ChannelType
	 --               used in xldv11TmnTable
	 --          ADD: comment about command value in all ControlReq
	 --               attributes
	 -- -------------------------------------------------------------
	 -- 99-03-17 CHG: requestBusy to aswRequestBusy ,       V13N  tv
	 --               because compiler problem
	 -- -------------------------------------------------------------
	 -- 99-04-07 ADD: sucUpgrNotComplete (234)              V13N  tv
	 -- -------------------------------------------------------------
	 -- 99-04-14 ADD: trap TrVplCcCreation(TRAPID 45)       V13N asvo
	 --          DEL: remove trap TrVplTpReload (TRAPID 140)
	 --          CHG: range of xldv11VplIndex,
	 --               range of xldv11VpcIndex,
	 --               range of xldv11VccIndex,
	 --               range of xldv11AccTerminationPointA,
	 --               range of xldv11AccTerminationPointZ,
	 --               range of xldv11AccEthVpcIndex,      
	 --               range of xldv11AccEthVccIndex,      
	 --               range of xldv11VplCvpIndexSource,   
	 --               range of xldv11VplCvpIndexSink,   
	 --               range of xldv11VpcVplIndex,
	 --               range of xldv11VccVpcIndex,
	 --               range of xldv11VcxEthVpcIndex,
	 --               range of xldv11VcxEthVccIndex
	 --          ADD: sucUpgrTaskCreationFault(1038),
	 --               sucUpgrDbAccessFault(1039)
	 --          DEL: sucUpgrNotComplete (sucUpgradeNotComplete exists
	 --               already)
	 -- -------------------------------------------------------------
	 -- 99-04-20 ADD: Definition of Unsigned16 as TEXTUAL   V13N wkop
	 --               CONVENTION (necessary to create the
	 --               file snmpinfo.dat)
	 -- -------------------------------------------------------------
	 -- 99-04-27 CHG: Comment of xldv11AdcMaxRateDnCfg and  V13N wkop
	 --               xldv11AdcMinRateDnCfg:
	 --               Range = 32 .. 8160 kBit/s
	 -- -------------------------------------------------------------
	 --               !!!!!!!!!!!!!!!!!!!!!!!!!!!!!!!!!!!!!!!
	 --               ATTETNTION::  BRANCH V13N from /main/86 
	 --               !!!!!!!!!!!!!!!!!!!!!!!!!!!!!!!!!!!!!!!
	 -- -------------------------------------------------------------
	 -- 99-05-05 CHG: some attribs set to RO instead of RW   V13n tv
	 -- -------------------------------------------------------------
	 -- 99-05-12 ADD: some attribs :  				V13n tv
	 --               suStandaloneStartupFinished(3)
	 --               cacTlmResourceConflict             
	 --               cacBwOverflowUp                   
	 --               cacBwOverflowDown                
	 --               cacLineBlockedByTlm             
	 --               cacVbrtNrtTypeConflict         
	 --               cacTrafficTypeConflict        
	 --               cacTrafficDirectionConflict  
	 -- -------------------------------------------------------------
	 -- 99-05-18 ADD: attribs for Void:  			V13n tv
	 --               actEthInvalidSubnetMaskOrIpAddr (316)
	 --         
	 -- -------------------------------------------------------------
	 -- 99-06-09 ADD: some new response-codes for Upd.COnfigFile V13n tv
	 --     	      snmUpFtpIpAddrFailed    (104) 
	 --               snmUpFtpAcountFailed    (105)
	 --               snmUpFtpPasswdFailed    (106)
	 --               snmUpFtpDescPathFailed  (107)
	 -- --------------------------------------------------------------
	 -- 99-06-18 ADD: trap variable xldv11TvBackupResult     V13n wkop
	 --     	      to xldv11TrDbBackup             
	 --          ADD: trap variable xldv11TvRestoreResult    V13n wkop
	 --     	      to xldv11TrDbRestore             
	 -- --------------------------------------------------------------
	 -- 99-06-21 MOD: ActPeakCellRateUp/Down no limitation   V13n tv
	 -- --------------------------------------------------------------
	 -- 99-06-24 ADD: new Type Xldv11Latency                 V13n tv
	 --          CHG: xldv11TvHweResetType to Xldv11StartupType
	 -- --------------------------------------------------------------
	 -- 99-06-27 CHG: AlarmStates corr. to TrapIds          MR1438  tv
	 -- --------------------------------------------------------------
	 -- 99-06-27 ADD: StartupResult    to SnmpControl       MR1378  tv
	 -- --------------------------------------------------------------
	 -- 99-07-01 ADD: Trap variables to TrVplCcCreation    MR1480 wkop
	 -- --------------------------------------------------------------
	 -- 99-07-01 ADD: New MIB attribute                    MR1489 wkop
         --               xldv11NeExternalTime45020
	 -- --------------------------------------------------------------
	 -- 99-07-05 CHG: Range of ... set to Unsigned32       MR1479 wkop
         --                 xldv11ActPeakCellRateUpstream
         --                 xldv11ActPeakCellRateDownstream
         --                 xldv11ActSustainableCellRateUpstream
         --                 xldv11ActSustainableCellRateDownstream
         --                 xldv11ActEthVciPeakCellRateUpstream
         --                 xldv11VplPeakCellRateUpstream
         --                 xldv11VplPeakCellRateDownstream
         --                 xldv11VplSustainableCellRateUpstream
         --                 xldv11VplSustainableCellRateDownstream
         --                 xldv11VclPeakCellRateUpstream
         --                 xldv11VclPeakCellRateDownstream
         --                 xldv11VclSustainableCellRateUpstream
         --                 xldv11VclSustainableCellRateDownstream
         --                 xldv11EthVciPeakCellRateUpstream
         --                 xldv11EthSustainableCellRateUpstream
	 -- --------------------------------------------------------------
	 -- 99-07-07 COR:  Correct SYNTAX of                   MR1504 wkop
         --                xldv11SnmCallpPollingFlag
	 -- --------------------------------------------------------------
	 -- 99-07-12 COR:  Correct trap variable values of     MR1547 wkop
         --                trap xldv11TrDbRestore and xldv11TrDbBackup:
         --          DEL:  Remove 2'nd trap variable 
         --                xldv11TvRestoreResult of xldv11TrDbRestore
         --          CHG:  enum values of Xldv11DbmResultType
         --          CHG:  enum values of SYNTAX of xldv11TvRestoreResult
	 -- --------------------------------------------------------------
         --          ADD:  enum values of Xldv11AlarmSeverity  MR1516 wkop
         --                = noAlarming(5)                       
	 -- --------------------------------------------------------------
	 -- 99-07-13 CHG:  VxWorks limitations for file and    MR1550 wkop
         --                path length for FTP actions: 
         --                xldv11SucPathName [121] and 
         --                xldv11SucFileName [33]
	 -- --------------------------------------------------------------
	 -- 99-07-19 ADD: some new response-codes for          MR1568 Muhn
	 --     	  actControlReq:        
	 -- 	          cacBwWarningUp          (367)
	 --               cacBwWarningDown        (368)
	 --               cacMbsWarningUp         (369)
	 --               cacMbsWarningDown       (370)
	 -- --------------------------------------------------------------
	 -- 99-07-20 CHG:  Change enum values of type          MR1583 wkop
	 --     	   Xldv11DbuReadStatus
         --                Spelling of ATM-CC control request  MR1577 wkop
         --                result 'VbrnrtTypeConflict' is not 
         --                correct
	 -- --------------------------------------------------------------
	 -- 99-07-22 ADD:  xldv11TrPltTestResult,              MR1537 wkop
	 --     	   xldv11TrAltTestResult
         --          DEL:  xldv11TrTestResult 
         --          ADD:  value 'commandFailed' to 
         --                xldv11PltControlReqResult and to
         --                xldv11AltControlReqResult 
	 -- --------------------------------------------------------------
	 -- 99-08-18 CHG:  Change lower range for all          MR1667 Muhn
	 --     	   MBS up   objects = 1..1500,
         --                MBS down objects = 1..18800, 
         --                New default value for  
         --                MBS up, down = 32  
	 -- --------------------------------------------------------------
	 -- 99-09-28 ADD: add control request DbReload    MR1728 tv
	 -- --------------------------------------------------------------
         -- 99-10-12 ADD: info-line SYNTAX for xldv11HwUnitTable       asvo
         --          ADD: info-line VALUE for xldv11S3nPathTraceExpect
	 -- --------------------------------------------------------------
         -- 99-10-27 CHG: range 1..155000000 of                MR1792 asvo
         --               xldv11ActSustainableCellRateUpstream
         --               xldv11ActSustainableCellRateDownstream
	 --          ADD: time stamp attributes               MR1737  asvo
         --                  xldv11SnmControlTimeStamp
         --                  xldv11ActControlTimeStamp
         --                  xldv11CocControlTimeStamp
         --                  xldv11HwuControlTimeStamp
         --                  xldv11RiControlTimeStamp
         --                  xldv11AdcCtrlControlTimeStamp
         --                  xldv11VdcCtrlControlTimeStamp
         --                  xldv11PltControlTimeStamp
         --                  xldv11AltControlTimeStamp
         --                  xldv11AlmControlTimeStamp
         --                  xldv11RstControlTimeStamp
         --                  xldv11DbuControlTimeStamp
         --                  xldv11SucControlTimeStamp
         --                  xldv11DbmControlTimeStamp
	 -- --------------------------------------------------------------
         -- 99-11-10 MR1731 : Enhanced SW upgrade (progress indication) asvo
	 --          ADD: SW upgrade task table:    
	 --                  xldv11SutTaskTable
	 --          ADD: new values in Xldv11ControlReq :
         --                  ,sutNotInitialized 
	 --                  ,sutToDo
         --                  ,sutStarted
         --                  ,sutCrashed 
         --                  ,sutFtpDone
         --                  ,sutDone
         --                  ,sutReadyForReset
         --                  ,sutObsolete
	 --          ADD: new attribute xldv11PiuUpgradeResult
	 -- --------------------------------------------------------------
         -- 99-11-11 MR1731 : Enhanced SW upgrade (progress indication) asvo
         --          ADD: xldv11SutTimeStamp
	 --          CHG: change the type of xldv11TvSucResult to 
	 --               Xldv11ControlReq to be consistent with content of
	 --               xldv11SucControlReqResult attribute
	 -- --------------------------------------------------------------
         -- 99-11-23 MR1731 : Move SW upgrade (progress indication)   wkop
         --                   table after Secure Telnet object
	 -- --------------------------------------------------------------
         -- 99-11-24 MR1731 : Modify value in Xldv11ControlReq:       wkop
         --                   sutNotInitialized -> sutInitialized
	 -- --------------------------------------------------------------
         -- 99-12-16 MR1731 : Cor: add missing entry in sequence of   tv
         --                   SutTaskEntry : TimeStamps
	 -- --------------------------------------------------------------
         -- 99-12-20        : Add some adaptations for HPOpenView     wkop
         --                   compatibility
	 -- --------------------------------------------------------------
         -- 99-12-20        : Add again adaptations for HPOpenView    wkop
	 -- --------------------------------------------------------------
         -- 99-12-22 Mr1868 : Add xldv11VpcEmSpecific rw attribute    asvo
         -- --------------------------------------------------------------
         -- 00-01-12 MR1870 : Xldv11EthNtMode: remove value           Muhn
         --                                    pppTunneling
         -- --------------------------------------------------------------
         -- 00-01-14 MR1851 : Add: rjResetNotSupported to             Muhn
         --                        DESCRIPTION of sucControlReq
         -- --------------------------------------------------------------
         -- 00-01-31 MR1897 : Add: new type Xldv11TrapIds             asvo
	 --                   CHG: use new Type for
	 --                        xldv11TvAlmNatureOfAlarm,
	 --                        xldv11AlmNatureOfAlarm,
	 --                        xldv11AlmSevTrapId,
	 --                        xldv11AlmFiltTrapId
         -- --------------------------------------------------------------
         -- 00-02-08 MR1897 : Add: new type entry trMaxTrapId        tv
	 --                        Xldv11TrapIds
         -- --------------------------------------------------------------
         -- 00-04-05 MR1968 : Add: suInProgress to type              Muhn
         --                        Xldv11StartupResult
         -- --------------------------------------------------------------
         -- 00-06-07 MR1934 : Add: changeHwUnitForced,               asvo
	 --                        hwuForcedChangeNotAllowed
	 --                   CHG: range to 1..512 of
	 --                        xxxContainedUnitAddr attributes
         -- --------------------------------------------------------------
         -- 00-06-27 MR1934 : Add: hwuUpgradeRunning                 Muhn
         -- --------------------------------------------------------------
         -- 00-07-10 MR2210 : Add: enum-Type for ADSL data rates     asvo
         -- --------------------------------------------------------------

	 -- **************************************************************
	 -- **************************************************************


	 -- **************************************************************
	 --             Information Block for Version Control
	 --             of MIB nodes and attributes (template)
	 -- **************************************************************
	 --
	 -- info-NODE:      xldv11Node             ==>> use line info-NODE
	 -- info-LEAF:      xldv11Attribute        ==>> or  line info-LEAF
	 -- info-TREE:      xldv11TreeName         ==>> e.g. xldv11Callp 
	 -- info-TRAPTYPE:  alarm/event            ==>> for traps only
	 -- info-ACC:       [ro,rw,nac]
	 -- info-INDEX:     Index variable of table
	 -- info-SYNTAX:    [INTEGER,Integer32,DisplayString,Enum-types]
	 -- info-VALUE:     minValue..maxValue; attrValue[(V1.0->)]
	 -- info-TRAPID:    trap-ID
	 -- info-TRAPVAR:   xldv11TvTrapVar1, xldv11TvTrapVar2
	 -- info-COMMENT:   Comment 1. Comment 2. ("." == line feed !) 
	 -- info-ROU:       GET  SET [db,gf,up,tm,hm,ut,so,sn,cp]
	 -- info-FAILEDSRC: hwm, tlm, callp       ==>> for alarm traps only
	 -- info-FAILEDOBJ: [hwm] LU155,LUDSX3,LUPON,CMU,SUAD,SUVD,LTAD,
	 -- info-FAILEDOBJ: [hwm] LIETH,LI25,NTAD,NTVD,
	 -- info-FAILEDOBJ: [tlm] S1n(= STM-1 NePPTP),S1f,S3n,E3n,D3n,S3f,
	 -- info-FAILEDOBJ: [tlm] D3f,E3f,Pon,Adc(= Adc-PPTP),Adr,Vdc,Vdr,
	 -- info-FAILEDOBJ: [tlm] Ibm(= Ibm-PPTP),Eth,Tca  
	 -- info-FAILEDOBJ: [callp] VpcTP, VccTP  
	 -- info-IMPL:      [V1.0,V1.1U,V1.2A,V1.2B,V1.3A,V1.3B,V1.x]:[rw,ro,*]
	 --                                           (* == like info-ACC)
	 -- info-IMPL:      e.g.: V1.1U-> (= all vers. begin. with V1.1U)
	 -- info-IMPL:      e.g.: V1.0->V1.1U V1.2B:rw->V1.3A V1.3B 
	 -- info-VERCTRL:   [GET,SET [db,asw,agent,blocked] or "-" 
	 --                             (blocked == blocked by SNMP agent)
	 --                             ("-"     == no special handling)
	 -- **************************************************************



	 xldv11 OBJECT IDENTIFIER  ::= { onu 2 }

	 -- **************************************************************
	 --             TEXTUAL-CONVENTIONs for XLDV11-MIB
	 --
	 -- use of textual convention syntax necessary for the exported
	 -- types Xldv11ControlStatus, Xldv11AdminState and Unsigned16 in
	 -- order to create the file snmpinfo.dat. For load production the
	 -- textual convention definitions are hidden by comment signs. 
	 -- **************************************************************
	 --
	 -- --------------------------------------------------------------
	 --                            States
	 -- --------------------------------------------------------------

	 -- The control status of an entity.
	 --
	 -- Xldv11ControlStatus ::= TEXTUAL-CONVENTION
	 --      STATUS current
	 --      DESCRIPTION
	 --        "This data type is used as the syntax for the control status 
	 --         attributes."
	 --      SYNTAX INTEGER {
	 --        requestIdle(1),
	 --        requestBusy(2),
	 --        requestPassed(3),
	 --        requestFailed(4)
	 --      }
	 Xldv11ControlStatus ::=
	     INTEGER {
		 requestIdle(1),
		 requestBusy(2),
		 requestPassed(3),
		 requestFailed(4)
	     }

	 -- The operating state of an entity.
	 --
	 Xldv11OperState ::=
	     INTEGER {
		 enabled(1),
		 disabled(2)
	     }

	 -- Indicates whether a slot is empty or not.
	 --
	 Xldv11SlotStatus ::=
	     INTEGER {
		 unknown(0),
		 used(1),
		 empty(2)
	     }

	 -- The administrative state of an entity.
	 --
	 -- Xldv11AdminState ::= TEXTUAL-CONVENTION
	 --      STATUS current
	 --      DESCRIPTION
	 --        "This data type is used as the syntax for the admin state 
	 --         attributes."
	 --      SYNTAX INTEGER {
	 --        unlocked(1),
	 --        locked(2)
	 --      }
	 Xldv11AdminState ::=
	     INTEGER {
		 unlocked(1),
		 locked(2)
	     }

	 -- The availability status of a hardware unit
	 --
	 Xldv11AvailStatus ::=
	     INTEGER {
		     available(1),
		     failed(2),
		     degraded(3),
		     offline(4),
		     notInstalled(5),
		     dependency(7)
	-- only internal states
	--               noDependency(6),
	--               noRestart(8),
	--               warmRestart(9),
	--               coldRestart(10),
	--               reloadRestart(11),
	--               noUpgrade(12),
	--               upgrade(13)
	    }

	 -- The attribute reflects upon the internal states of the
	 -- Central Office Modem.
	 --
	 Xldv11LinkState ::=
	     INTEGER {
		 quiet(0),
		 idle(1),
		 train(2),
		 active(3),
		 download(4),
		 remoteDownload(6),
		 sleepMode(7),
		 unknown(255)
	     }

	 -- The log read status.
	 --
	 Xldv11DbuReadStatus ::=
	     INTEGER {
		 dbuReadComplete(1041),
		 dbuReadFailed(1042),
		 dbuFileCreationFailed(1043),
		 dbuFileTransmissionFailed(1044)
	     }
 
	 -- The access mode of a telnet session
	 --
	 Xldv11TelnetAccess ::=
	     INTEGER {
		 read(1),
		 trace(2),
		 write(3),
		 noAccess(4)
	     }

	 -- The status of a telnet session
	 --
	 Xldv11TvTelnetSessionStatus ::=
	     INTEGER {
		 running(1),
		 stopped(2)
	     }

	 -- The type of endpoint for continuity check
	 --
	 Xldv11EndpointType ::=
	     INTEGER { 
		 source  (1),
		 sink    (2),
		 both    (3)
		 }

	 -- The type of reset result
	 --
	 Xldv11RstResult ::=
	     INTEGER { 
		 requestFailed (4)
		 }

	 -- --------------------------------------------------------------
	 --                           Types
	 -- --------------------------------------------------------------

	 --
	 --
	 -- The textual convention like SNMPv2-TC. See rfc1903.
	 -- In the XldV1 system we terminate all strings with '\0'.
	 --
	 --
	 DisplayString ::= OCTET STRING (SIZE (0..255))


	 -- The textual convention for a 32 bit integer value.
	 --
	 Integer32 ::= INTEGER (-2147483648..2147483647)


	 -- The textual convention for a 32 bit integer index , 
	 -- positive, beginning with value 1.
	 -- Unsigned16 ::= TEXTUAL-CONVENTION
	 --    STATUS current
	 --    DESCRIPTION
	 --      "Textual convention for a 16 bit integer value."
	 --    SYNTAX INTEGER (0..65535)

	 Unsigned16::= INTEGER (0..65535)

	 -- The textual convention for a 32 bit integer index , 
	 -- positive, beginning with value 0, used for timer counts.
	 -- MR1202a

	 Unsigned32 ::= INTEGER (0..2147483647)


	 -- A general hardware unit type identifier.
	 --
	 Xldv11HwUnitType ::=
	     INTEGER {
		 equipment(1),
		 equipmentHolder(2),
		 plugInUnit(3)
	     }

	 -- The type of a TLM interface.
	 --
	 Xldv11IfType ::=
	     INTEGER {
		 s1n(1),         -- XLDV1.0  for stm1nePPTP
		 s1f(2),         -- XLDV1.0  for stm1fePPTP
		 adc(3),         -- XLDV1.0  for adslcPPTP
		 adr(4),         -- XLDV1.0  for adslrPPTP
		 ibm(5),         -- XLDV1.0  for ibmPPTP
		 tca(6),         -- XLDV1.0  for all TC Adaptors
		 pon(7),         -- XLDV1.1U for BPON
		 vdc(8),         -- XLDV1.1  for vdslcPPTP
		 vdr(9),         -- XLDV1.1  for vdslrPPTP
		 eth(10),        -- XLDV1.1L for LIETH PPTP
		 d3n(11),        -- XLDV1.3A for d3nePPTP
		 d3f(12),        -- XLDV1.3A for d3fePPTP
		 e3n(13),        -- XLDV1.3A for e3nePPTP
		 e3f(14),        -- XLDV1.3A for e3fePPTP
		 s3n(15),        -- XLDV1.3A for sts3nePPTP
		 s3f(16)         -- XLDV1.3A for sts3fePPTP
	     }

	 -- The alarm state of a TLM entity.
	 --
	 Xldv11AlarmState ::=
	     INTEGER {
		 noAlarm(0),
		 hpEBER(1),
		 hpUNEQ(2),
		 lcd(3),
		 lof(4),
		 lop(5),
		 los(6),
		 msAIS(7),
		 msEBER(8),
		 msRDI(9),
		 msSD(10),
		 pAIS(11),
		 pRDI(12),
		 rsEBER(13),
		 slm(14),
		 tim(15),
		 actFault(16),
		 hiBER(43),
		 lomf(102),
		 fail(103),
		 lps(104),
		 xmissionErr(105),
		 ais(114),
		 rdi(115),
		 plcpLof(116),
		 plcpRDI(117),
		 internalFault(123),
		 immMNR(130),          
		 lpr(131),
		 lol(132),
		 wrongServiceConfigData(141)
	     }

	 -- This type selects the mode for the trap flow control :
	 --   noTraps  : no traps are sent
	 --   allTraps : all traps are sent
	 --   noEvents : only alarms but no events are sent
	 --   noAlarms : only events but no alarms are sent
	 --
	 Xldv11SuppressionType ::=
	     INTEGER {
		 noTraps(1),
		 allTraps(2),
		 noEvents(3),
		 noAlarms(4)
	     }
	 --
	 -- This type selects the traffic type of a VPC.    
	 -- for the trap flow control
	 --
	 Xldv11TrafficType ::=
	     INTEGER {
		 cbr    (1),              -- constant bit rate, default
		 ubr    (2),              -- unspecified bit rate,
		 nrtVbr (3),              -- used in V1.3 !!
		 rtVbr  (4)               -- used in V1.3 !!
	     }


	 --  new for V1.2A
	 --  this type selects the traffic direction
	 --
	Xldv11TrafficDirection ::=
	       INTEGER {
		     bidirectional (1),
		     upstream      (2),
		     downstream    (3) }

	Xldv11TrafficPriority ::=
	       INTEGER {
		     low(1),
		     high(2)
		     }
	 -- 
	 -- This type selects the equipment holder type.    
	 --
	 Xldv11EqhType ::=
	     INTEGER {
		 shelf(1),    -- unused in V11 up
		 slot(2),   
		 basicShelf(3),
		 extendedShelf(4),
		 ntAdslShelf(5), 
		 ntVdslShelf(6),
		 cpeShelf(7)
	     }
	 --
	 --
	 -- This type specifies the different line types
	 --
	 Xldv11LineType ::=
	     INTEGER {
		 other(1),
		 shortSingleMode(2),          -- s1n, s3n
		 mediumSingleMode(3),         -- s1n, s3n
		 longSingleMode(4),           -- s1n, s3n
		 coax(5),                     -- s1n, s3n
		 utp(6),                      -- s1n, s3n
		 e3direct(7),                 -- e3n 
		 ds3plcp(8)                   -- d3n
	     }

     
	  -- Default value of all current xldv11Adc... attributes of table
	  -- xldv11AdcPPTPTable
	  --
	  -- THIS CUR DEFAULT WILL NOT BE USED IN THE MIB, BUT WILL BE USED BY 
	  -- THE ONU SW TO SIGNALIZE A DEFAULT VALUE TO THE TMN_OS
	  -- Xldv11AdcCurDefault ::=
	  --     INTEGER {
	  --             adcCurDefault(32767)
	  --          }

	  -- This type represents the latency for ADSL modems
	  --
	  Xldv11Latency ::=
	      INTEGER {  low                  (0),
			 high                 (1) }


	 -- TLM S1n/S3n excessive bit error check threshold
	 --
	 Xldv11S1nS3nEberThreshold ::=
	     INTEGER {
		 exp10E3(1),
		 exp10E4(2),
		 exp10E5(3),
		 noSupervision(255)
	     }

	 -- TLM S1n/S3n signal degration check threshold
	 --
	 Xldv11S1nS3nSDThreshold ::=
	     INTEGER {
		 exp10E5(3),
		 exp10E6(4),
		 exp10E7(5),
		 exp10E8(6),
		 exp10E9(7),
		 noSupervision(255)
	     }

	 -- The value of this object identifies the severity
	 -- of an alarm that has occured.
	 --
	 Xldv11AlarmSeverity ::=
	     INTEGER {
		 critical(1),
		 major(2),
		 minor(3),
		 warning(4),
		 noAlarming(5)
	     }

	 -- The value of this object identifies the range
	 -- of the alarm severity index.
	 --
	 Xldv11AlmSevProfileIndex ::= INTEGER (1..40) 

	 -- The value of this object identifies the range
	 -- of the alarm filtering index.
	 --
	 Xldv11AlmFiltProfileIndex ::= INTEGER (1..40) 

	 -- This type specifies remote inventory result type
	 --
	 Xldv11RiResultType ::=
	     INTEGER {
		 riRemoteInventoryComplete(1),
		 riFileCreationFailed(2),
		 riFileTransmissionFailed(3)
	     }
	 --
	 -- This type specifies row status type
	 --
	 Xldv11RowStatus ::=
	     INTEGER {
		 create(1),
		 delete(2)
	     }
	 --
	 -- This type specifies result of a DbmControlReq
	 --
	 Xldv11DbmResultType ::=
	      INTEGER {
		  localBackupOk(1051),
		  remoteBackupOk(1052),
		  localBackupFailed(1053),
		  remoteBackupFailed(1054),
		  flashAccessFailed(1055),
		  dbReadFailed(1056)
		  }
	 --
	 -- This type specifies the coding type of a E3/Ds3 interface
	 --
	 Xldv11CodingType ::=
	     INTEGER {
		 e3HDB3(1),
		 dsx3B3ZS(2)
	     }
	 --
	 -- This type specifies the external alarm state
	 --
	 Xldv11ExtAlarmActivityState ::=
	     INTEGER {
		 undeterminate(0),
		 on(1),
		 off(2)
	     }

	 -- This type specifies the empty cell variant
	 --
	 Xldv11EmptyCellType ::=
	     INTEGER {
		 idle(1),
		 unassigned(2)
	     }

	 -- Indicates the log to be read.
	 --
	 Xldv11LogType ::=
	     INTEGER {
		  hwmLog(1),
		  sweLog(2),
		  swTraceLog(3)
	     }

	 -- Indicates the validity of a request.
	 --
	 Xldv11SucAllOfType ::=
	     INTEGER {
		  sucUpgrSingle(1),
		  sucUpgrAll(2)
	     }

	 -- Indicates the validity of a request.
	 --
	 Xldv11ResetLevel ::=
	     INTEGER {
		  plugInUnit(3),
		  system(4)
	     }

	 -- Indicates the downstream data rate.
	 --
	 Xldv11VdcRateDn ::=
	     INTEGER { rateDn2(2),
		       rateDn4(4),
		       rateDn6(6),
		       rateDn8(8),
		       rateDn12(12),
		       rateDn16(16),
		       rateDn24(24),
		       rateDn32(32),
		       rateDn48(48),
		       rateDn64(64) }

	 -- Indicates the upstream data rate.
	 --
	 Xldv11VdcRateUp ::=
	     INTEGER { rateUp1(1),
		       rateUp2(2),
		       rateUp4(4),
		       rateUp8(8),
		       rateUp12(12),
		       rateUp16(16) }

	 -- Indicates the latency period in downstream direction.
	 --
	 Xldv11VdcLatencyDn ::=
	     INTEGER { latencyDn0(0),
		       latencyDn2(2),
		       latencyDn4(4),
		       latencyDn8(8),
		       latencyDn12(12),
		       latencyDn16(16),
		       latencyDn20(20),
		       latencyDn32(32) }

	 -- Indicates the latency period in upstream direction.
	 --
	 Xldv11VdcLatencyUp ::=
	     INTEGER { latencyUp0(0),
		       latencyUp2(2),
		       latencyUp4(4),
		       latencyUp8(8),
		       latencyUp10(10),
		       latencyUp20(20) }

	 -- Indicates the configured power boost mode/power adaptation option.
	 --
	 Xldv11VdcPowerBoostAdaptationType ::=
	     INTEGER { suEnabled(1),
		       ntEnabled(2),
		       bothEnabled(3),
		       bothDisabled(4) }

	 -- Indicates the configured VDSL mode option.
	 --
	 Xldv11VdcVdslMode ::=
	     INTEGER { adslFriendly(1),
		       vdslEfficient(2) }

	 -- Indicates the configured PSD mask option.
	 --
	 Xldv11VdcPsdMask ::=
	     INTEGER { m1(1),
		       m2(2) }

	 -- This type represents the Ethernet NT modes
	 --
	 Xldv11EthNtMode ::=
	     INTEGER { bridging    (1),
		       routing     (2)}
	
	 -- This type represents the received payload types
	 -- of e3n interface
	 --
	 Xldv11E3nPayloadType ::=
	     INTEGER { unequipped  (1),
		       nonSpecific (2),
		       atm         (3)}

	 -- This type represents Problems with Connection Admision Control 
	 --
	 Xldv11CACProblemType ::=
	     INTEGER {  bandwidthUpstreamWarning    (1),
			bandwidthDownstreamWarning  (2),
			mbsUpstreamWarning          (3), 
			mbsDownstreamWarning        (4) }

	 -- This type represents the alarm state for Callp objects
	 --
	 Xldv11CallpAlarmState ::=
	     INTEGER {  noAlarm      (1),
			alarmPresent (2) }

	 -- This type represents the alarm state for Callp termination point objects
	 --
	 Xldv11TpAlarmState ::=
	     INTEGER {  noAlarm              (1),
			upstreamAlarm        (2),
			downstreamAlarm      (3),
			upAndDownstreamAlarm (4) }

	 -- This type represents the requester for SW upgrade
	 --
	 Xldv11Requester ::=
	     INTEGER {  tmn (1),
			hwm (2) }


         -- Type for ADSL up and downstream data rates .
         -- The enumeration shows the mapping
         -- Bitrates in kbits/sec (kbps) and
         -- ATM Cellrate in cells/sec (cps).
         -- k means 1000.
         -- The bit rate of an ATM cell is 424=53*8 bits/sec.
         --
         Xldv11AdslDataRateDown ::=
               INTEGER {
                 kbps32Cps75       (   1 ),
                 kbps64Cps150      (   2 ),
                 kbps96Cps226      (   3 ),
                 kbps128Cps301     (   4 ),
                 kbps160Cps377     (   5 ),
                 kbps192Cps452     (   6 ),
                 kbps224Cps528     (   7 ),
                 kbps256Cps603     (   8 ),
                 kbps288Cps679     (   9 ),
                 kbps320Cps754     (  10 ),
                 kbps352Cps830     (  11 ),
                 kbps384Cps905     (  12 ),
                 kbps416Cps981     (  13 ),
                 kbps448Cps1056    (  14 ),
                 kbps480Cps1132    (  15 ),
                 kbps512Cps1207    (  16 ),
                 kbps544Cps1283    (  17 ),
                 kbps576Cps1358    (  18 ),
                 kbps608Cps1433    (  19 ),
                 kbps640Cps1509    (  20 ),
                 kbps672Cps1584    (  21 ),
                 kbps704Cps1660    (  22 ),
                 kbps736Cps1735    (  23 ),
                 kbps768Cps1811    (  24 ),
                 kbps800Cps1886    (  25 ),
                 kbps832Cps1962    (  26 ),
                 kbps864Cps2037    (  27 ),
                 kbps896Cps2113    (  28 ),
                 kbps928Cps2188    (  29 ),
                 kbps960Cps2264    (  30 ),
                 kbps992Cps2339    (  31 ),
                 kbps1024Cps2415   (  32 ),
                 kbps1056Cps2490   (  33 ),
                 kbps1088Cps2566   (  34 ),
                 kbps1120Cps2641   (  35 ),
                 kbps1152Cps2716   (  36 ),
                 kbps1184Cps2792   (  37 ),
                 kbps1216Cps2867   (  38 ),
                 kbps1248Cps2943   (  39 ),
                 kbps1280Cps3018   (  40 ),
                 kbps1312Cps3094   (  41 ),
                 kbps1344Cps3169   (  42 ),
                 kbps1376Cps3245   (  43 ),
                 kbps1408Cps3320   (  44 ),
                 kbps1440Cps3396   (  45 ),
                 kbps1472Cps3471   (  46 ),
                 kbps1504Cps3547   (  47 ),
                 kbps1536Cps3622   (  48 ),
                 kbps1568Cps3698   (  49 ),
                 kbps1600Cps3773   (  50 ),
                 kbps1632Cps3849   (  51 ),
                 kbps1664Cps3924   (  52 ),
                 kbps1696Cps4000   (  53 ),
                 kbps1728Cps4075   (  54 ),
                 kbps1760Cps4150   (  55 ),
                 kbps1792Cps4226   (  56 ),
                 kbps1824Cps4301   (  57 ),
                 kbps1856Cps4377   (  58 ),
                 kbps1888Cps4452   (  59 ),
                 kbps1920Cps4528   (  60 ),
                 kbps1952Cps4603   (  61 ),
                 kbps1984Cps4679   (  62 ),
                 kbps2016Cps4754   (  63 ),
                 kbps2048Cps4830   (  64 ),
                 kbps2080Cps4905   (  65 ),
                 kbps2112Cps4981   (  66 ),
                 kbps2144Cps5056   (  67 ),
                 kbps2176Cps5132   (  68 ),
                 kbps2208Cps5207   (  69 ),
                 kbps2240Cps5283   (  70 ),
                 kbps2272Cps5358   (  71 ),
                 kbps2304Cps5433   (  72 ),
                 kbps2336Cps5509   (  73 ),
                 kbps2368Cps5584   (  74 ),
                 kbps2400Cps5660   (  75 ),
                 kbps2432Cps5735   (  76 ),
                 kbps2464Cps5811   (  77 ),
                 kbps2496Cps5886   (  78 ),
                 kbps2528Cps5962   (  79 ),
                 kbps2560Cps6037   (  80 ),
                 kbps2592Cps6113   (  81 ),
                 kbps2624Cps6188   (  82 ),
                 kbps2656Cps6264   (  83 ),
                 kbps2688Cps6339   (  84 ),
                 kbps2720Cps6415   (  85 ),
                 kbps2752Cps6490   (  86 ),
                 kbps2784Cps6566   (  87 ),
                 kbps2816Cps6641   (  88 ),
                 kbps2848Cps6716   (  89 ),
                 kbps2880Cps6792   (  90 ),
                 kbps2912Cps6867   (  91 ),
                 kbps2944Cps6943   (  92 ),
                 kbps2976Cps7018   (  93 ),
                 kbps3008Cps7094   (  94 ),
                 kbps3040Cps7169   (  95 ),
                 kbps3072Cps7245   (  96 ),
                 kbps3104Cps7320   (  97 ),
                 kbps3136Cps7396   (  98 ),
                 kbps3168Cps7471   (  99 ),
                 kbps3200Cps7547   ( 100 ),
                 kbps3232Cps7622   ( 101 ),
                 kbps3264Cps7698   ( 102 ),
                 kbps3296Cps7773   ( 103 ),
                 kbps3328Cps7849   ( 104 ),
                 kbps3360Cps7924   ( 105 ),
                 kbps3392Cps8000   ( 106 ),
                 kbps3424Cps8075   ( 107 ),
                 kbps3456Cps8150   ( 108 ),
                 kbps3488Cps8226   ( 109 ),
                 kbps3520Cps8301   ( 110 ),
                 kbps3552Cps8377   ( 111 ),
                 kbps3584Cps8452   ( 112 ),
                 kbps3616Cps8528   ( 113 ),
                 kbps3648Cps8603   ( 114 ),
                 kbps3680Cps8679   ( 115 ),
                 kbps3712Cps8754   ( 116 ),
                 kbps3744Cps8830   ( 117 ),
                 kbps3776Cps8905   ( 118 ),
                 kbps3808Cps8981   ( 119 ),
                 kbps3840Cps9056   ( 120 ),
                 kbps3872Cps9132   ( 121 ),
                 kbps3904Cps9207   ( 122 ),
                 kbps3936Cps9283   ( 123 ),
                 kbps3968Cps9358   ( 124 ),
                 kbps4000Cps9433   ( 125 ),
                 kbps4032Cps9509   ( 126 ),
                 kbps4064Cps9584   ( 127 ),
                 kbps4096Cps9660   ( 128 ),
                 kbps4128Cps9735   ( 129 ),
                 kbps4160Cps9811   ( 130 ),
                 kbps4192Cps9886   ( 131 ),
                 kbps4224Cps9962   ( 132 ),
                 kbps4256Cps10037  ( 133 ),
                 kbps4288Cps10113  ( 134 ),
                 kbps4320Cps10188  ( 135 ),
                 kbps4352Cps10264  ( 136 ),
                 kbps4384Cps10339  ( 137 ),
                 kbps4416Cps10415  ( 138 ),
                 kbps4448Cps10490  ( 139 ),
                 kbps4480Cps10566  ( 140 ),
                 kbps4512Cps10641  ( 141 ),
                 kbps4544Cps10716  ( 142 ),
                 kbps4576Cps10792  ( 143 ),
                 kbps4608Cps10867  ( 144 ),
                 kbps4640Cps10943  ( 145 ),
                 kbps4672Cps11018  ( 146 ),
                 kbps4704Cps11094  ( 147 ),
                 kbps4736Cps11169  ( 148 ),
                 kbps4768Cps11245  ( 149 ),
                 kbps4800Cps11320  ( 150 ),
                 kbps4832Cps11396  ( 151 ),
                 kbps4864Cps11471  ( 152 ),
                 kbps4896Cps11547  ( 153 ),
                 kbps4928Cps11622  ( 154 ),
                 kbps4960Cps11698  ( 155 ),
                 kbps4992Cps11773  ( 156 ),
                 kbps5024Cps11849  ( 157 ),
                 kbps5056Cps11924  ( 158 ),
                 kbps5088Cps12000  ( 159 ),
                 kbps5120Cps12075  ( 160 ),
                 kbps5152Cps12150  ( 161 ),
                 kbps5184Cps12226  ( 162 ),
                 kbps5216Cps12301  ( 163 ),
                 kbps5248Cps12377  ( 164 ),
                 kbps5280Cps12452  ( 165 ),
                 kbps5312Cps12528  ( 166 ),
                 kbps5344Cps12603  ( 167 ),
                 kbps5376Cps12679  ( 168 ),
                 kbps5408Cps12754  ( 169 ),
                 kbps5440Cps12830  ( 170 ),
                 kbps5472Cps12905  ( 171 ),
                 kbps5504Cps12981  ( 172 ),
                 kbps5536Cps13056  ( 173 ),
                 kbps5568Cps13132  ( 174 ),
                 kbps5600Cps13207  ( 175 ),
                 kbps5632Cps13283  ( 176 ),
                 kbps5664Cps13358  ( 177 ),
                 kbps5696Cps13433  ( 178 ),
                 kbps5728Cps13509  ( 179 ),
                 kbps5760Cps13584  ( 180 ),
                 kbps5792Cps13660  ( 181 ),
                 kbps5824Cps13735  ( 182 ),
                 kbps5856Cps13811  ( 183 ),
                 kbps5888Cps13886  ( 184 ),
                 kbps5920Cps13962  ( 185 ),
                 kbps5952Cps14037  ( 186 ),
                 kbps5984Cps14113  ( 187 ),
                 kbps6016Cps14188  ( 188 ),
                 kbps6048Cps14264  ( 189 ),
                 kbps6080Cps14339  ( 190 ),
                 kbps6112Cps14415  ( 191 ),
                 kbps6144Cps14490  ( 192 ),
                 kbps6176Cps14566  ( 193 ),
                 kbps6208Cps14641  ( 194 ),
                 kbps6240Cps14716  ( 195 ),
                 kbps6272Cps14792  ( 196 ),
                 kbps6304Cps14867  ( 197 ),
                 kbps6336Cps14943  ( 198 ),
                 kbps6368Cps15018  ( 199 ),
                 kbps6400Cps15094  ( 200 ),
                 kbps6432Cps15169  ( 201 ),
                 kbps6464Cps15245  ( 202 ),
                 kbps6496Cps15320  ( 203 ),
                 kbps6528Cps15396  ( 204 ),
                 kbps6560Cps15471  ( 205 ),
                 kbps6592Cps15547  ( 206 ),
                 kbps6624Cps15622  ( 207 ),
                 kbps6656Cps15698  ( 208 ),
                 kbps6688Cps15773  ( 209 ),
                 kbps6720Cps15849  ( 210 ),
                 kbps6752Cps15924  ( 211 ),
                 kbps6784Cps16000  ( 212 ),
                 kbps6816Cps16075  ( 213 ),
                 kbps6848Cps16150  ( 214 ),
                 kbps6880Cps16226  ( 215 ),
                 kbps6912Cps16301  ( 216 ),
                 kbps6944Cps16377  ( 217 ),
                 kbps6976Cps16452  ( 218 ),
                 kbps7008Cps16528  ( 219 ),
                 kbps7040Cps16603  ( 220 ),
                 kbps7072Cps16679  ( 221 ),
                 kbps7104Cps16754  ( 222 ),
                 kbps7136Cps16830  ( 223 ),
                 kbps7168Cps16905  ( 224 ),
                 kbps7200Cps16981  ( 225 ),
                 kbps7232Cps17056  ( 226 ),
                 kbps7264Cps17132  ( 227 ),
                 kbps7296Cps17207  ( 228 ),
                 kbps7328Cps17283  ( 229 ),
                 kbps7360Cps17358  ( 230 ),
                 kbps7392Cps17433  ( 231 ),
                 kbps7424Cps17509  ( 232 ),
                 kbps7456Cps17584  ( 233 ),
                 kbps7488Cps17660  ( 234 ),
                 kbps7520Cps17735  ( 235 ),
                 kbps7552Cps17811  ( 236 ),
                 kbps7584Cps17886  ( 237 ),
                 kbps7616Cps17962  ( 238 ),
                 kbps7648Cps18037  ( 239 ),
                 kbps7680Cps18113  ( 240 ),
                 kbps7712Cps18188  ( 241 ),
                 kbps7744Cps18264  ( 242 ),
                 kbps7776Cps18339  ( 243 ),
                 kbps7808Cps18415  ( 244 ),
                 kbps7840Cps18490  ( 245 ),
                 kbps7872Cps18566  ( 246 ),
                 kbps7904Cps18641  ( 247 ),
                 kbps7936Cps18716  ( 248 ),
                 kbps7968Cps18792  ( 249 ),
                 kbps8000Cps18867  ( 250 ),
                 kbps8032Cps18943  ( 251 ),
                 kbps8064Cps19018  ( 252 ),
                 kbps8096Cps19094  ( 253 ),
                 kbps8128Cps19169  ( 254 ),
                 kbps8160Cps19245  ( 255 )
                 }

             Xldv11AdslDataRateUp ::=
               INTEGER {
                 kbps32Cps75       (   1 ),
                 kbps64Cps150      (   2 ),
                 kbps96Cps226      (   3 ),
                 kbps128Cps301     (   4 ),
                 kbps160Cps377     (   5 ),
                 kbps192Cps452     (   6 ),
                 kbps224Cps528     (   7 ),
                 kbps256Cps603     (   8 ),
                 kbps288Cps679     (   9 ),
                 kbps320Cps754     (  10 ),
                 kbps352Cps830     (  11 ),
                 kbps384Cps905     (  12 ),
                 kbps416Cps981     (  13 ),
                 kbps448Cps1056    (  14 ),
                 kbps480Cps1132    (  15 ),
                 kbps512Cps1207    (  16 ),
                 kbps544Cps1283    (  17 ),
                 kbps576Cps1358    (  18 ),
                 kbps608Cps1433    (  19 ),
                 kbps640Cps1509    (  20 ),
                 kbps672Cps1584    (  21 ),
                 kbps704Cps1660    (  22 ),
                 kbps736Cps1735    (  23 ),
                 kbps768Cps1811    (  24 ),
                 kbps800Cps1886    (  25 )
                 }



	 -- --------------------------------------------------------------
	 --                       Trap type
	 -- --------------------------------------------------------------
             -- This type represents the traps and their IDs
             --
             Xldv11TrapIds ::=
                 INTEGER { trNoTrapId                ( 0 ),
                           trHpExcBER                ( 1 ),
                           trHpUNEQ                  ( 2 ),
                           trLcd                     ( 3 ),
                           trLof                     ( 4 ),
                           trLop                     ( 5 ),
                           trLos                     ( 6 ),
                           trMsAIS                   ( 7 ),
                           trMsExcBER                ( 8 ),
                           trMsRDI                   ( 9 ),
                           trMsSD                    ( 10 ),
                           trPAIS                    ( 11 ),
                           trPRDI                    ( 12 ),
                           trRsExcBER                ( 13 ),
                           trSlm                     ( 14 ),
                           trTim                     ( 15 ),
                           trActFault                ( 16 ),
                           trReplaceableUnitTypeMismatch ( 17 ),
                           trReplaceableUnitFailure      ( 18 ),
                           trReplaceableUnitProblem      ( 19 ),
                           trReplaceableUnitNotInstalled ( 20 ),
                           trReplaceableUnitSwMismatch   ( 21 ),
                           trReplaceableUnitReset        ( 22 ),
                           trReplaceableUnitResetEnd     ( 23 ),
                           trStartupEnd           ( 24 ),
                           trLctSession           ( 25 ),
                           trAgentRunning         ( 26 ),
                           trRstResult            ( 27 ),
                           trPltTestResult        ( 28 ),
                           trStateChangeAdmin     ( 29 ),
 
                           trStateChangeOper      ( 30 ),
                           trChangeRate           ( 31 ),
                           trCmuReadyForReset     ( 32 ),
                           trAltTestResult        ( 33 ),
                           trActivateLoadResult   ( 34 ),
                           trPUUpgradeSucc        ( 35 ),
                           trUpgradeCancelled     ( 36 ),
 
                           trFtpError             ( 38 ),
 
                           trSweLogRead           ( 40 ),
                           trHwmLogRead           ( 41 ),
                           trTraceLogRead         ( 42 ),

                           trActCcReload          ( 44 ),
                           trVplCcCreation        ( 45 ),
                           trVplCcDeletion        ( 46 ),
 
                           trObjCreate                  ( 100 ),
                           trObjDelete                  ( 101 ),
                           trLOMF                       ( 102 ),

                           trXmissionErr                ( 105 ),
                           trVpcTpAIS                   ( 106 ),
                           trVpcTpRDI                   ( 107 ),
                           trVccTpAIS                   ( 108 ),
                           trVccTpRDI                   ( 109 ),
                           trExternalAlarm              ( 110 ),
                           trUnitReadyForReset          ( 111 ),
                           trHwuControl                 ( 112 ),
                           trReplaceableUnitRemoved     ( 113 ),
                           trAIS                        ( 114 ),
                           trRDI                        ( 115 ),
                           trPlcpLof                    ( 116 ),
                           trPlcpRDI                    ( 117 ),
                           trRemInvReady                ( 118 ),
                           trDbBackup                   ( 119 ),
                           trSwVersionSet               ( 120 ),
                           trReadSAPSContentFileReady   ( 121 ),
                           trReplaceableUnitSwMissing   ( 122 ),
                           trInternalFault              ( 123 ),
                           trAttributeValueChange       ( 124 ),
                           trVplTpCreation              ( 125 ),
                           trVplTpDeletion              ( 126 ),
                           trVclCcCreation              ( 127 ),
                           trVclCcDeletion              ( 128 ),
 
                           trImmMNR                     ( 130 ),
                           trLpr                        ( 131 ),
                           trLol                        ( 132 ),
                           trAtmLayerMultiAlarm         ( 135 ),
                           trTelnetSession              ( 136 ),
 
                           trVplCACProblem              ( 137 ),
                           trVplTpCACProblem            ( 138 ),
                           trVclCACProblem              ( 139 ),
                           trVplTpReload                ( 140 ),
                           trWrongServiceConfigData     ( 141 ),
                           trReplaceableUnitPlugged     ( 142 ),
                           trReplaceableUnitUnplugged   ( 143 ),
                           trStateChangeOperExt         ( 144 ),
                           trLOC                        ( 145 ),
                           trContinuityCheckVplTpEntryCreated ( 146 ),
                           trContinuityCheckVplTpEntryDeleted ( 147 ),
                           trContinuityCheckVclTpEntryCreated ( 148 ),
                           trContinuityCheckVclTpEntryDeleted ( 149 ),
                           trDbRestore                   ( 150 ),
                           trUpgradeEndRequestResult     ( 151 ),
                           trUnitUpgradeNotRequested     ( 152 ),

 
                           -- trap ID's for Performance Management
                           trThresholdCrossingAlert     ( 200 ),
                           trHistoryDayCounters         ( 201 ),

                           -- LAST TABLE ENTRY FOR RANGE CHECK
                           -- CORRECT THIS AND 
                           -- ADD NEW VALUES ABOVE THIS LINE
                           trMaxTrapId                  ( 202 )

                           }
	 -- --------------------------------------------------------------
	 --                       Trap Var values
	 -- --------------------------------------------------------------

	 -- Describes the result of a startup.
	 --
	 Xldv11StartupResult ::=
	     INTEGER {
		 suFinished(1),
		 suFailed(2),
		 suStandaloneStartupFinished(3),
		 suInProgress(4)
	     }

	 -- Indicates the startup type.
	 --
	 Xldv11StartupType ::=
	     INTEGER {
		 warm(2),
		 cold(3),
		 reload(4),
		 cmuUpgrade(5)
	     }

	 -- Indicates a session with a connected LCT.
	 --
	 Xldv11SnmLctSession ::=
	     INTEGER {
		 connected(1),
		 disconnected(2),
		 sessionCancelled(3),
		 sessionTimeout(4),
		 onuCutSession(5)
	     }

	 -- Indicates the source of a reporting entity.
	 --
	 Xldv11RepSource ::=
	     INTEGER {
		 hwm(1),
		 tlm(2),
		 callpNni(3),
		 callpUni(4),
		 extAlarm(5),
		 vccTp(6),
		 vpcTp(7),
		 line(8),
		 vclTp(9),
		 vplTp(10),
		 vclCc(11)
	     }

	 -- Indicates the hwu control result.
	 --
	 Xldv11HwuControlResult ::=
	     INTEGER {
		 paramFaulty(11),
		 commandFailed(212),
		 objExists(1003),
		 equTypeNotAvail(1004),
		 eqhTypeNotAvail(1005),
		 piuTypeNotAvail(1006),
		 piuTypeNotAccepted(1007),
		 containingUnitNotAvail(1008),
		 objNotAvail(1009),
		 objNotEmpty(1010),
		 objNotLocked(1011),
		 objNotValid(1012),
		 hwuOk(1013)
	     }

	 -- Type of polling flags
	 --
	 Xldv11PollingFlagType ::=
	     INTEGER {
		 flagSet(1),
		 flagNotSet(2)
	     }

	 -- Type of Terminal
	 --
	 Xldv11TerminalType ::=
	     INTEGER {
		 tmn(1),
		 lct(2),
		 unknown(10)
	     }

	 -- Type of communication channel
	 --
	 Xldv11ChannelType ::=
	     INTEGER {
		 inband(1),
		 outband(2),
		 unknown(10)
	     }
	 -- --------------------------------------------------------------
	 --                          Commands
	 -- --------------------------------------------------------------


	 -- The control request commands from the TMN-OS or LCT and reject reasons.

     Xldv11ControlReq ::=
	INTEGER {
-- introduced with XLDV1.0
	  noRequest                         (1)   -- For all
	  ,warm                             (2)   -- RstControlReq
	  ,cold                             (3)   -- RstControlReq
	  ,reload                           (4)   -- RstControlReq
	  ,commExecStarted                  (5)   -- For all
	  ,rjUpgRunning                     (6)   -- RstControlReq
	  ,rjRstRunning                     (7)   -- RstControlReq
	  ,rjPiuNotAvail                    (8)   -- RstControlReq
	  ,rjResetNotSupported              (9)   -- RstControlReq,
						  -- SucControlReq  
	  ,loopDiagRequest                  (10)  -- PltControlReq
	  ,paramFaulty                      (11)  -- For all
	  ,loopTestRequest                  (12)  -- AltControlReq
	  ,loopTestBusy                     (13)  -- PltControlReq,
	  ,loopTestReject                   (14)  -- PltControlReq,
	  ,createCC                         (19)  -- ActControlReq
	  ,deleteCC                         (20)  -- ActControlReq
	  ,createAllCC                      (21)  -- ActControlReq
						  -- obsolete from 1.3N

	  ,actVpiNniFaulty                  (22)  -- ActControlReq
	  ,actVpiUniFaulty                  (23)  -- ActControlReq
	  ,actPortLocationIdFaulty          (24)  -- ActControlReq
	  ,actControlReqFaulty              (25)  -- ActControlReq
	  ,lineNotEnabled                   (26)  -- ActControlReq
	  ,ccExists                         (27)  -- ActControlReq
	  ,dbuReadRequest                   (28)  -- DbuControlReq
	  ,sucUpgrStartRequest              (29)  -- SucControlReq
	  ,sucActivateLoad                  (31)  -- SucControlReq
	  ,sucUpgrMissParameter             (32)  -- SucControlReq
-- MR 1728
	  ,dbReload                         (33)  -- RstControlReq 

-- do not change the sequence of enums above this line
-- this is for compatibility with TMN os V1.0 !!

-- new Requests add below this line !!!!!

-- introduced with XLDV1.1
	  ,snmUpdateSnmpConfigFile          (100) -- SnmControlReq
	  ,snmUpdateComplete                (101) -- SnmControlReq
	  ,snmUpdateFailed                  (102) -- SnmControlReq
	  ,snmFtpError                      (103) -- SnmControlReq
	  ,snmUpFtpIpAddrFailed             (104) -- SnmControlReq
	  ,snmUpFtpAcountFailed             (105) -- SnmControlReq
	  ,snmUpFtpPasswdFailed             (106) -- SnmControlReq
	  ,snmUpFtpDescPathFailed           (107) -- SnmControlReq

	  ,createVplCC                      (110) -- ActControlReq
	  ,deleteVplCC                      (111) -- ActControlReq
	  ,createVclCC                      (112) -- ActControlReq
	  ,deleteVclCC                      (113) -- ActControlReq
	  ,createVplTp                      (114) -- ActControlReq
	  ,deleteVplTp                      (119) -- ActControlReq

	  ,actPeakCellRateUpstreamFaulty    (130) -- ActControlReq
	  ,actPeakCellRateDownstreamFaulty  (131) -- ActControlReq
	  ,actCellDelayVariationUpstreamFaulty  (132) -- ActControlReq
	  ,actCellDelayVariationDownstreamFaulty(133) -- ActControlReq
	  ,actTrafficTypeFaulty             (134) -- ActControlReq
	  ,actInsufficientBw                (135) -- ActControlReq
	  ,vplTpExists                      (136) -- ActControlReq
	  ,createVplTpDelayed               (137) -- ActControlReq
	  ,actSCRUpstreamFaulty             (138) -- ActControlReq
	  ,actSCRDownstreamFaulty           (139) -- ActControlReq
	  ,actMBSUpstreamFaulty             (140) -- ActControlReq
	  ,actMBSDownstreamFaulty           (141) -- ActControlReq
	  ,actVplTpNotExisting              (142) -- ActControlReq
	  ,actTrafficDirectionFaulty        (143) -- ActControlReq
	  ,actVciNniFaulty                  (144) -- ActControlReq
	  ,actVciUniFaulty                  (145) -- ActControlReq
	  ,configAtmf                       (146) -- Calp
	  ,configAtmfFailed                 (147) -- Calp
	  ,actLineBlocked                   (148) -- ActControlReq

	  ,loopBackRequest                  (150) -- AlbControlReq
	  ,loopBackBusy                     (151) -- AlbControlReq
	  ,loopBackReject                   (152) -- AlbControlReq

	  ,createHwUnit                     (160) -- HwuControlReq
	  ,deleteHwUnit                     (161) -- HwuControlReq
	  ,changeHwUnitForced               (162) -- HwuControlReq

	  ,connectNt                        (170) -- HwnControlReq
	  ,disconnectNt                     (171) -- HwnControlReq
	  ,ntPiuIndexNotAvail               (172) -- HwnControlReq
	  ,ntPiuIndexNotValid               (173) -- HwnControlReq
	  ,ntPiuPortNotAvail                (174) -- HwnControlReq
	  ,ntPiuPortAlreadyConnected        (175) -- HwnControlReq
	  ,onuPiuIndexNotAvail              (176) -- HwnControlReq
	  ,onuPiuIndexNotValid              (177) -- HwnControlReq
	  ,onuPiuPortNotAvail               (178) -- HwnControlReq
	  ,onuPiuPortAlreadyConnected       (179) -- HwnControlReq
	  
	  ,activateData                     (190) -- Adc/VdcControlReq
	  ,resourceProblem                  (191) -- Adc/VdcControlReq
	  ,vpProblem                        (192) -- Adc/VdcControlReq
	  ,resourceProblemUpstream          (193) -- AdcControlReq
	  ,resourceProblemDownstream        (194) -- AdcControlReq
	  ,vpProblemUpstream                (195) -- AdcControlReq 
	  ,vpProblemDownstream              (196) -- AdcControlReq
	  ,bandwidthUpstreamWarning         (197) -- AdcControlReq
	  ,bandwidthDownstreamWarning       (198) -- AdcControlReq
	  ,mbsUpstreamWarning               (199) -- AdcControlReq
	  ,mbsDownstreamWarning             (200) -- AdcControlReq
		

	 ,riSingleBoard                     (205) -- RiControlReq
	 ,riAllData                         (206) -- RiControlReq

	 ,updateAlmList                     (210) -- AlmControlReq
	 ,updateFiltList                    (211) -- AlmControlReq
	 ,commandFailed                     (212) -- AlmControlReq
	 ,startSendingAlarms                (213) -- AlmControlReq   (V1.2B)
	 ,noCurrentAlarms                   (214) -- AlmControlReq   (V1.2B)

	 ,backupDb                          (220) -- DbmControlReq   (V1.3H)
	 ,localBackupOk                     (221) -- DbmControlReq   (V1.3H)
	 ,remoteBackupOk                    (222) -- DbmControlReq   (V1.3H)
	 ,localBackupFailed                 (223) -- DbmControlReq   (V1.3H)
	 ,remoteBackupFailed                (224) -- DbmControlReq   (V1.3H)
	 ,flashAccessFailed                 (225) -- DbmControlReq   (V1.3H)
	 ,dbReadFailed                      (226) -- DbmControlReq   (V1.3H)

	 ,sucReadSAPSContentFile            (230) -- SucControlReq
	 ,sucGetSwVersions                  (231) -- SucControlReq
	 ,sucGetSwVersionsFailed            (232) -- SucControlReq
	 ,sucUpgrEndRequest                 (233) -- SucControlReq   (V1.3N)
	 ,sucUpgrTaskCreationFault          (234) -- SucControlReq   (V1.3N)
	 ,sucUpgrDbAccessFault              (235) -- SucControlReq   (V1.3N)

	 ,wrongAdminState                   (240) -- AdcControlReq

-- new for V1.2A
-- tv        ,configEth                     (250) 
-- tv    ,configEthFailed                   (251)
-- tv    ,configEthDelayed                  (252
	 ,vpiUniNotExisting                 (253) -- EthernetConfigReq
	 ,modeInvalid                       (254) -- EthernetConfigReq
	 ,vpiUniValueFaulty                 (255) -- EthernetConfigReq
	 ,vciTrafficTypeInvalid             (256) -- EthernetConfigReq
	 ,peakCellRateUpstreamFaulty        (257) -- EthernetConfigReq
	 ,vciUniValueFaulty                 (258) -- EthernetConfigReq
	 ,sustainableCellRateUpstreamFaulty (259) -- EthernetConfigReq
	 ,maximumBurstSizeUpstreamFaulty    (260) -- EthernetConfigReq


 -- new for the Eth changes by tv
	 ,createEthVplCC                    (300)
	 ,createEthVclCC                    (301)
	 ,configEth                         (302)
	 ,configEthFailed                   (303)

	 ,ethModeInvalid                    (305)
	 ,ethVpiUniNotExisting              (306)
	 ,ethVciUniNotExisting              (307)
	 ,ethVciTrafficTypeFaulty           (308)
	 ,ethVciPeakCellRateUpstreamFaulty  (309)
	 ,actWrongLiType                    (310)
	 ,actTrafficPriorityConflict        (311)
	 ,actSegmentEndPointUniFaulty       (312)
	 ,actSegmentEndPointNniFaulty       (313)
	 ,actVclCCExists                    (314)
	 ,actEthVplTpDeletionNotAllowed     (315)
	 ,actEthInvalidSubnetMaskOrIpAddr   (316)
	
 -- new for continuity check by asvo
	 ,continuityCheckRequest            (330)
	 ,continuityCheckBusy               (331)
	 ,continuityCheckReject             (332)

 -- new for V1.3N
	 ,requestBusy                       (340) -- user command handling
	 ,setDataFailed                     (341) -- user command handling
	 ,aswTimeout                        (342) -- user command handling

-- configuration inband Vpi/Vci
	 ,configInbandTmn                   (343) -- ActControlReq
	 ,configInbandTmnFailed             (344) -- ActControlReq
	 ,inbandVpiExists                   (345) -- ActControlReq
	 ,inbandVciExists                   (346) -- ActControlReq
	 ,createEthVplTp                    (347) -- ActControlReq
	 ,deleteEthVplTp                    (348) -- ActControlReq

 -- C A L L P  CONNECTION ADMISSION CONTROL

	  ,cacTlmResourceConflict             (360)
	  ,cacBwOverflowUp                    (361)
	  ,cacBwOverflowDown                  (362)
	  ,cacLineBlockedByTlm                (363)
	  ,cacVbrNrtTypeConflict              (364)
	  ,cacTrafficTypeConflict             (365)
	  ,cacTrafficDirectionConflict        (366)
	  ,cacBwWarningUp                     (367)
	  ,cacBwWarningDown                   (368)
	  ,cacMbsWarningUp                    (369)
	  ,cacMbsWarningDown                  (370)
   

-- values for control request result from long running commands (V1.3N)

	 ,rstRequestFailed                  (900) -- TrRstResult

	 ,tsrRequestIdle                    (901) -- TrTestResult
	 ,tsrRequestBusy                    (902)
	 ,tsrRequestPassed                  (903)
	 ,tsrRequestFailed                  (904)
	 
	 ,hwuParamFaulty                    (1001) -- TrHwuControl
	 ,hwuCommandFailed                  (1002)
	 ,hwuObjExists                      (1003)
	 ,hwuEquTypeNotAvail                (1004)
	 ,hwuEqhTypeNotAvail                (1005)
	 ,hwuPiuTypeNotAvail                (1006)
	 ,hwuPiuTypeNotAccepted             (1007)
	 ,hwuContainingUnitNotAvail         (1008)
	 ,hwuObjNotAvail                    (1009)
	 ,hwuObjNotEmpty                    (1010)
	 ,hwuObjNotLocked                   (1011)
	 ,hwuObjNotValid                    (1012)
	 ,hwuOk                             (1013)
	 ,hwuForcedChangeNotAllowed         (1014)
	 ,hwuUpgradeRunning                 (1015)

	 ,sucOk                             (1020) -- SW upgrade traps    
	 ,sucNotOk                          (1021)
	 ,sucDbAccessFailed                 (1022)
	 ,sucPiuUnlocked                    (1023)
	 ,sucTransmissionError              (1024)
	 ,sucWrongSwVersion                 (1025)
	 ,sucUnitTypeMismatch               (1026)
	 ,sucFtpTransError                  (1027)
	 ,sucFtpCrcError                    (1028)
	 ,sucSwHwMismatch                   (1029)
	 ,sucUpgrWrongAvState               (1030)
	 ,sucFepromCopyFault                (1031)
	 ,sucUpdateDescFileFailed           (1032)
	 ,sucFtpServerNoteAvailable         (1033)
	 ,sucFtpSendError                   (1034)
	 ,sucDbBackupFault                  (1035)
	 ,sucUpgradeComplete                (1036) 
	 ,sucUpgradeNotComplete             (1037)


	 ,dbuReadComplete                   (1041) -- TrxxxLogRead
	 ,dbuReadFailed                     (1042)
	 ,dbuFileCreationFailed             (1043)
	 ,dbuFileTransmissionFailed         (1044)

	 ,dbmLocalBackupOk                  (1051) -- TrDbBackup
	 ,dbmRemoteBackupOk                 (1052)
	 ,dbmLocalBackupFailed              (1053)
	 ,dbmRemoteBackupFailed             (1054)
	 ,dbmFlashAccessFailed              (1055)
	 ,dbmDbReadFailed                   (1056)

	 
	 -- SW upgrade task states
         ,sutInitialized                    (1100) -- MR1731
	 ,sutToDo                           (1101)
         ,sutStarted                        (1102)
         ,sutCrashed                        (1104)
         ,sutFtpDone                        (1108)
         ,sutDone                           (1116)
         ,sutReadyForReset                  (1132)
         ,sutObsolete                       (1164)

	 }



     -- ==============================================================
     --       M a i n   g r o u p s  of the  X L D V 1 1 - M I B
     -- ==============================================================

     xldv11SnmpMgmt OBJECT IDENTIFIER ::= { xldv11 1 }

     xldv11CallP    OBJECT IDENTIFIER ::= { xldv11 2 }

     xldv11Hwm      OBJECT IDENTIFIER ::= { xldv11 3 }

     xldv11Tlm      OBJECT IDENTIFIER ::= { xldv11 4 }

     xldv11Alarming OBJECT IDENTIFIER ::= { xldv11 5 }

     xldv11Swm      OBJECT IDENTIFIER ::= { xldv11 6 }

     xldv11Dbm      OBJECT IDENTIFIER ::= { xldv11 7 }

     xldv11Traps    OBJECT IDENTIFIER ::= { xldv11 8 }


     -- ==============================================================
     --          S N M P   M a n a g e m e n t   G r o u p 
     -- ==============================================================
     --
     --

     xldv11SnmTmnTrapFlowControl OBJECT-TYPE
	-- info-LEAF:    xldv11SnmTmnTrapFlowControl
	-- info-TREE:    xldv11SnmpMgmt
	-- info-ACC:     rw
	-- info-SYNTAX:  Xldv11SuppressionType 
	-- info-VALUE:   noTraps(1), allTraps(2),
	-- info-VALUE:   noEvents(3), noAlarms(4)
	-- info-COMMENT: Trap Flow Control flag. Flag to suppress
	-- info-COMMENT: or not autonomous messages to TMN-OS.
	-- info-ROU:     GET db  SET db 
	-- info-IMPL:    V1.3A->
	-- info-VERCTRL: V1.1U..V1.2B: GET db  SET db
	SYNTAX        Xldv11SuppressionType
	ACCESS        read-write
	STATUS        mandatory
	DESCRIPTION
	     " TMN specific flag to suppress or not autonomous messages to TMN-OS.
	       Range of values is: noTraps(1), allTraps(2),
	       noEvents(3), noAlarms(4).
	       Default is noTraps after reload or first time power up. "
	--DEFAULT test-function-async     fsnSnmTest
	--DEFAULT next-function-async     fsnSnmNext
	--DEFAULT set-function-async      fsnSnmSet
	--DEFAULT get-function-async      fsnSnmGet
	::= { xldv11SnmpMgmt 1 }

     xldv11SnmLctTrapFlowControl OBJECT-TYPE
	-- info-LEAF:    xldv11SnmLctTrapFlowControl
	-- info-TREE:    xldv11SnmpMgmt
	-- info-ACC:     rw
	-- info-SYNTAX:  Xldv11SuppressionType
	-- info-VALUE:   noTraps(1), allTraps(2),
	-- info-VALUE:   noEvents(3), noAlarms(4)
	-- info-COMMENT: Trap Flow Control flag. TMN specific flag to suppress
	-- info-COMMENT: or not autonomous messages to LCT.
	-- info-ROU:     GET db  SET db
	-- info-IMPL:    V1.3A->
	-- info-VERCTRL: V1.1U..V1.2B: GET db  SET db 
	SYNTAX        Xldv11SuppressionType
	ACCESS        read-write
	STATUS        mandatory
	DESCRIPTION
	     " TMN specific flag to suppress or not autonomous messages to LCT.
	       Range of values is: noTraps(1), allTraps(2),
	       noEvents(3), noAlarms(4).
	       Default is noTraps after reload or first time power up. "
	--DEFAULT test-function-async     fsnSnmTest
	--DEFAULT next-function-async     fsnSnmNext
	--DEFAULT set-function-async      fsnSnmSet
	--DEFAULT get-function-async      fsnSnmGet
	::= { xldv11SnmpMgmt 2 }

     xldv11SnmControlReq OBJECT-TYPE
	-- info-LEAF:    xldv11SnmControlReq
	-- info-TREE:    xldv11SnmpMgmt
	-- info-ACC:     rw
	-- info-SYNTAX:  Xldv11ControlReq
	-- info-VALUE:   snmUpdateSnmpConfigFile(command), snmUpdateComplete
	-- info-VALUE:   aswTimeout
	-- info-VALUE:   snmUpdateFailed, snmFtpError       
	-- info-COMMENT: This attribute signalizes the start of a
	-- info-COMMENT: configuration file update.
	-- info-ROU:     GET db  SET sn 
	-- info-IMPL:    V1.3A->
	-- info-VERCTRL: V1.1U..V1.2B: GET db  SET blocked 
	SYNTAX        Xldv11ControlReq
	ACCESS        read-write
	STATUS        mandatory
	DESCRIPTION
	     " This attribute signalizes the start of a configuration file
	       update.
	       Range of values is:
		  noRequest,
		  snmUpdateSnmpConfigFile,
		  snmUpdateComplete,
		  snmUpdateFailed,
		  snmFtpError .
	       Notifications :
		  xldv11TrSnmAgentRunning,
		  xldv11TrSnmLctSession. "
	--DEFAULT test-function-async     fsnSnmTest
	--DEFAULT next-function-async     fsnSnmNext
	--DEFAULT set-function-async      fsnSnmSet
	--DEFAULT get-function-async      fsnSnmGet
	::= { xldv11SnmpMgmt 3 }

     xldv11SnmControlStatus OBJECT-TYPE
	-- info-LEAF:    xldv11SnmControlStatus
	-- info-TREE:    xldv11SnmpMgmt
	-- info-ACC:     ro
	-- info-SYNTAX:  Xldv11ControlStatus
	-- info-VALUE:   requestIdle(1), requestBusy(2), requestPassed(3)
	-- info-VALUE:   requestFailed(4)
	-- info-COMMENT: Indicates the status of a control request.
	-- info-ROU:     GET db 
	-- info-IMPL:    V1.3A->
	-- info-VERCTRL: V1.1U..V1.2B: GET db
	SYNTAX        Xldv11ControlStatus
	ACCESS        read-only
	STATUS        mandatory
	DESCRIPTION
	     " This attribute indicates the status of a control request.
	       The start of an update of the configuration file will
	       only be started if the SnmControlStatus is not requestBusy.
	       Range of values is:
		  requestIdle,
		  requestBusy,
		  requestPassed,
		  requestFailed . "
	--DEFAULT next-function-async     fsnSnmNext
	--DEFAULT get-function-async      fsnSnmGet
	::= { xldv11SnmpMgmt 4 }

     xldv11SnmLctConnected OBJECT-TYPE   --XLDV1.1U
	-- info-LEAF:    xldv11SnmLctConnected
	-- info-TREE:    xldv11SnmpMgmt
	-- info-ACC:     rw
	-- info-SYNTAX:  INTEGER
	-- info-VALUE:   yes(1)..no(2) 
	-- info-COMMENT: If a LCT is connected to the ONU the attribute will be set.
	-- info-ROU:     GET db  SET sn 
	-- info-IMPL:    V1.0->
	-- info-VERCTRL: -
	SYNTAX        INTEGER {
			 yes(1),
			 no(2) }
	ACCESS        read-write
	STATUS        mandatory
	DESCRIPTION
	     " If a LCT is connected to the ONU the attribute will be set . "
	--DEFAULT test-function-async     fsnSnmTest
	--DEFAULT next-function-async     fsnSnmNext
	--DEFAULT set-function-async      fsnSnmSet
	--DEFAULT get-function-async      fsnSnmGet
	::= { xldv11SnmpMgmt 5 }

     xldv11SnmTmnConnected OBJECT-TYPE   --XLDV1.1U
	-- info-LEAF:    xldv11SnmTmnConnected
	-- info-TREE:    xldv11SnmpMgmt
	-- info-ACC:     rw
	-- info-SYNTAX:  INTEGER
	-- info-VALUE:   yes(1)..no(2)
	-- info-COMMENT: The attribute is set by TMN-OS to indicate
	-- info-COMMENT: the receipt of the trap 'startupEnd'
	-- info-ROU:     GET db  SET sn 
	-- info-IMPL:    V1.0->
	-- info-VERCTRL: -
	SYNTAX        INTEGER {
			 yes(1),
			 no(2) }
	ACCESS        read-write
	STATUS        mandatory
	DESCRIPTION
	     " The attribute is set by TMN-OS to indicate the receipt
	       of the trap 'startupEnd' . "
	--DEFAULT test-function-async     fsnSnmTest
	--DEFAULT next-function-async     fsnSnmNext
	--DEFAULT set-function-async      fsnSnmSet
	--DEFAULT get-function-async      fsnSnmGet
	::= { xldv11SnmpMgmt 6 }

     xldv11SnmMaxResponseTime OBJECT-TYPE   --XLDV1.1U
	-- info-LEAF:    xldv11SnmMaxResponseTime
	-- info-TREE:    xldv11SnmpMgmt
	-- info-ACC:     ro
	-- info-SYNTAX:  Integer32
	-- info-VALUE:   -2147483648..2147483647
	-- info-COMMENT: TMN-OS maximum wait time in sec for responses.
	-- info-ROU:     GET db 
	-- info-IMPL:    V1.0->
	-- info-VERCTRL: -
	SYNTAX        Integer32
	ACCESS        read-only
	STATUS        mandatory
	DESCRIPTION
	     " TMN-OS maximum wait time in sec for responses . "
	--DEFAULT next-function-async     fsnSnmNext
	--DEFAULT get-function-async      fsnSnmGet
	::= { xldv11SnmpMgmt 7 }

     xldv11SnmTmnMaxNumber OBJECT-TYPE   --XLDV1.3N
	-- info-LEAF:    xldv11SnmTmnMaxNumber
	-- info-TREE:    xldv11SnmpMgmt
	-- info-ACC:     ro
	-- info-SYNTAX:  Unsigned16
	-- info-VALUE:   range according to number of TMNs in
	-- info-VALUE:   SNMP configuration file
	-- info-COMMENT: TMN-OS can read out the maximum number of TMNs
	-- info-COMMENT: which are allowed to connect to the ONU
	-- info-ROU:     GET db 
	-- info-IMPL:    V1.3N->
	-- info-VERCTRL: -
	SYNTAX        Unsigned16
	ACCESS        read-only
	STATUS        mandatory
	DESCRIPTION
	     " This read-only attribute holds the maximum number of
	     TMNs which can be connected to the XLD netelement."
	--DEFAULT next-function-async     fsnSnmNext
	--DEFAULT get-function-async      fsnSnmGet
	::= { xldv11SnmpMgmt 8 }

     xldv11SnmTmnSpecificIndex OBJECT-TYPE   --XLDV1.3N
	-- info-LEAF:    xldv11SnmTmnSpecificIndex
	-- info-TREE:    xldv11SnmpMgmt
	-- info-ACC:     ro
	-- info-SYNTAX:  Unsigned16
	-- info-VALUE:   range according to number of TMNs in
	-- info-VALUE:   SNMP configuration file
	-- info-COMMENT: Each TMN-OS can read out its specific index.
	-- info-COMMENT: This index is used to access the TmnTable
	-- info-ROU:     GET db 
	-- info-IMPL:    V1.3N->
	-- info-VERCTRL: -
	SYNTAX        Unsigned16
	ACCESS        read-only
	STATUS        mandatory
	DESCRIPTION
	     " This read-only attribute holds the specific index of 
	     a TMN which can be connected to the XLD netelement."
	--DEFAULT next-function-async     fsnSnmNext
	--DEFAULT get-function-async      fsnSnmGet
	::= { xldv11SnmpMgmt 9 }

     -- The following two polling flag attributes are new for XLDV1.3N.
     -- They are used in the context of polling, discovery and alarm processing scenario.
     -- Discovery is a process where the TMN reads out the NE data to
     -- perform data sychronization between its own and the NE data.
     -- The NE sets these attributes when alarm traps have been sent or
     -- an LCT session has been terminated. 
     -- Under the assumption that traps can get lost these polling flags
     -- inform about ONU data changes and the TMN can discover the NE
     -- data.
     
     xldv11SnmCallpPollingFlag OBJECT-TYPE   --XLDV1.3N
	-- info-LEAF:    xldv11SnmCallpPollingFlag
	-- info-TREE:    xldv11SnmpMgmt
	-- info-ACC:     ro
	-- info-SYNTAX:  Xldv11CallpAlarmState
	-- info-VALUE:   noAlarm(1), alarmPresent(2)
	-- info-COMMENT: Callp specific alarm polling flag
	-- info-ROU:     GET db
	-- info-IMPL:    V1.3N->
	-- info-VERCTRL: -
	SYNTAX        Xldv11CallpAlarmState
	ACCESS        read-only
	STATUS        mandatory
	DESCRIPTION
	     " Callp provides this specific alarm polling flag.
	     Range of values : 
	     The TMN can poll this global alarm flag to see whether for
	     any Callp object an alarm is present. "
	--DEFAULT next-function-async     fsnSnmNext
	--DEFAULT get-function-async      fsnSnmGet
	::= { xldv11SnmpMgmt 10 }

     xldv11SnmLctSessionPollingFlag OBJECT-TYPE   --XLDV1.3N
	-- info-LEAF:    xldv11SnmLctSessionPollingFlag
	-- info-TREE:    xldv11SnmpMgmt
	-- info-ACC:     rw
	-- info-SYNTAX:  Xldv11PollingFlagType
	-- info-VALUE:   flagSet(1), flagNotSet(2)
	-- info-COMMENT: TMN specific Lct session polling flag
	-- info-COMMENT: Reset by TMN-OS
	-- info-ROU:     GET db SET sn
	-- info-IMPL:    V1.3N->
	-- info-VERCTRL: -
	SYNTAX        Xldv11PollingFlagType
	ACCESS        read-write
	STATUS        mandatory
	DESCRIPTION
	     " TMN specific Lct session polling flag.
	     Range of values : set(1), notSet(2).
	     The TMN can poll this flag to see whether an LCT session
	     has been terminated within the last polling period (value set).
	     During the LCT session ONU configuration data may have been
	     changed and therefore the TMN database is inconsistent.
	     The TMN can perform a discovery to sychronize the data.
	     The TMN should set the value to notSet before the discovery."
	--DEFAULT test-function-async     fsnSnmTest
	--DEFAULT next-function-async     fsnSnmNext
	--DEFAULT set-function-async      fsnSnmSet
	--DEFAULT get-function-async      fsnSnmGet
	::= { xldv11SnmpMgmt 11 }

     xldv11SnmControlReqResult OBJECT-TYPE
	-- info-LEAF:    xldv11SnmControlReqResult
	-- info-TREE:    xldv11SnmpMgmt
	-- info-ACC:     ro
	-- info-SYNTAX:  Xldv11ControlReq
	-- info-VALUE:   snmUpdateComplete, aswTimeout
	-- info-VALUE:   snmUpdateFailed, snmFtpError       
	-- info-COMMENT: specifies the result of user command
	-- info-ROU:     GET db
	-- info-IMPL:    V1.3N->
	-- info-VERCTRL: -
	SYNTAX        Xldv11ControlReq
	ACCESS        read-only
	STATUS        mandatory
	DESCRIPTION
	   " This read-only attribute informs about the result of 
	     the last user command."
	 --DEFAULT next-function-async     fsnSnmNext
	 --DEFAULT get-function-async      fsnSnmGet
	 ::= { xldv11SnmpMgmt 12 }


        xldv11SnmStartupResult OBJECT-TYPE
            -- info-LEAF:    xldv11SnmStartupResult
            -- info-TREE:    xldv11SnmpMgmt
            -- info-ACC:     ro
            -- info-SYNTAX:  Xldv11StartupResult
            -- info-VALUE:   suFinished, suFailed,
            -- info-VALUE:   suStandaloneStartupFinished,
            -- info-VALUE:   suInProgress
            -- info-COMMENT: specifies the result of startup
            -- info-ROU:     GET db
	    -- info-IMPL:    V1.3N->
            -- info-VERCTRL: -
            SYNTAX        Xldv11StartupResult
            ACCESS        read-only
            STATUS        mandatory
            DESCRIPTION
               " This read-only attribute informs about the result of
                 the last startup ."
             --DEFAULT next-function-async     fsnSnmNext
             --DEFAULT get-function-async      fsnSnmGet
             ::= { xldv11SnmpMgmt 13 }

         xldv11SnmControlTimeStamp OBJECT-TYPE
            -- info-LEAF:    xldv11SnmControlTimeStamp
            -- info-TREE:    xldv11SnmpControl
            -- info-ACC:     ro
            -- info-SYNTAX:  TimeTicks
            -- info-VALUE:   0..2Giga
            -- info-COMMENT: specifies the time stamp in seconds
            -- info-COMMENT: of the last command
            -- info-COMMENT: (end of command)
            -- info-ROU:     GET db
	    -- info-IMPL:    V1.3N->
            -- info-VERCTRL: -
            SYNTAX        TimeTicks
            ACCESS        read-only
            STATUS        mandatory
            DESCRIPTION
               " This read-only attribute informs about the time stamp
                 of the last command (end of command)."
             --DEFAULT next-function-async     fsnSnmNext
             --DEFAULT get-function-async      fsnSnmGet
             ::= { xldv11SnmpMgmt 14 }

     -- This table is valid from version XLDV1.3N.

     xldv11TmnTable OBJECT-TYPE
	-- info-NODE:    xldv11TmnTable
	-- info-TREE:    xldv11SnmpMgmt
	-- info-ACC:     nac
	-- info-SYNTAX:  SEQUENCE OF Xldv11TmnEntry
	-- info-COMMENT: Table for TMN specific data
	-- info-IMPL:    V1.3N->
	-- info-VERCTRL: -
	SYNTAX        SEQUENCE OF Xldv11TmnEntry
	ACCESS        not-accessible
	STATUS        mandatory
	DESCRIPTION
	     " The TMN table holds entries for TMN specific attributes.
	       Instances of this managed entity shall be automatically
	       SNMP configuration file has been read. "
	::= { xldv11SnmpMgmt 15 }

     xldv11TmnEntry OBJECT-TYPE
	-- info-NODE:    xldv11TmnEntry
	-- info-TREE:    xldv11SnmpMgmt
	-- info-INDEX:   xldv11TmnIndex
	-- info-ACC:     nac
	-- info-SYNTAX:  Xldv11TmnEntry
	-- info-COMMENT: An entry in the Tmn table.
	-- info-IMPL:    V1.3N->
	-- info-VERCTRL: -
	SYNTAX        Xldv11TmnEntry
	ACCESS        not-accessible
	STATUS        mandatory
	DESCRIPTION
	     " An entry in the Tmn table.
	       Notifications : none."
	INDEX         { xldv11TmnIndex }
	::= { xldv11TmnTable 1 }

     Xldv11TmnEntry ::=
	SEQUENCE { xldv11TmnIndex                 INTEGER,
		   xldv11TmnOrLctTerminal         Xldv11TerminalType,
		   xldv11TmnInOrOutBand           Xldv11ChannelType,
		   xldv11TmnConnected             INTEGER,
		   xldv11TmnTrapFlowControl       Xldv11SuppressionType,
		   xldv11TmnLctSessionPollingFlag Xldv11PollingFlagType
		   }

     xldv11TmnIndex OBJECT-TYPE
	-- info-LEAF:    xldv11TmnIndex
	-- info-TREE:    xldv11SnmpMgmt
	-- info-ACC:     ro
	-- info-SYNTAX:  INTEGER
	-- info-VALUE:   1..11 
	-- info-COMMENT: INDEX of TmnTable. Entries with same index
	-- info-COMMENT: belong to same TMN. The TMN can read its index
	-- info-COMMENT: via xldv11SnmTmnSpecificIndex
	-- info-ROU:     GET db
	-- info-IMPL:    V1.3N->
	-- info-VERCTRL: -
	SYNTAX        INTEGER (1..11)
	ACCESS        read-only
	STATUS        mandatory
	DESCRIPTION
	     " This attribute identifies the index of Tmn table.
	     Entries of the table with same index belong to the same TMN."
	--DEFAULT next-function-async     fsnTmnEntryNext
	--DEFAULT get-function-async      fsnTmnEntryGet
	::= { xldv11TmnEntry 1 }

     xldv11TmnOrLctTerminal OBJECT-TYPE
	-- info-LEAF:    xldv11TmnOrLctTerminal
	-- info-TREE:    xldv11SnmpMgmt
	-- info-ACC:     ro
	-- info-SYNTAX:  Xldv11TerminalType
	-- info-VALUE:   tmn(1), lct(2), unknown(10)
	-- info-COMMENT: specifies a LCT or TMN terminal
	-- info-ROU:     GET db
	-- info-IMPL:    V1.3N->
	-- info-VERCTRL: -
	SYNTAX        Xldv11TerminalType
	ACCESS        read-only
	STATUS        mandatory
	DESCRIPTION
	     " This attribute identifies the index of Tmn table.
	     Entries of the table with same index belong to the same TMN."
	--DEFAULT next-function-async     fsnTmnEntryNext
	--DEFAULT get-function-async      fsnTmnEntryGet
	::= { xldv11TmnEntry 2 }
 
     xldv11TmnInOrOutBand OBJECT-TYPE
	-- info-LEAF:    xldv11TmnInOrOutBand
	-- info-TREE:    xldv11SnmpMgmt
	-- info-ACC:     ro
	-- info-SYNTAX:  Xldv11ChannelType
	-- info-VALUE:   inband(1), outband(2), unknown(10)
	-- info-COMMENT: specifies whether communication is in or outband
	-- info-ROU:     GET db
	-- info-IMPL:    V1.3N->
	-- info-VERCTRL: -
	SYNTAX        Xldv11ChannelType
	ACCESS        read-only
	STATUS        mandatory
	DESCRIPTION
	     " This attribute specifies whether communication is in or outband."
	--DEFAULT next-function-async     fsnTmnEntryNext
	--DEFAULT get-function-async      fsnTmnEntryGet
	::= { xldv11TmnEntry 3 }
 
     xldv11TmnConnected OBJECT-TYPE
	-- info-LEAF:    xldv11TmnConnected
	-- info-TREE:    xldv11SnmpMgmt
	-- info-ACC:     ro
	-- info-SYNTAX:  INTEGER
	-- info-VALUE:   yes(1)..no(2) (default)
	-- info-COMMENT: indicates whether this TMN/LCT is connected
	-- info-ROU:     GET db
	-- info-IMPL:    V1.3N->
	-- info-VERCTRL: -
	SYNTAX        INTEGER {
			 yes(1),
			 no(2) }
	ACCESS        read-only
	STATUS        mandatory
	DESCRIPTION
	     " The attribute indicates whether this TMN/LCT is connected."
	--DEFAULT next-function-async     fsnTmnEntryNext
	--DEFAULT get-function-async      fsnTmnEntryGet
	::= { xldv11TmnEntry 4 }

     xldv11TmnTrapFlowControl OBJECT-TYPE
	-- info-LEAF:    xldv11TmnTrapFlowControl
	-- info-TREE:    xldv11SnmpMgmt
	-- info-ACC:     ro
	-- info-SYNTAX:  Xldv11SuppressionType 
	-- info-VALUE:   noTraps(1) (default), allTraps(2),
	-- info-VALUE:   noEvents(3), noAlarms(4)
	-- info-COMMENT: Trap Flow Control flag. Flag to suppress
	-- info-COMMENT: or not autonomous messages to TMN-OS.
	-- info-ROU:     GET db
	-- info-IMPL:    V1.3N->
	-- info-VERCTRL: -
	SYNTAX        Xldv11SuppressionType
	ACCESS        read-only
	STATUS        mandatory
	DESCRIPTION
	     " TMN specific flag to suppress or not autonomous messages to TMN-OS.
	       Range of values is: noTraps(1) (default), allTraps(2),
	       noEvents(3), noAlarms(4).
	       Default is noTraps after reload or first time power up. "
	--DEFAULT next-function-async     fsnTmnEntryNext
	--DEFAULT get-function-async      fsnTmnEntryGet
	::= { xldv11TmnEntry 5 }

     xldv11TmnLctSessionPollingFlag OBJECT-TYPE
	-- info-LEAF:    xldv11TmnLctSessionPollingFlag
	-- info-TREE:    xldv11SnmpMgmt
	-- info-ACC:     ro
	-- info-SYNTAX:  Xldv11PollingFlagType
	-- info-VALUE:   flagSet(1), flagNotSet(2) (default)
	-- info-COMMENT: TMN specific Lct session polling flag
	-- info-ROU:     GET db
	-- info-IMPL:    V1.3N->
	-- info-VERCTRL: -
	SYNTAX        Xldv11PollingFlagType
	ACCESS        read-only
	STATUS        mandatory
	DESCRIPTION
	     " TMN specific Lct session polling flag.
	     Range of values : flagSet(1), flagNotSet(2) (default)."
	--DEFAULT next-function-async     fsnTmnEntryNext
	--DEFAULT get-function-async      fsnTmnEntryGet
	::= { xldv11TmnEntry 6 }

     -- ==============================================================
     --           C a l l   P r o c e s s i n g   G r o u p
     -- ==============================================================

     -- --------------------------------------------------------------
     --              ATM Cross Connect Control subgroup
     -- --------------------------------------------------------------

     xldv11AtmCcControl OBJECT IDENTIFIER ::= { xldv11CallP 1 }
	-- info-NODE:    xldv11AtmCcControl
	-- info-TREE:    xldv11CallP 
	-- info-ACC:     nac
	-- info-IMPL:    V1.0->
	-- info-VERCTRL: -

     -- This managed entity manages the establishment and release
     -- of VP cross-connections ( e.g. VPI ) in the ATM NE.
     -- It is valid from XLDV1.1U.
     --
     -- An instance of this managed entity shall be automatically
     -- created by the ATM NE immediately following ATM NE initialization.

     xldv11ActOperationalState OBJECT-TYPE
	-- info-LEAF:    xldv11ActOperationalState
	-- info-TREE:    xldv11CallP
	-- info-ACC:     nac
	-- info-SYNTAX:  Xldv11OperState
	-- info-VALUE:   enabled(1)..disabled(2)
	-- info-COMMENT: unused
	-- info-COMMENT: Indicates whether ATM cross connect control
	-- info-COMMENT: is capable of performing its normal function.
	-- info-ROU:     GET db 
	-- info-IMPL:    V1.0->
	-- info-VERCTRL: -
	SYNTAX        Xldv11OperState
	ACCESS        not-accessible
	STATUS        mandatory
	DESCRIPTION
	     " Unused.
	       This attribute indicates whether ATM cross connect control
	       is capable of performing its normal function. Altering this
	       attribute is without reporting this state change via the
	       trap 'xldv11TrStateChangeOper'.
	       Range of values is: enabled, disabled. "
	--DEFAULT next-function-async     fsnActNext
	--DEFAULT get-function-async      fsnActGet
	::= { xldv11AtmCcControl 1 }

     xldv11ActControlReq OBJECT-TYPE
	-- info-LEAF:    xldv11ActControlReq
	-- info-TREE:    xldv11CallP
	-- info-ACC:     rw
	-- info-SYNTAX:  Xldv11ControlReq
	-- info-VALUE:   createCC(V1.0)(command), deleteCC(V1.0)(command),
	-- info-VALUE:   createAllCC(V1.0->V1.3B)(command) 
	-- info-VALUE:   actVpiNniFaulty(V1.0->), actVpiUniFaulty(V1.0->)
	-- info-VALUE:   actPortLocationIdFaulty(V1.0->), actControlReqFaulty(V1.0->)
	-- info-VALUE:   lineNotEnabled(V1.0->), ccExists(V1.0->), dbuReadRequest(V1.0->)
	-- info-VALUE:
	-- info-VALUE:   createVplCC(V1.0->)(command), deleteVplCC(V1.0->)(command),
	-- info-VALUE:   createVclCC(V1.2B->)(command),deleteVclCC(V1.2B->)(command),
	-- info-VALUE:   createVplTp(V1.2B->)(command), deleteVplTp(V1.2B->)(command)         
	-- info-VALUE:
	-- info-VALUE:   actPeakCellRateUpstreamFaulty(V1.1U, V1.3A->)
	-- info-VALUE:   actPeakCellRateDownstreamFaulty(V1.1U, V1.3A->)   
	-- info-VALUE:   actCellDelayVariationUpstreamFaulty(V1.1U, V1.3A->) 
	-- info-VALUE:   actCellDelayVariationDownstreamFaulty(V1.1U, V1.3A->)
	-- info-VALUE:   actTrafficTypeFaulty(V1.1U, V1.3A->)
	-- info-VALUE:   actInsufficientBw(V1.1U, V1.3A->),actLineBlocked(V1.3A->), 
	-- info-VALUE:   vplTpExists(V1.2B->), createVplTpDelayed(V1.2B->)               
	-- info-VALUE:   actSCRUpstreamFaulty(V1.2B->), actSCRDownstreamFaulty(V1.3A->)         
	-- info-VALUE:   actMBSUpstreamFaulty(V1.3A->), actMBSDownstreamFaulty(V1.3A->)     
	-- info-VALUE:   actVplTpNotExisting(V1.2B->), actTrafficDirectionFaulty(V1.2A->)
	-- info-VALUE:
	-- info-VALUE:   createEthVplCC(V1.2b->)(command), createEthVclCC(V1.2b->)(command), 
	-- info-VALUE:       
	-- info-VALUE:   configEth(V1.1U->)(command), configEthFailed(V1.1U->),
	-- info-VALUE:
	-- info-VALUE:   ethModeInvalid(V1.1U->)
	-- info-VALUE:   ethVpiUniNotExisting(V1.1U->), ethVciUniNotExisting(V1.1U->)
	-- info-VALUE:   ethVciTrafficTypeFaulty(V1.1U->),ethVciPeakCellRateUpstreamFaulty (V1.1U->) 
	-- info-VALUE:   actWrongLiType(V1.1U->), actVciUniFaulty(V1.2b->)
	-- info-VALUE:   actTrafficPriorityConflict(V1.3a->), 
	-- info-VALUE:      
	-- info-VALUE:   actSegmentEndPointUniFaulty(V1.2b->), actSegmentEndPointNniFaulty(V1.2b->)
	-- info-VALUE:   actVclCCExists(V1.2b->), actEthVplTpDeletionNotAllowed(V1.2b->)
	-- info-VALUE:   continuityCheckReject(V1.3B->)
	-- info-VALUE:      
	-- info-VALUE:   requestBusy(V1.3N->),setDataFailed(V1.3N->),
	-- info-VALUE:   aswTimeout(V1.3N->),
	-- info-VALUE:      
	-- info-VALUE:   configInbandTmn(V1.3N->)(command),configInbandTmnFailed(V1.3N->),
	-- info-VALUE:   inbandVpiExists(V1.3N->),inbandVciExists(V1.3N->)
	-- info-VALUE:   createEthVplTp(V1.3N),deleteEthVplTp(V1.3N)
	-- info-COMMENT: Callp user command:
	-- info-COMMENT: createCC.deleteCC.createVplCC.deleteVplCC.
	-- info-COMMENT: createVclCC.deleteVclCC.createVplTp, deleteVplTp.
	-- info-COMMENT: createEthVplCC.createEthVclCC.configEth.
	-- info-COMMENT: createEthVplTp.deleteEthVplTp.configInbandTmn
	-- info-ROU:     GET db  SET cp 
	-- info-IMPL:    V1.0->
	-- info-VERCTRL: - 
	SYNTAX        Xldv11ControlReq
	ACCESS        read-write
	STATUS        mandatory
	DESCRIPTION
	     " This attribute identifies CallP user commands and their results.
	       Range of values:
		  noRequest
		  ,createVplCC 
		  ,deleteVplCC
		  ,createAllCC (obsolete from XLDV1.3N, no download !)
		  ,createVclCC
		  ,deleteVclCC
		  ,commExecStarted
		  ,actVpiNniFaulty
		  ,actVpiUniFaulty
		  ,actPortLocationIdFaulty
		  ,actControlReqFaulty
		  ,lineNotEnabled
		  ,ccExists
		  ,actPeakCellRateUpstreamFaulty
		  ,actPeakCellRateDownstreamFaulty
		  ,actCellDelayVariationUpstreamFaulty
		  ,actCellDelayVariationDownstreamFaulty
		  ,actTrafficTypeFaulty
		  ,actInsufficientBw 
		  ,actLineBlocked
		  ,actVplTpNotExisting 
		  ,actTrafficDirectionFaulty 
		  ,createEthVplCC
		  ,createEthVclCC
		  ,configEth    
		  ,configEthFailed
		  ,ethModeInvalid 
		  ,ethVpiUniNotExisting
		  ,ethVciUniNotExisting
		  ,ethVciTrafficTypeFaulty
		  ,ethVciPeakCellRateUpstreamFaulty
		  ,actWrongLiType                   
		  ,actTrafficPriorityConflict   
		  ,actSegmentEndPointUniFaulty 
		  ,actSegmentEndPointNniFaulty
		  ,actVclCCExists                   
		  ,actEthVplTpDeletionNotAllowed
		  ,countinuityCheckReject
		  ,aswRequestBusy 
		  ,setDataFailed
		  ,aswTimeout  
		  ,configInbandTmn
		  ,configInbandTmnFailed
		  ,inbandVpiExists
		  ,inbandVciExists
		  ,createEthVplTp
		  ,deleteEthVplTp .
		
	       Notifications :
		  xldv11TrStateChangeOper,
		  xldv11TrActCcCreation,
		  xldv11TrActCcDeletion,
		  xldv11TrActCcReload ."
	--DEFAULT test-function-async     fsnActTest
	--DEFAULT next-function-async     fsnActNext
	--DEFAULT set-function-async      fsnActSet
	--DEFAULT get-function-async      fsnActGet
	::= { xldv11AtmCcControl 2 }

     xldv11ActControlStatus OBJECT-TYPE
	-- info-LEAF:    xldv11ActControlStatus
	-- info-TREE:    xldv11CallP
	-- info-ACC:     ro
	-- info-SYNTAX:  Xldv11ControlStatus
	-- info-VALUE:   requestIdle(1), requestBusy(2), requestPassed(3)
	-- info-VALUE:   requestFailed(4)
	-- info-COMMENT: Indicates the status of a control request.
	-- info-ROU:     GET db 
	-- info-IMPL:    V1.0->
	-- info-VERCTRL: -
	SYNTAX        Xldv11ControlStatus
	ACCESS        read-only
	STATUS        mandatory
	DESCRIPTION
	     " This attribute indicates the status of a control request.
	       Range of values is:
	       requestIdle,
	       requestBusy,
	       requestPassed,
	       requestFailed . "
	--DEFAULT next-function-async     fsnActNext
	--DEFAULT get-function-async      fsnActGet
	::= { xldv11AtmCcControl 3 }

     xldv11ActVpiNni OBJECT-TYPE
	-- info-LEAF:    xldv11ActVpiNni
	-- info-TREE:    xldv11CallP
	-- info-ACC:     rw
	-- info-SYNTAX:  INTEGER
	-- info-VALUE:   0..4095
	-- info-VALUE:   Default for inband VPI: 255
	-- info-COMMENT: Identifies the VPI value associated with
	-- info-COMMENT: the Local Exchange.
	-- info-ROU:     GET db  SET db 
	-- info-IMPL:    V1.0->
	-- info-VERCTRL: -
	SYNTAX        INTEGER (0..4095)
	ACCESS        read-write
	STATUS        mandatory
	DESCRIPTION
	     " This attribute identifies the VPI value associated with
	       the Local Exchange.
	       V1.1U/V1.2/V1.3: Value 255 is reserved for inband OAM channel.
	       V1.1U: Value 64 has to be used for SDVB channel."
	--DEFAULT test-function-async     fsnActTest
	--DEFAULT next-function-async     fsnActNext
	--DEFAULT set-function-async      fsnActSet
	--DEFAULT get-function-async      fsnActGet
	::= { xldv11AtmCcControl 4 }

     xldv11ActVpiUni OBJECT-TYPE
	-- info-LEAF:    xldv11ActVpiUni
	-- info-TREE:    xldv11CallP
	-- info-ACC:     rw
	-- info-SYNTAX:  INTEGER
	-- info-VALUE:   0..63
	-- info-COMMENT: identifies the VPI value associated with
	-- info-COMMENT: the Network Termination.
	-- info-ROU:     GET db  SET db 
	-- info-IMPL:    V1.0->
	-- info-VERCTRL: -
	SYNTAX        INTEGER (0..63)
	ACCESS        read-write
	STATUS        mandatory
	DESCRIPTION
	     " This attribute identifies the VPI value associated with
	       the Network Termination.
	       V1.1U: Value 4 is reserved for SDVB channel."
	--DEFAULT test-function-async     fsnActTest
	--DEFAULT next-function-async     fsnActNext
	--DEFAULT set-function-async      fsnActSet
	--DEFAULT get-function-async      fsnActGet
	::= { xldv11AtmCcControl 5 }

     xldv11ActVciNni OBJECT-TYPE
	-- info-LEAF:    xldv11ActVciNni
	-- info-TREE:    xldv11CallP
	-- info-ACC:     rw
	-- info-SYNTAX:  INTEGER
	-- info-VALUE:   0..65535
	-- info-COMMENT: identifies the VCI value associated with
	-- info-COMMENT: the Local Exchange.
	-- info-ROU:     GET db  SET db 
	-- info-IMPL:    V1.2A->
	-- info-VERCTRL: GET db  SET db 
	SYNTAX        INTEGER (0..65535)
	ACCESS        read-write
	STATUS        mandatory
	DESCRIPTION
	     " This attribute identifies the VCI value associated with
	       the Local Exchange. 
	       Values 0..31 have to be used for OAM channels."
	--DEFAULT test-function-async     fsnActTest
	--DEFAULT next-function-async     fsnActNext
	--DEFAULT set-function-async      fsnActSet
	--DEFAULT get-function-async      fsnActGet
	::= { xldv11AtmCcControl 6 }

     xldv11ActVciUni OBJECT-TYPE
	-- info-LEAF:    xldv11ActVciUni
	-- info-TREE:    xldv11CallP
	-- info-ACC:     rw
	-- info-SYNTAX:  INTEGER
	-- info-VALUE:   0..65535
	-- info-COMMENT: Identifies the VCI value associated with
	-- info-COMMENT: the Network Termination.
	-- info-ROU:     GET db  SET db 
	-- info-IMPL:    V1.2A->
	-- info-VERCTRL: GET db  SET db 
	SYNTAX        INTEGER (0..65535)
	ACCESS        read-write
	STATUS        mandatory
	DESCRIPTION
	     " This attribute identifies the VCI value associated with
	       the Network Termination."
	--DEFAULT test-function-async     fsnActTest
	--DEFAULT next-function-async     fsnActNext
	--DEFAULT set-function-async      fsnActSet
	--DEFAULT get-function-async      fsnActGet
	::= { xldv11AtmCcControl 7 }


     xldv11ActIfIndex OBJECT-TYPE
	-- info-LEAF:    xldv11ActIfIndex
	-- info-TREE:    xldv11CallP
	-- info-ACC:     rw
	-- info-SYNTAX:  Unsigned16
	-- info-VALUE:   V1.0->V1.1U: ifIndex of tcaAdaptor of LI*
	-- info-VALUE:   V1.2A->: ifIndex of PPTP of LI* 
	-- info-COMMENT: It is the relevant interface index of the
	-- info-COMMENT: connected PPTP in the LI.
	-- info-ROU:     GET db  SET db 
	-- info-IMPL:    V1.0->
	-- info-VERCTRL: -
	SYNTAX        Unsigned16
	ACCESS        read-write
	STATUS        mandatory
	DESCRIPTION
	     " NEW for V1.2A:
	       It is the relevant interface index of the connected
	       PPTP in the LI "
	--DEFAULT test-function-async     fsnActTest
	--DEFAULT next-function-async     fsnActNext
	--DEFAULT set-function-async      fsnActSet
	--DEFAULT get-function-async      fsnActGet
	::= { xldv11AtmCcControl 8 }

     xldv11ActControlTimerCreation OBJECT-TYPE
	-- info-LEAF:    xldv11ActControlTimerCreation
	-- info-TREE:    xldv11CallP
	-- info-ACC:     nac
	-- info-SYNTAX:  Integer32
	-- info-VALUE:   -2147483648..2147483647
	-- info-COMMENT: Maximum wait time for the TMN-OS when a cross
	-- info-COMMENT: connect creation request cannot be executed immediately.
	-- info-ROU:     GET db   
	-- info-IMPL:    V1.0->V1.3B
	-- info-VERCTRL: -
	SYNTAX        Integer32
	ACCESS        not-accessible
	STATUS        mandatory
	DESCRIPTION
	      " Unused as from V1.3N no long running command for Callp.
	      The maximum wait time for the TMN-OS when a cross
		connect creation request cannot be executed
		immediately ( Value lineNotEnabled in the Get
		Response for actControlReq ).
		TMN-OS reads this value from the ONU. "
	--DEFAULT next-function-async     fsnActNext
	--DEFAULT get-function-async      fsnActGet
	::= { xldv11AtmCcControl 9 }

     xldv11ActControlTimerReload OBJECT-TYPE
	-- info-LEAF:    xldv11ActControlTimerReload
	-- info-TREE:    xldv11CallP
	-- info-ACC:     nac
	-- info-SYNTAX:  Integer32
	-- info-VALUE:   -2147483648..2147483647
	-- info-COMMENT: The TMN-OS maximum wait time for the createAllCC
	-- info-COMMENT: request after a reload of the ONU.
	-- info-ROU:     GET db
	-- info-IMPL:    V1.0->V1.3B
	-- info-VERCTRL: -
	SYNTAX        Integer32
	ACCESS        not-accessible
	STATUS        mandatory
	DESCRIPTION
	      " Unused as from V1.3N no long running command for Callp.
		The TMN-OS maximum wait time for the createAllCC request
		after a reload of the ONU.
		Within the timer actControlTimerReload the TMN-OS will
		receive for each cross connect which could not be created
		a trap xldv11TrActCcReload with result NOT OKAY. The end of
		reload is indicated by the trap xldv11TrActCcReload with
		result OK."
	--DEFAULT next-function-async     fsnActNext
	--DEFAULT get-function-async      fsnActGet
	::= { xldv11AtmCcControl 10 }

     xldv11ActPeakCellRateUpstream OBJECT-TYPE
	-- info-LEAF:    xldv11ActPeakCellRateUpstream
	-- info-TREE:    xldv11CallP
	-- info-ACC:     rw
	-- info-SYNTAX:  Unsigned32
	-- info-VALUE:   0..2147483647 (default 800 000 )
	-- info-COMMENT: Identifies the peak cell rate in upstream direction.
	-- info-COMMENT: unit bit/sec
	-- info-ROU:     GET db  SET db 
	-- info-IMPL:    V1.1U->
	-- info-VERCTRL: GET db  SET db 
	SYNTAX        Unsigned32
	ACCESS        read-write
	STATUS        mandatory
	DESCRIPTION
	     " This read-write attribute identifies the upstream peak cell rate
	       in bit/sec of the VP cross connect.
	       ( Bit rate per ATM cell is 53*8 bit/sec ).
	       Default value is 800 000."
	--DEFAULT test-function-async     fsnActTest
	--DEFAULT next-function-async     fsnActNext
	--DEFAULT set-function-async      fsnActSet
	--DEFAULT get-function-async      fsnActGet
	::= { xldv11AtmCcControl 11 }

     xldv11ActPeakCellRateDownstream OBJECT-TYPE
	-- info-LEAF:    xldv11ActPeakCellRateDownstream
	-- info-TREE:    xldv11CallP
	-- info-ACC:     rw
	-- info-SYNTAX:  Unsigned32
	-- info-VALUE:   0..2147483647 (default: 2 000 000)
	-- info-COMMENT: identifies the peak cell rate in downstream direction.
	-- info-COMMENT: unit bit/sec
	-- info-ROU:     GET db  SET db 
	-- info-IMPL:    V1.1U->
	-- info-VERCTRL: GET db  SET db 
	SYNTAX        Unsigned32
	ACCESS        read-write
	STATUS        mandatory
	DESCRIPTION
	     " This read-write attribute identifies the peak cell rate in 
	       downstream direction of the VP cross connect.
	       ( Bit rate per ATM cell is 53*8 bit/sec ).
	       Default: 2 000 000 "
	--DEFAULT test-function-async     fsnActTest
	--DEFAULT next-function-async     fsnActNext
	--DEFAULT set-function-async      fsnActSet
	--DEFAULT get-function-async      fsnActGet
	::= { xldv11AtmCcControl 12 }

     xldv11ActCellDelayVariationToleranceUpstream OBJECT-TYPE
	-- info-LEAF:    xldv11ActCellDelayVariationToleranceUpstream
	-- info-TREE:    xldv11CallP
	-- info-ACC:     rw
	-- info-SYNTAX:  INTEGER
	-- info-VALUE:   200..360,000,000 (default: 360,000,000)
	-- info-COMMENT: Identifies the cell delay variation (in nsec)
	-- info-COMMENT: in upstream direction.
	-- info-ROU:     GET db  SET db 
	-- info-IMPL:    V1.1U->
	-- info-VERCTRL: GET db  SET db 
	SYNTAX        INTEGER(200..360000000)
	ACCESS        read-write
	STATUS        mandatory
	DESCRIPTION
	     " This read-write attribute identifies the cell delay variation (in nsec)
	       in upstream direction of the VP cross connect.
	       Default is 360,000,000. "
	--DEFAULT test-function-async     fsnActTest
	--DEFAULT next-function-async     fsnActNext
	--DEFAULT set-function-async      fsnActSet
	--DEFAULT get-function-async      fsnActGet
	::= { xldv11AtmCcControl 13 }

     xldv11ActCellDelayVariationToleranceDownstream OBJECT-TYPE
	-- info-LEAF:    xldv11ActCellDelayVariationToleranceDownstream
	-- info-TREE:    xldv11CallP
	-- info-ACC:     rw
	-- info-SYNTAX:  INTEGER
	-- info-VALUE:   200..360,000,000 (default: 200)
	-- info-COMMENT: identifies the cell delay variation (in nsec)
	-- info-COMMENT: in downstream direction.
	-- info-ROU:     GET db  SET db 
	-- info-IMPL:    V1.1U->
	-- info-VERCTRL: GET db  SET db 
	SYNTAX        INTEGER(200..360000000)
	ACCESS        read-write
	STATUS        mandatory
	DESCRIPTION
	     " This read-write attribute identifies the cell delay variation (in nsec)
	       in downstream direction of the VP cross connect. "
	--DEFAULT test-function-async     fsnActTest
	--DEFAULT next-function-async     fsnActNext
	--DEFAULT set-function-async      fsnActSet
	--DEFAULT get-function-async      fsnActGet
	::= { xldv11AtmCcControl 14 }


     xldv11ActTrafficType OBJECT-TYPE
	-- info-LEAF:    xldv11ActTrafficType
	-- info-TREE:    xldv11CallP
	-- info-ACC:     rw
	-- info-SYNTAX:  Xldv11TrafficType
	-- info-VALUE:   cbr(V1.1U->), ubr(V1.2A->), nrtVbr(V1.3A->)
	-- info-VALUE:   rtVbr(V1.3A->) (default: cbr)
	-- info-COMMENT: Identifies the traffic type.
	-- info-ROU:     GET db  SET db 
	-- info-IMPL:    V1.1U->
	-- info-VERCTRL: GET db  SET db 
	SYNTAX        Xldv11TrafficType
	ACCESS        read-write
	STATUS        mandatory
	DESCRIPTION
	     " This read-write attribute identifies the traffic type of the
	       VP cross connect. 
	       The range of values is 
		     constant bit rate    cbr
		     unspecified bit rate ubr
		     For V1.3:
					  nrtVbr
					  rtVbr
	       Default value is constant bit rate (cbr)."
	--DEFAULT test-function-async     fsnActTest
	--DEFAULT next-function-async     fsnActNext
	--DEFAULT set-function-async      fsnActSet
	--DEFAULT get-function-async      fsnActGet
	::= { xldv11AtmCcControl 15 }

     xldv11ActTrafficDirection OBJECT-TYPE
	-- info-LEAF:    xldv11ActTrafficDirection
	-- info-TREE:    xldv11CallP
	-- info-ACC:     rw
	-- info-SYNTAX:  Xldv11TrafficDirection
	-- info-VALUE:   bidirectional, upstream, downstream
	-- info-VALUE:   (default: bidirectional)
	-- info-COMMENT: Identifies the traffic direction.
	-- info-ROU:     GET db  SET db 
	-- info-IMPL:    V1.2B->
	-- info-VERCTRL: GET db  SET db 
	SYNTAX        Xldv11TrafficDirection
	ACCESS        read-write
	STATUS        mandatory
	DESCRIPTION
	     "  This read-write attribute identifies the traffic direction.
		Possible Values: bidirectional, upstream, downstream.
		Default Value:   bidirectional."
	--DEFAULT test-function-async     fsnActTest
	--DEFAULT next-function-async     fsnActNext
	--DEFAULT set-function-async      fsnActSet
	--DEFAULT get-function-async      fsnActGet
	::= { xldv11AtmCcControl 16 }

     xldv11ActSustainableCellRateUpstream OBJECT-TYPE
	-- info-LEAF:    xldv11ActSustainableCellRateUpstream
	-- info-TREE:    xldv11CallP
	-- info-ACC:     rw
	-- info-SYNTAX:  INTEGER
	-- info-VALUE:   0..155000000 (default: 100 000)
	-- info-COMMENT: The upstream sustainable cell rate in cells/sec
	-- info-COMMENT: for nrtVbr traffic.
	-- info-ROU:     GET db  SET db 
	-- info-IMPL:    V1.3A->
	-- info-VERCTRL: GET db  SET db 
	SYNTAX        INTEGER (0..155000000)
	ACCESS        read-write
	STATUS        mandatory
	DESCRIPTION
	     "  The upstream sustainable cell rate in cells/sec
		for nrtVbr traffic.
		Default Value:   100 000."
	--DEFAULT test-function-async     fsnActTest
	--DEFAULT next-function-async     fsnActNext
	--DEFAULT set-function-async      fsnActSet
	--DEFAULT get-function-async      fsnActGet
	::= { xldv11AtmCcControl 17 }

     xldv11ActSustainableCellRateDownstream OBJECT-TYPE
	-- info-LEAF:    xldv11ActSustainableCellRateDownstream
	-- info-TREE:    xldv11CallP
	-- info-ACC:     rw
	-- info-SYNTAX:  INTEGER
	-- info-VALUE:   0..155000000 (default: 100 000)
	-- info-COMMENT: The downstream sustainable cell rate in cells/sec
	-- info-COMMENT: for nrtVbr traffic.
	-- info-ROU:     GET db  SET db 
	-- info-IMPL:    V1.3A->
	-- info-VERCTRL: GET db  SET db 
	SYNTAX        INTEGER (0..155000000)
	ACCESS        read-write
	STATUS        mandatory
	DESCRIPTION
	     "  The downstream sustainable cell rate in cells/sec
		for nrtVbr traffic.
		Default Value:   100 000."
	--DEFAULT test-function-async     fsnActTest
	--DEFAULT next-function-async     fsnActNext
	--DEFAULT set-function-async      fsnActSet
	--DEFAULT get-function-async      fsnActGet
	::= { xldv11AtmCcControl 18 }

     xldv11ActMaximumBurstSizeUpstream OBJECT-TYPE
	-- info-LEAF:    xldv11ActMaximumBurstSizeUpstream
	-- info-TREE:    xldv11CallP
	-- info-ACC:     rw
	-- info-SYNTAX:  Integer32
	-- info-VALUE:   1..1500 (default: 32)
	-- info-COMMENT: The upstream maximum burst size tolerance in
	-- info-COMMENT: cells/sec for nrtVbr traffic.
	-- info-ROU:     GET db  SET db 
	-- info-IMPL:    V1.3A->
	-- info-VERCTRL: GET db  SET db 
	SYNTAX        INTEGER(1..1500)
	ACCESS        read-write
	STATUS        mandatory
	DESCRIPTION
	     "  The upstream maximum burst size tolerance in cells/sec
		for nrtVbr traffic.
		Default Value:   32."
	--DEFAULT test-function-async     fsnActTest
	--DEFAULT next-function-async     fsnActNext
	--DEFAULT set-function-async      fsnActSet
	--DEFAULT get-function-async      fsnActGet
	::= { xldv11AtmCcControl 19 }

     xldv11ActMaximumBurstSizeDownstream OBJECT-TYPE
	-- info-LEAF:    xldv11ActMaximumBurstSizeDownstream
	-- info-TREE:    xldv11CallP
	-- info-ACC:     rw
	-- info-SYNTAX:  Integer32
	-- info-VALUE:   1..18 800 (default: 32)
	-- info-COMMENT: The downstream maximum burst size tolerance
	-- info-COMMENT: in cells/sec for nrtVbr traffic.
	-- info-ROU:     GET db  SET db 
	-- info-IMPL:    V1.3A->
	-- info-VERCTRL: GET db  SET db 
	SYNTAX        INTEGER(1..18800)
	ACCESS        read-write
	STATUS        mandatory
	DESCRIPTION
	     "  The downstream maximum burst size tolerance in cells/sec
		for nrtVbr traffic.
		Default Value:   32."
	--DEFAULT test-function-async     fsnActTest
	--DEFAULT next-function-async     fsnActNext
	--DEFAULT set-function-async      fsnActSet
	--DEFAULT get-function-async      fsnActGet
	::= { xldv11AtmCcControl 20 }

     xldv11ActSegmentEndPointNni OBJECT-TYPE
	-- info-LEAF:    xldv11ActSegmentEndPointNni
	-- info-TREE:    xldv11CallP
	-- info-ACC:     rw
	-- info-SYNTAX:  INTEGER
	-- info-VALUE:   yes..no (default: no)
	-- info-COMMENT: This value specifies whether the VplTp/VclTp is
	-- info-COMMENT  a segment endpoint (yes) or a connecting point (no).
	-- info-ROU:     GET db  SET db
	-- info-IMPL:    V1.2B->
	-- info-VERCTRL: GET db  SET db
	SYNTAX        INTEGER { yes(1), 
				no (2)    }
	ACCESS        read-write
	STATUS        mandatory
	DESCRIPTION
	     "  This value specifies whether the VplTp/VclTp is
		a segment endpoint (yes) or a connecting point (no) "
	--DEFAULT test-function-async     fsnActTest
	--DEFAULT next-function-async     fsnActNext
	--DEFAULT set-function-async      fsnActSet
	--DEFAULT get-function-async      fsnActGet
	::= { xldv11AtmCcControl 21 }

     xldv11ActSegmentEndPointUni OBJECT-TYPE
	-- info-LEAF:    xldv11ActSegmentEndPointUni
	-- info-TREE:    xldv11CallP
	-- info-ACC:     rw
	-- info-SYNTAX:  INTEGER
	-- info-VALUE:   yes..no (default: no)
	-- info-COMMENT: This value specifies whether the VplTp/VclTp is
	-- info-COMMENT: a segment endpoint (yes) or a connecting point (no).
	-- info-ROU:     GET db  SET db
	-- info-IMPL:    V1.2B->
	-- info-VERCTRL: GET db  SET db
	SYNTAX        INTEGER { yes(1), 
				no (2)    }
	ACCESS        read-write
	STATUS        mandatory
	DESCRIPTION
	     "  This value specifies whether the VplTp/VclTp is
		a segment endpoint (yes) or a connecting point (no) "
	--DEFAULT test-function-async     fsnActTest
	--DEFAULT next-function-async     fsnActNext
	--DEFAULT set-function-async      fsnActSet
	--DEFAULT get-function-async      fsnActGet
	::= { xldv11AtmCcControl 22 }

     xldv11ActEthVciTrafficType  OBJECT-TYPE
	-- info-LEAF:    xldv11ActEthVciTrafficType
	-- info-TREE:    xldv11CallP
	-- info-ACC:     nac
	-- info-SYNTAX:  Xldv11TrafficType
	-- info-VALUE:   ubr 
	-- info-COMMENT: This value defines the traffic type
	-- info-ROU:     -
	-- info-IMPL:    V1.1U->V1.3B
	-- info-VERCTRL: V1.3N->:nac
	SYNTAX        Xldv11TrafficType
	ACCESS        not-accessible
	STATUS        mandatory
	DESCRIPTION
	     "  This value defines the Traffic Types of Ethernet interface.
	     Unused from V1.3N on. "
	--DEFAULT test-function-async     fsnActTest
	--DEFAULT next-function-async     fsnActNext
	--DEFAULT set-function-async      fsnActSet
	--DEFAULT get-function-async      fsnActGet
	::= { xldv11AtmCcControl 23 }
 
     xldv11ActEthVciPeakCellRateUpstream OBJECT-TYPE
	-- info-LEAF:    xldv11ActEthVciPeakCellRateUpstream
	-- info-TREE:    xldv11CallP
	-- info-ACC:     nac
	-- info-SYNTAX:  Unsigned32
	-- info-VALUE:   0..2 Giga (default: 800 000)
	-- info-COMMENT: Peak Cell Rate for Eth Upstream
	-- info-ROU:     -
	-- info-IMPL:    V1.1U->V1.3B
	-- info-VERCTRL: V1.3N->:nac
	SYNTAX        Unsigned32
	ACCESS        not-accessible
	STATUS        mandatory
	DESCRIPTION
	     "PeakCell Rate upstream from 0 to 2 Giga 
	      Default: 800 000.
	      Unused from V1.3N on. "
	--DEFAULT test-function-async     fsnActTest
	--DEFAULT next-function-async     fsnActNext
	--DEFAULT set-function-async      fsnActSet
	--DEFAULT get-function-async      fsnActGet
	::= { xldv11AtmCcControl 24 }


     xldv11ActEthMode OBJECT-TYPE
	-- info-LEAF:    xldv11ActEthMode 
	-- info-TREE:    xldv11CallP
	-- info-ACC:     rw
	-- info-SYNTAX:  Xldv11EthNtMode
	-- info-VALUE:   bridging(V1.2A->), routing(V1.2A->)
	-- info-VALUE:   default: bridging
	-- info-COMMENT: operational mode of the ethernet configuration
	-- info-ROU:     GET db  SET db
	-- info-IMPL:    V1.1U->
	-- info-VERCTRL: GET db  SET db
	SYNTAX        Xldv11EthNtMode
	ACCESS        read-write
	STATUS        mandatory
	DESCRIPTION
	      " The operational mode of the ethernet configuration:
		Available modes: bridging, routing. 
		Default: bridging"
	--DEFAULT test-function-async     fsnActTest
	--DEFAULT next-function-async     fsnActNext
	--DEFAULT set-function-async      fsnActSet
	--DEFAULT get-function-async      fsnActGet
	::= { xldv11AtmCcControl 25 }

     xldv11ActEthE164Isp     OBJECT-TYPE
	-- info-LEAF:    xldv11ActEthE164Isp
	-- info-TREE:    xldv11CallP
	-- info-ACC:     rw
	-- info-SYNTAX:  OCTET STRING
	-- info-VALUE:   -
	-- info-COMMENT: -
	-- info-ROU:     GET db SET db
	-- info-IMPL:    V1.1U->
	-- info-VERCTRL: -
	SYNTAX            OCTET STRING ( SIZE (0..20) ) 
	ACCESS            read-write
	STATUS            mandatory
	DESCRIPTION
	      " The telephon number of the Internet Service Provider,
		parameter for ipForwarding - mode"
	--DEFAULT test-function-async     fsnActTest
	--DEFAULT next-function-async     fsnActNext
	--DEFAULT set-function-async      fsnActSet
	--DEFAULT get-function-async      fsnActGet
	::= { xldv11AtmCcControl 26 }

     xldv11ActEthIpAddressNt   OBJECT-TYPE
	-- info-LEAF:    xldv11ActEthIpAddressNt 
	-- info-TREE:    xldv11CallP
	-- info-ACC:     rw
	-- info-SYNTAX:  IpAddress
	-- info-VALUE:   -
	-- info-COMMENT: -
	-- info-ROU:     GET db SET db
	-- info-IMPL:    V1.1U->
	-- info-VERCTRL: -
	SYNTAX                IpAddress
	ACCESS            read-write
	STATUS            mandatory
	DESCRIPTION
	      " The IP Address of the NT,
		parameter for ipForwarding - mode
		Default: 0.0.0.0"
	--DEFAULT test-function-async     fsnActTest
	--DEFAULT next-function-async     fsnActNext
	--DEFAULT set-function-async      fsnActSet
	--DEFAULT get-function-async      fsnActGet
	::= { xldv11AtmCcControl 27 }

     xldv11ActEthIpAddressSubnetMaskNt   OBJECT-TYPE
	-- info-LEAF:    xldv11ActEthIpAddressSubnetMaskNt
	-- info-TREE:    xldv11CallP
	-- info-ACC:     rw
	-- info-SYNTAX:  IpAddress
	-- info-VALUE:   -
	-- info-COMMENT: -
	-- info-ROU:     GET db SET db
	-- info-IMPL:    V1.1U>
	-- info-VERCTRL: -
	SYNTAX                IpAddress
	ACCESS            read-write
	STATUS            mandatory
	DESCRIPTION
	      " The subnet mask of the NT ,
		parameter for ipForwarding - mode.
		Default: 0.0.0.0"
	--DEFAULT test-function-async     fsnActTest
	--DEFAULT next-function-async     fsnActNext
	--DEFAULT set-function-async      fsnActSet
	--DEFAULT get-function-async      fsnActGet
	::= { xldv11AtmCcControl 28 }


     xldv11ActEthIpAddressCo   OBJECT-TYPE
	-- info-LEAF:    xldv11ActEthIpAddressCo
	-- info-TREE:    xldv11CallP
	-- info-ACC:     rw
	-- info-SYNTAX:  IpAddress
	-- info-VALUE:   -
	-- info-COMMENT: -
	-- info-ROU:     GET db SET db
	-- info-IMPL:    V1.1U->
	-- info-VERCTRL: -
	SYNTAX                IpAddress
	ACCESS            read-write
	STATUS            mandatory
	DESCRIPTION
	      " The IP Address of the destination NT (office side),
		parameter for ipForwarding - mode.
		Default: 0.0.0.0"
	--DEFAULT test-function-async     fsnActTest
	--DEFAULT next-function-async     fsnActNext
	--DEFAULT set-function-async      fsnActSet
	--DEFAULT get-function-async      fsnActGet
	::= { xldv11AtmCcControl 29 }

     xldv11ActEthIpAddressSubnetMaskCo   OBJECT-TYPE
	-- info-LEAF:    xldv11ActEthIpAddressSubnetMaskCo
	-- info-TREE:    xldv11CallP
	-- info-ACC:     rw
	-- info-SYNTAX:  IpAddress
	-- info-VALUE:   -
	-- info-COMMENT: -
	-- info-ROU:     GET db SET db
	-- info-IMPL:    V1.1U->
	-- info-VERCTRL: -
	SYNTAX                IpAddress
	ACCESS            read-write
	STATUS            mandatory
	DESCRIPTION
	      " The subnet mask of the CO  ,
		parameter for ipForwarding - mode.
		Default: 0.0.0.0"
	--DEFAULT test-function-async     fsnActTest
	--DEFAULT next-function-async     fsnActNext
	--DEFAULT set-function-async      fsnActSet
	--DEFAULT get-function-async      fsnActGet
	::= { xldv11AtmCcControl 30 }

     xldv11ActEthIpAddressRemoteRouter    OBJECT-TYPE
	-- info-LEAF:    xldv11ActEthIpAddressRemoteRouter 
	-- info-TREE:    xldv11CallP
	-- info-ACC:     rw
	-- info-SYNTAX:  IpAddress
	-- info-VALUE:   -
	-- info-COMMENT: -
	-- info-ROU:     GET db SET db
	-- info-IMPL:    V1.1U->
	-- info-VERCTRL: -
	SYNTAX                IpAddress
	ACCESS            read-write
	STATUS            mandatory
	DESCRIPTION
	      " The subnet mask of the ISP router  ,
		parameter for ipForwarding - mode.
		Default: 0.0.0.0"
	--DEFAULT test-function-async     fsnActTest
	--DEFAULT next-function-async     fsnActNext
	--DEFAULT set-function-async      fsnActSet
	--DEFAULT get-function-async      fsnActGet
	::= { xldv11AtmCcControl 31 }

     xldv11ActEthControlTimer OBJECT-TYPE
	-- info-LEAF:    xldv11ActEthControlTimer
	-- info-TREE:    xldv11CallP
	-- info-ACC:     nac
	-- info-SYNTAX:  Integer32
	-- info-VALUE:   -2147483648..2147483647
	-- info-COMMENT: control timer 
	-- info-ROU:     GET db 
	-- info-IMPL:    V1.1U->V1.3B
	-- info-VERCTRL: -
	SYNTAX        Integer32
	ACCESS        not-accessible
	STATUS        mandatory
	DESCRIPTION
	     " Unused as Ethernet configuration is no long running command.
	     Maximum wait time for Ethernet configuration command.  "
	--DEFAULT get-function-async      fsnActGet
	--DEFAULT next-function-async     fsnActNext
	::= { xldv11AtmCcControl 32 }

     xldv11ActTrafficPriority OBJECT-TYPE
	-- info-LEAF:    xldv11ActTrafficPriority
	-- info-TREE:    xldv11CallP
	-- info-ACC:     rw
	-- info-SYNTAX:  Xldv11TrafficPriority
	-- info-VALUE:   low or high (default: high)
	-- info-COMMENT: Identifies the traffic priority.
	-- info-ROU:     GET db SET db1
	-- info-IMPL:    V1.3H->
	-- info-VERCTRL: -
	SYNTAX        Xldv11TrafficPriority
	ACCESS        read-write
	STATUS        mandatory
	DESCRIPTION
	     " traffic priority: 
	      Default value: high.  "
	--DEFAULT test-function-async     fsnActTest
	--DEFAULT next-function-async     fsnActNext
	--DEFAULT set-function-async      fsnActSet
	--DEFAULT get-function-async      fsnActGet
	::= { xldv11AtmCcControl 33 }

     -- for continuity check
     
     xldv11ActTestTypeNni OBJECT-TYPE
	-- info-LEAF:    xldv11ActTestTypeNni
	-- info-TREE:    xldv11CallP
	-- info-ACC:     rw
	-- info-SYNTAX:  INTEGER
	-- info-VALUE:   segment(1), endToEnd(2) 
	-- info-COMMENT: Type of continuity check
	-- info-COMMENT: on Nni side
	-- info-ROU:     GET db  SET db 
	-- info-IMPL:    V1.3B->
	-- info-VERCTRL: -
	SYNTAX        INTEGER { segment      (1),
				endToEnd     (2) }
	ACCESS        read-write
	STATUS        mandatory
	DESCRIPTION
	     " The type of continuity check segment or endToEnd ."    
	--DEFAULT test-function-async     fsnActTest
	--DEFAULT next-function-async     fsnActNext
	--DEFAULT set-function-async      fsnActSet
	--DEFAULT get-function-async      fsnActGet
	::= { xldv11AtmCcControl 34 }

     xldv11ActContinuityCheckNni OBJECT-TYPE
	-- info-LEAF:    xldv11ActContinuityCheckNni
	-- info-TREE:    xldv11CallP
	-- info-ACC:     rw
	-- info-SYNTAX:  Xldv11OperState
	-- info-VALUE:   enabled(1)..disabled(2)
	-- info-COMMENT: enables or disables the continuity check
	-- info-ROU:     GET db  SET db 
	-- info-IMPL:    V1.3B->
	-- info-VERCTRL: -
	SYNTAX        Xldv11OperState
	ACCESS        read-write
	STATUS        mandatory
	DESCRIPTION
	     " This attribute specifies whether or not the 
	       continuity check should be enabled for this instance of
	       the ATM Cross Connection managed entity ."
	--DEFAULT test-function-async     fsnActTest
	--DEFAULT next-function-async     fsnActNext
	--DEFAULT set-function-async      fsnActSet
	--DEFAULT get-function-async      fsnActGet
	::= { xldv11AtmCcControl 35 }

     xldv11ActEndpointTypeNni OBJECT-TYPE
	-- info-LEAF:    xldv11ActEndpointTypeNni
	-- info-TREE:    xldv11CallP
	-- info-ACC:     rw
	-- info-SYNTAX:  Xldv11EndpointType
	-- info-VALUE:   source (1), sink (2)
	-- info-VALUE:   both (3)
	-- info-COMMENT: specifies whether the endpoint should be 
	-- info-COMMENT: a source or sink or in case of bidirectional
	-- info-COMMENT: connection both
	-- info-ROU:     GET db  SET db 
	-- info-IMPL:    V1.3B->
	-- info-VERCTRL: -
	SYNTAX        Xldv11EndpointType 
	ACCESS        read-write
	STATUS        mandatory
	DESCRIPTION
	     " This attribute specifies whether the endpoint 
	     VplTp/VclTp during countinuity check should be a
	     source or sink or both (bidirectional connection only). "
	--DEFAULT test-function-async     fsnActTest
	--DEFAULT next-function-async     fsnActNext
	--DEFAULT set-function-async      fsnActSet
	--DEFAULT get-function-async      fsnActGet
	::= { xldv11AtmCcControl 36 }

     xldv11ActTestTypeUni OBJECT-TYPE
	-- info-LEAF:    xldv11ActTestTypeUni
	-- info-TREE:    xldv11CallP
	-- info-ACC:     rw
	-- info-SYNTAX:  INTEGER
	-- info-VALUE:   segment(1), endToEnd(2) 
	-- info-COMMENT: Type of continuity check.
	-- info-COMMENT: On F5 level (Vc) only segment.
	-- info-COMMENT: on Uni side
	-- info-ROU:     GET db  SET db 
	-- info-IMPL:    V1.3B->
	-- info-VERCTRL: -
	SYNTAX        INTEGER { segment      (1),
				endToEnd     (2) }
	ACCESS        read-write
	STATUS        mandatory
	DESCRIPTION
	     " The type of continuity check segment or endToEnd .
	     On F5 level (Vc) only segment."    
	--DEFAULT test-function-async     fsnActTest
	--DEFAULT next-function-async     fsnActNext
	--DEFAULT set-function-async      fsnActSet
	--DEFAULT get-function-async      fsnActGet
	::= { xldv11AtmCcControl 37 }

     xldv11ActContinuityCheckUni OBJECT-TYPE
	-- info-LEAF:    xldv11ActContinuityCheckUni
	-- info-TREE:    xldv11CallP
	-- info-ACC:     rw
	-- info-SYNTAX:  Xldv11OperState
	-- info-VALUE:   enabled(1)..disabled(2)
	-- info-VALUE:   V1.1U->V1.3N:disabled(2)
	-- info-COMMENT: Enables or disables the continuity check.
	-- info-COMMENT: Currently always disabled 
	-- info-COMMENT: as NT does not support continuity check
	-- info-ROU:     GET db  SET db 
	-- info-IMPL:    V1.3B->
	-- info-VERCTRL: -
	SYNTAX        Xldv11OperState
	ACCESS        read-write
	STATUS        mandatory
	DESCRIPTION
	     " This attribute specifies whether or not the 
	       continuity check should be enabled for this instance of
	       the ATM Cross Connection managed entity .
	       V1.3N->: Currently the value is always disabled as the NT does not
	       support continuity check. "
	--DEFAULT test-function-async     fsnActTest
	--DEFAULT next-function-async     fsnActNext
	--DEFAULT set-function-async      fsnActSet
	--DEFAULT get-function-async      fsnActGet
	::= { xldv11AtmCcControl 38 }

     xldv11ActEndpointTypeUni OBJECT-TYPE
	-- info-LEAF:    xldv11ActEndpointTypeUni
	-- info-TREE:    xldv11CallP
	-- info-ACC:     rw
	-- info-SYNTAX:  Xldv11EndpointType
	-- info-VALUE:   source (1), sink (2)
	-- info-VALUE:   both (3)
	-- info-COMMENT: specifies whether the endpoint should be 
	-- info-COMMENT: a source or sink or in case of bidirectional
	-- info-COMMENT: connection both
	-- info-ROU:     GET db  SET db 
	-- info-IMPL:    V1.3B->
	-- info-VERCTRL: -
	SYNTAX        Xldv11EndpointType
	ACCESS        read-write
	STATUS        mandatory
	DESCRIPTION
	     " This attribute specifies whether the endpoint 
	     VplTp/VclTp during countinuity check should be 
	     source or sink or both (bidirectional connection only). "
	--DEFAULT test-function-async     fsnActTest
	--DEFAULT next-function-async     fsnActNext
	--DEFAULT set-function-async      fsnActSet
	--DEFAULT get-function-async      fsnActGet
	::= { xldv11AtmCcControl 39 }

     xldv11ActControlReqResult OBJECT-TYPE
	-- info-LEAF:    xldv11ActControlReqResult
	-- info-TREE:    xldv11CallP
	-- info-ACC:     ro
	-- info-SYNTAX:  Xldv11ControlReq
	-- info-VALUE:   see xldv11ActControlReq
	-- info-COMMENT: specifies the result of user command
	-- info-ROU:     GET db
	-- info-IMPL:    V1.3N->
	-- info-VERCTRL: -
	SYNTAX        Xldv11ControlReq
	ACCESS        read-only
	STATUS        mandatory
	DESCRIPTION
	     " This attribute informs about the result of 
	     the last user command."
	--DEFAULT next-function-async     fsnActNext
	--DEFAULT get-function-async      fsnActGet
	::= { xldv11AtmCcControl 40 }

     xldv11ActInbandVpi OBJECT-TYPE
	-- info-LEAF:    xldv11ActInbandVpi
	-- info-TREE:    xldv11CallP
	-- info-ACC:     rw
	-- info-SYNTAX:  INTEGER
	-- info-VALUE:   0..4095
	-- info-COMMENT: value of configured inband Vpi
	-- info-ROU:     GET db SET db
	-- info-IMPL:    V1.3N->
	-- info-VERCTRL: -
	SYNTAX        INTEGER (0..4095)
	ACCESS        read-write
	STATUS        mandatory
	DESCRIPTION
	     " The value of the configured inband Vpi.
	     The configured Vpi will be effective only after next reload.  "
	--DEFAULT test-function-async     fsnActTest
	--DEFAULT next-function-async     fsnActNext
	--DEFAULT set-function-async      fsnActSet
	--DEFAULT get-function-async      fsnActGet
	::= { xldv11AtmCcControl 41 }

     xldv11ActInbandVci OBJECT-TYPE
	-- info-LEAF:    xldv11ActInbandVci
	-- info-TREE:    xldv11CallP
	-- info-ACC:     rw
	-- info-SYNTAX:  INTEGER
	-- info-VALUE:   0..65535
	-- info-COMMENT: value of configured inband Vci
	-- info-ROU:     GET db SET db
	-- info-IMPL:    V1.3N->
	-- info-VERCTRL: -
	SYNTAX        INTEGER (0..65535)
	ACCESS        read-write
	STATUS        mandatory
	DESCRIPTION
	     " The value of the configured inband Vci.
	     The configured Vci will be effective only after next reload.  "
	--DEFAULT test-function-async     fsnActTest
	--DEFAULT next-function-async     fsnActNext
	--DEFAULT set-function-async      fsnActSet
	--DEFAULT get-function-async      fsnActGet
	::= { xldv11AtmCcControl 42 }

     xldv11ActCallpTableIndex OBJECT-TYPE
	-- info-LEAF:    xldv11ActCallpTableIndex
	-- info-TREE:    xldv11CallP
	-- info-ACC:     ro
	-- info-SYNTAX:  INTEGER
	-- info-VALUE:   1..4144
	-- info-COMMENT: index of the created/deleted  
	-- info-COMMENT: CallP object after successfull
	-- info-COMMENT: creation or deleteion of cross connect
	-- info-ROU:     GET db
	-- info-IMPL:    V1.3N->
	-- info-VERCTRL: -
	SYNTAX        INTEGER (1..4144)
	ACCESS        read-only
	STATUS        mandatory
	DESCRIPTION
	     " After a successfull creation or deletion of a cross connect
	     CallP provides the index of the created or deleted object."
	--DEFAULT next-function-async     fsnActNext
	--DEFAULT get-function-async      fsnActGet
	::= { xldv11AtmCcControl 43 }

        xldv11ActControlTimeStamp OBJECT-TYPE
        -- info-LEAF:    xldv11ActControlTimeStamp
        -- info-TREE:    xldv11CallP
        -- info-ACC:     ro
        -- info-SYNTAX:  TimeTicks
        -- info-VALUE:   0..2Giga
        -- info-COMMENT: specifies the time stamp in seconds
        -- info-COMMENT: of the last command
        -- info-COMMENT: (end of command)
        -- info-ROU:     GET db
	-- info-IMPL:    V1.3N->
        -- info-VERCTRL: -
        SYNTAX        TimeTicks
        ACCESS        read-only
        STATUS        mandatory
        DESCRIPTION
           " This read-only attribute informs about the time stamp
             of the last command (end of command)."
        --DEFAULT next-function-async     fsnActNext
        --DEFAULT get-function-async      fsnActGet
        ::= { xldv11AtmCcControl 44 }


     -- --------------------------------------------------------------
     --                    ATM Cross Connect Table
     -- --------------------------------------------------------------

     -- This table is valid from version XLDV1.1U.
     --

     xldv11AtmCrossConnectTable OBJECT-TYPE
	-- info-NODE:    xldv11AtmCrossConnectTable
	-- info-TREE:    xldv11CallP
	-- info-ACC:     nac
	-- info-SYNTAX:  SEQUENCE OF Xldv11AtmCrossConnectEntry
	-- info-COMMENT: Table for point-to-point VPL-TP cross connections.
	-- info-IMPL:    V1.0->
	-- info-VERCTRL: -
	SYNTAX        SEQUENCE OF Xldv11AtmCrossConnectEntry
	ACCESS        not-accessible
	STATUS        mandatory
	DESCRIPTION
	     " The ATM cross connect table for point-to-point cross
	       connections. This managed entity is used to represent
	       the cross-connect relationship between two termination
	       points.
	       Instances of this managed entity shall be automatically
	       created and deleted by the management system based on
	       ATM Connect and ATM Disconnect actions performed on
	       an instance of the ATM Cross Connect Control managed
	       entity. They are downloaded after an ONU reload."
	::= { xldv11CallP 2 }

     xldv11AtmCrossConnectEntry OBJECT-TYPE
	-- info-NODE:    xldv11AtmCrossConnectEntry
	-- info-TREE:    xldv11CallP
	-- info-INDEX:   xldv11AccVpiNniIndex
	-- info-ACC:     nac
	-- info-SYNTAX:  Xldv11AtmCrossConnectEntry
	-- info-COMMENT: An entry in the ATM cross connect table.
	-- info-IMPL:    V1.0->
	-- info-VERCTRL: -
	SYNTAX        Xldv11AtmCrossConnectEntry
	ACCESS        not-accessible
	STATUS        mandatory
	DESCRIPTION
	     " An entry in the ATM cross connect table.
	       Notifications : xldv11TrStateChangeOper."
	INDEX         { xldv11AccVpiNniIndex }
	::= { xldv11AtmCrossConnectTable 1 }

     Xldv11AtmCrossConnectEntry ::=
	SEQUENCE { xldv11AccOperationalState   Xldv11OperState,
		   xldv11AccTerminationPointA  INTEGER,
		   xldv11AccTerminationPointZ  INTEGER,
		   xldv11AccLineIndex          Unsigned16,
		   xldv11AccLineIndexLi        Unsigned16,
		   xldv11AccEthVpcIndex        INTEGER,
		   xldv11AccEthVccIndex        INTEGER,
		   xldv11AccVpiNniIndex        INTEGER,
		   xldv11AccAlarmState         Xldv11CallpAlarmState }

     xldv11AccOperationalState OBJECT-TYPE
	-- info-LEAF:    xldv11AccOperationalState
	-- info-TREE:    xldv11CallP
	-- info-ACC:     ro
	-- info-SYNTAX:  Xldv11OperState
	-- info-VALUE:   enabled(1)..disabled(2)
	-- info-COMMENT: Identifies whether or not this instance of
	-- info-COMMENT: ATM Cross Connection managed entity is capable of
	-- info-COMMENT: performing its normal function.
	-- info-ROU:     GET db
	-- info-IMPL:    V1.0->
	-- info-VERCTRL: -
	SYNTAX        Xldv11OperState
	ACCESS        read-only
	STATUS        mandatory
	DESCRIPTION
	     " This attribute identifies whether or not this instance of
	       the ATM Cross Connection managed entity is capable of
	       performing its normal function ( i.e. switching cells ).
	       Altering this attribute is without reporting this state
	       change via the trap 'xldv11TrStateChangeOper'.
	       Range of value: enabled, disabled . "
	--DEFAULT next-function-async     fsnAccEntryNext
	--DEFAULT get-function-async      fsnAccEntryGet
	::= { xldv11AtmCrossConnectEntry 1 }

     xldv11AccTerminationPointA OBJECT-TYPE
	-- info-LEAF:    xldv11AccTerminationPointA
	-- info-TREE:    xldv11CallP
	-- info-ACC:     ro
	-- info-SYNTAX:  INTEGER
	-- info-VALUE:   1..4096+92
	-- info-COMMENT: Identifies the instance of the VPL termination
	-- info-COMMENT: point that represents the VPL at the LE side.
	-- info-ROU:     GET db
	-- info-IMPL:    V1.0->V1.3B:rw, V1.3N->:ro
	-- info-VERCTRL: -
	SYNTAX        INTEGER (1..4188)
	ACCESS        read-only
	STATUS        mandatory
	DESCRIPTION
	     " For a point-to-point cross connect this attribute identifies
	       the instance of the VPL termination point that represents
	       the VPL at the LE side. "
	--DEFAULT next-function-async     fsnAccEntryNext
	--DEFAULT get-function-async      fsnAccEntryGet
	::= { xldv11AtmCrossConnectEntry 2 }

     xldv11AccTerminationPointZ OBJECT-TYPE
	-- info-LEAF:    xldv11AccTerminationPointZ
	-- info-TREE:    xldv11CallP
	-- info-ACC:     ro
	-- info-SYNTAX:  INTEGER
	-- info-VALUE:   1..4096+92
	-- info-COMMENT: Identifies the instance of the VPL termination
	-- info-COMMENT: point that represents the VPL at the NT side.
	-- info-ROU:     GET db
	-- info-IMPL:    V1.0->V1.3B:rw, V1.3N->:ro
	-- info-VERCTRL: -
	SYNTAX        INTEGER (1..4188)
	ACCESS        read-only
	STATUS        mandatory
	DESCRIPTION
	     " For a point-to-point cross connect this attribute identifies
	       the instance of the VPL termination point that represents
	       the VPL at the NT side. "
	--DEFAULT next-function-async     fsnAccEntryNext
	--DEFAULT get-function-async      fsnAccEntryGet
	::= { xldv11AtmCrossConnectEntry 3 }

     xldv11AccLineIndex OBJECT-TYPE
	-- info-LEAF:    xldv11AccLineIndex
	-- info-TREE:    xldv11CallP
	-- info-ACC:     ro
	-- info-SYNTAX:  Unsigned16
	-- info-VALUE:   0..65535
	-- info-COMMENT: Identifies the interfaces belonging to the same line.
	-- info-ROU:     GET db
	-- info-IMPL:    V1.0->V1.3B:rw, V1.3N->:ro
	-- info-VERCTRL: -
	SYNTAX        Unsigned16
	ACCESS        read-only
	STATUS        mandatory
	DESCRIPTION
	     " This value identifies the interface belonging to the
	       same line. "
	--DEFAULT next-function-async     fsnAccEntryNext
	--DEFAULT get-function-async      fsnAccEntryGet
	::= { xldv11AtmCrossConnectEntry 4 }

     xldv11AccLineIndexLi OBJECT-TYPE
	-- info-LEAF:    xldv11AccLineIndexLi
	-- info-TREE:    xldv11CallP
	-- info-ACC:     ro
	-- info-SYNTAX:  Unsigned16
	-- info-VALUE:   0..65535
	-- info-COMMENT: This value identifies the line index of the VpiUni
	-- info-COMMENT: within the LI.
	-- info-ROU:     GET db
	-- info-IMPL:    V1.1U->V1.3B:rw, V1.3N->:ro
	-- info-VERCTRL: -
	SYNTAX        Unsigned16
	ACCESS        read-only
	STATUS        mandatory
	DESCRIPTION
	     " This value identifies the line index of the VpiUni
	       within the LI"
	--DEFAULT next-function-async     fsnAccEntryNext
	--DEFAULT get-function-async      fsnAccEntryGet
	::= { xldv11AtmCrossConnectEntry 5 }

     xldv11AccEthVpcIndex OBJECT-TYPE
	-- info-LEAF:    xldv11AccEthVpcIndex
	-- info-TREE:    xldv11CallP
	-- info-ACC:     ro
	-- info-SYNTAX:  INTEGER
	-- info-VALUE:   0..4144
	-- info-COMMENT: For cross connects at the LIETH this value
	-- info-COMMENT: identifies the belonging VPC .
	-- info-ROU:     GET db
	-- info-IMPL:    V1.1U->V1.3B:rw, V1.3N->:ro
	-- info-VERCTRL: -
	SYNTAX        INTEGER (0..4144)
	ACCESS        read-only
	STATUS        mandatory
	DESCRIPTION
	     " For cross connects at the LIETH this value identifies the 
	       belonging VPC . The value is the entry number in the
	       xldv11VpcTpTable.
	       For all other cross connects the value is always 0."
	--DEFAULT next-function-async     fsnAccEntryNext
	--DEFAULT get-function-async      fsnAccEntryGet
	::= { xldv11AtmCrossConnectEntry 6 }

     xldv11AccEthVccIndex OBJECT-TYPE
	-- info-LEAF:    xldv11AccEthVccIndex
	-- info-TREE:    xldv11CallP
	-- info-ACC:     ro
	-- info-SYNTAX:  INTEGER
	-- info-VALUE:   0..48
	-- info-COMMENT: For cross connects at the LIETH this value
	-- info-COMMENT: identifies the belonging VCC.
	-- info-ROU:     GET db
	-- info-IMPL:    V1.1U->V1.3B:rw, V1.3N->:ro
	-- info-VERCTRL: -
	SYNTAX        INTEGER (0..48)
	ACCESS        read-only
	STATUS        mandatory
	DESCRIPTION
	     " For cross connects at the LIETH this value identifies the 
	       belonging VCC. The value is the entry number in the
	       xldv11VccTpTable.
	       For all other cross connects the value is always 0."
	--DEFAULT next-function-async     fsnAccEntryNext
	--DEFAULT get-function-async      fsnAccEntryGet
	::= { xldv11AtmCrossConnectEntry 7 }
 
     xldv11AccVpiNniIndex OBJECT-TYPE
	-- info-LEAF:    xldv11AccVpiNniIndex
	-- info-TREE:    xldv11CallP
	-- info-ACC:     ro
	-- info-SYNTAX:  INTEGER
	-- info-VALUE:   1..2048
	-- info-COMMENT: Index of an VPL-TP cross connect.
	-- info-ROU:     GET db
	-- info-IMPL:    V1.0->
	-- info-VERCTRL: -
	SYNTAX        INTEGER (1..2048)
	ACCESS        read-only
	STATUS        mandatory
	DESCRIPTION
	     " This attribute is a unique value to identify an ATM
	       cross connect for the download of VP cross connects
	       after a reload. "
	--DEFAULT next-function-async     fsnAccEntryNext
	--DEFAULT get-function-async      fsnAccEntryGet
	::= { xldv11AtmCrossConnectEntry 8 }

     xldv11AccAlarmState OBJECT-TYPE
	-- info-LEAF:    xldv11AccAlarmState
	-- info-TREE:    xldv11CallP
	-- info-ACC:     ro
	-- info-SYNTAX:  Xldv11CallpAlarmState
	-- info-VALUE:   noAlarm(1), alarmPresent(2)
	-- info-COMMENT: indicates whether for the cross connect
	-- info-COMMENT: an alarm is present or not
	-- info-ROU:     GET db
	-- info-IMPL:    V1.3N->
	-- info-VERCTRL: -
	SYNTAX        Xldv11CallpAlarmState
	ACCESS        read-only
	STATUS        mandatory
	DESCRIPTION
	     " This attribute indicates whether for the cross connect
	       an alarm is present or not. "
	--DEFAULT next-function-async     fsnAccEntryNext
	--DEFAULT get-function-async      fsnAccEntryGet
	::= { xldv11AtmCrossConnectEntry 9 }

     -- --------------------------------------------------------------
     --                        VPL TP Table
     -- --------------------------------------------------------------

     -- This table is valid from version XLDV1.1U
     --

     xldv11VplTpTable OBJECT-TYPE
	-- info-NODE:    xldv11VplTpTable
	-- info-TREE:    xldv11CallP
	-- info-ACC:     nac
	-- info-SYNTAX:  SEQUENCE OF Xldv11VplTpEntry
	-- info-COMMENT: This table contains the entries for the VP links.
	-- info-IMPL:    V1.0->
	-- info-VERCTRL: -
	SYNTAX        SEQUENCE OF Xldv11VplTpEntry
	ACCESS        not-accessible
	STATUS        mandatory
	DESCRIPTION
	     " This table contains the entries for Vpl termination
	     points."
	::= { xldv11CallP 3 }

     xldv11VplTpEntry OBJECT-TYPE
	-- info-NODE:    xldv11VplTpEntry
	-- info-TREE:    xldv11CallP
	-- info-INDEX:   xldv11VplIndex
	-- info-ACC:     nac
	-- info-SYNTAX:  Xldv11VplTpEntry
	-- info-COMMENT: Represent the termination of VPLs on an ATM NE.
	-- info-IMPL:    V1.0->
	-- info-VERCTRL: -
	SYNTAX        Xldv11VplTpEntry
	ACCESS        not-accessible
	STATUS        mandatory
	DESCRIPTION
	     " The entries represent the termination of VPLs on an ATM NE.
	       An instance of the ATM Cross Connection managed entity may be
	       used to relate two instances of the VPL Termination Point
	       managed entity (i.e. for point-to-point cross connection).
	       Instances of this managed entity may be created automatically
	       by the ATM NE or as a result of an ATM cross connect request.
	       Similarly instances of this managed entity may be deleted
	       automatically by the ATM NE or as a result of an ATM Cross
	       Connect release request.
	       Notifications : xldv11TrStateChangeOper."
	INDEX         { xldv11VplIndex }
	::= { xldv11VplTpTable 1 }

     Xldv11VplTpEntry ::=
	SEQUENCE { xldv11VplOperationalState          Xldv11OperState,
		   xldv11VplVpiValue                  INTEGER,
		   xldv11VplHwUnitIndex               Unsigned16,
		   xldv11VplIfIndex                   Unsigned16,
		   xldv11VplPeakCellRateUpstream      Unsigned32,
		   xldv11VplPeakCellRateDownstream    Unsigned32,
		   xldv11VplCellDelayVariationToleranceUpstream  INTEGER,
		   xldv11VplCellDelayVariationToleranceDownstream  INTEGER,
		   xldv11VplTrafficType                   Xldv11TrafficType,
		   xldv11VplTrafficDirection              Xldv11TrafficDirection,
		   xldv11VplTrafficPriority               Xldv11TrafficPriority,
		   xldv11VplConnectivityPointer           Integer32,
		   xldv11VplLineIndex                     Unsigned16,
		   xldv11VplLineIndexLi                   Unsigned16,
		   xldv11VplSegmentEndPoint               INTEGER,
		   xldv11VplSustainableCellRateUpstream   Unsigned32, 
		   xldv11VplSustainableCellRateDownstream Unsigned32, 
		   xldv11VplMaximumBurstSizeUpstream      INTEGER,
		   xldv11VplMaximumBurstSizeDownstream    INTEGER,
		   xldv11VplVpcIndex                      Unsigned16,
		   xldv11VplAlarmSeverityIndex            Xldv11AlmSevProfileIndex,
		   xldv11VplAlarmFilteringIndex           Xldv11AlmFiltProfileIndex,
		   xldv11VplCvpIndexSource                INTEGER,    -- continuity check
		   xldv11VplCvpIndexSink                  INTEGER,    -- continuity check
		   xldv11VplIndex                         INTEGER,
		   xldv11VplLOCAlarm                  Xldv11TpAlarmState
		   }

     xldv11VplOperationalState OBJECT-TYPE
	-- info-LEAF:    xldv11VplOperationalState
	-- info-TREE:    xldv11CallP
	-- info-ACC:     ro
	-- info-SYNTAX:  Xldv11OperState
	-- info-VALUE:   enabled(1)..disabled(2)
	-- info-COMMENT: Identifies whether or not the VPL termination
	-- info-COMMENT: is capable of performing its normal functions.
	-- info-ROU:     GET db  SET db 
	-- info-IMPL:    V1.0->
	-- info-VERCTRL: -
	SYNTAX        Xldv11OperState
	ACCESS        read-only
	STATUS        mandatory
	DESCRIPTION
	     " This read-only attribute identifies whether or not the VPL
	       termination is capable of performing its normal functions
	       (in-service or out-of-service).
	       The range of values is enabled, disabled . "
	--DEFAULT test-function-async     fsnVplEntryTest
	--DEFAULT next-function-async     fsnVplEntryNext
	--DEFAULT set-function-async      fsnVplEntrySet
	--DEFAULT get-function-async      fsnVplEntryGet
	::= { xldv11VplTpEntry 1 }

     xldv11VplVpiValue OBJECT-TYPE
	-- info-LEAF:    xldv11VplVpiValue
	-- info-TREE:    xldv11CallP
	-- info-ACC:     ro
	-- info-SYNTAX:  INTEGER
	-- info-VALUE:   0..4095
	-- info-COMMENT: The VPI value associated with the VPL-TP.
	-- info-ROU:     GET db
	-- info-IMPL:    V1.0:rw->V1.3B V1.3N->
	-- info-VERCTRL: -
	SYNTAX        INTEGER (0..4095)
	ACCESS        read-only
	STATUS        mandatory
	DESCRIPTION
	     " This attribute identifies the VPI value associated with the
	       VP link being terminated. "
	--DEFAULT next-function-async     fsnVplEntryNext
	--DEFAULT get-function-async      fsnVplEntryGet
	::= { xldv11VplTpEntry 2 }

     xldv11VplHwUnitIndex OBJECT-TYPE
	-- info-LEAF:    xldv11VplHwUnitIndex
	-- info-TREE:    xldv11CallP
	-- info-ACC:     ro
	-- info-SYNTAX:  Unsigned16
	-- info-VALUE:   0..65535
	-- info-COMMENT: Index of HWM sublayer (LU* or LI*).
	-- info-ROU:     GET db
	-- info-IMPL:    V1.0:rw->V1.3B:rw V1.3N->
	-- info-VERCTRL: -
	SYNTAX        Unsigned16 
	ACCESS        read-only
	STATUS        mandatory
	DESCRIPTION
	     " The unique identifier for hardware units,
	       here the HWM sublayer (LU* or LI*). "
	--DEFAULT next-function-async     fsnVplEntryNext
	--DEFAULT get-function-async      fsnVplEntryGet
	::= { xldv11VplTpEntry 3 }

     xldv11VplIfIndex OBJECT-TYPE
	-- info-LEAF:    xldv11VplIfIndex
	-- info-TREE:    xldv11CallP
	-- info-ACC:     ro
	-- info-SYNTAX:  Unsigned16
	-- info-VALUE:   0..65535
	-- info-COMMENT: The TLM interface index of the connected PPTP
	-- info-COMMENT: in the LI. 
	-- info-ROU:     GET db
	-- info-IMPL:    V1.0:rw->V1.3B V1.3N->
	-- info-VERCTRL: -
	SYNTAX        Unsigned16 
	ACCESS        read-only
	STATUS        mandatory
	DESCRIPTION
	     "V1.0->V1.1U: ifIndex of tca of LI*.
	      V1.2->V1.3: The TLM interface index of the connected PPTP 
	     in the LI. "
	--DEFAULT next-function-async     fsnVplEntryNext
	--DEFAULT get-function-async      fsnVplEntryGet
	::= { xldv11VplTpEntry 4 }

     xldv11VplPeakCellRateUpstream OBJECT-TYPE
	-- info-LEAF:    xldv11VplPeakCellRateUpstream
	-- info-TREE:    xldv11CallP
	-- info-ACC:     ro
	-- info-SYNTAX:  Unsigned32
	-- info-VALUE:   0..2 Giga 
	-- info-VALUE:   (default: 800 000)
	-- info-COMMENT: Identifies the upstream peak cell rate of the
	-- info-COMMENT: VP cross connect. 
	-- info-COMMENT: unit bit/sec
	-- info-ROU:     GET db
	-- info-IMPL:    V1.1U:rw->V1.3B:rw V1.3N->
	-- info-VERCTRL: -
	SYNTAX        Unsigned32
	ACCESS        read-only
	STATUS        mandatory
	DESCRIPTION
	     " This attribute identifies the upstream peak cell rate
	       in bit/sec of the VP cross connect. Default value: 800 000"
	--DEFAULT next-function-async     fsnVplEntryNext
	--DEFAULT get-function-async      fsnVplEntryGet
	::= { xldv11VplTpEntry 5 }

     xldv11VplPeakCellRateDownstream OBJECT-TYPE
	-- info-LEAF:    xldv11VplPeakCellRateDownstream
	-- info-TREE:    xldv11CallP
	-- info-ACC:     ro
	-- info-SYNTAX:  Unsigned32
	-- info-VALUE:   0..2 Giga (default: 2 000 000)
	-- info-COMMENT: Identifies the downstream peak cell rate of the
	-- info-COMMENT: VP cross connect. 
	-- info-COMMENT: unit bit/sec
	-- info-ROU:     GET db
	-- info-IMPL:    V1.1U:rw->V1.3B V1.3N->
	-- info-VERCTRL: -
	SYNTAX        Unsigned32
	ACCESS        read-only
	STATUS        mandatory
	DESCRIPTION
	     " This attribute identifies the downstream peak cell rate
	       in bit/sec of the VP cross connect. 
	       Default value: 2 000 000. "
	--DEFAULT next-function-async     fsnVplEntryNext
	--DEFAULT get-function-async      fsnVplEntryGet
	::= { xldv11VplTpEntry 6 }

     xldv11VplCellDelayVariationToleranceUpstream OBJECT-TYPE
	-- info-LEAF:    xldv11VplCellDelayVariationToleranceUpstream
	-- info-TREE:    xldv11CallP
	-- info-ACC:     ro
	-- info-SYNTAX:  INTEGER
	-- info-VALUE:   200..360,000,000 (default: 360,000,000)
	-- info-COMMENT: Identifies the upstream cell delay variation (in nsec)
	-- info-COMMENT: of the VP cross connect.
	-- info-ROU:     GET db
	-- info-IMPL:    V1.1U:rw->V1.3B:rw V1.3N->
	-- info-VERCTRL: -
	SYNTAX        INTEGER(200..360000000)
	ACCESS        read-only
	STATUS        mandatory
	DESCRIPTION
	     " This attribute identifies the upstream cell delay variation (in nsec)
	       of the VP cross connect. "
	--DEFAULT next-function-async     fsnVplEntryNext
	--DEFAULT get-function-async      fsnVplEntryGet
	::= { xldv11VplTpEntry 7 }

     xldv11VplCellDelayVariationToleranceDownstream OBJECT-TYPE
	-- info-LEAF:    xldv11VplCellDelayVariationToleranceDownstream
	-- info-TREE:    xldv11CallP
	-- info-ACC:     ro
	-- info-SYNTAX:  INTEGER
	-- info-VALUE:   200..360,000,000 (default: 200)
	-- info-COMMENT: Identifies the downstream cell delay variation (in nsec)
	-- info-COMMENT: of the VP cross connect.
	-- info-ROU:     GET db
	-- info-IMPL:    V1.1U:rw->V1.3B V1.3N->
	-- info-VERCTRL: -
	SYNTAX        INTEGER(200..360000000)
	ACCESS        read-only
	STATUS        mandatory
	DESCRIPTION
	     " This attribute identifies the downstream cell delay variation (in nsec)
	       of the VP cross connect. "
	--DEFAULT next-function-async     fsnVplEntryNext
	--DEFAULT get-function-async      fsnVplEntryGet
	::= { xldv11VplTpEntry 8 }

     xldv11VplTrafficType OBJECT-TYPE
	-- info-LEAF:    xldv11VplTrafficType
	-- info-TREE:    xldv11CallP
	-- info-ACC:     ro
	-- info-SYNTAX:  Xldv11TrafficType
	-- info-VALUE:   cbr(V1.1U->), ubr(V1.2A->), nrtVbr(V1.3A->)
	-- info-VALUE:   rtVbr(V1.3A->) (default: cbr)
	-- info-COMMENT: Identifies the traffic type of the VP cross connect.
	-- info-ROU:     GET db
	-- info-IMPL:    V1.1U:rw->V1.3B:rw V1.3N->
	-- info-VERCTRL: -
	SYNTAX        Xldv11TrafficType
	ACCESS        read-only
	STATUS        mandatory
	DESCRIPTION
	     " This attribute identifies the traffic type of the
	       VP cross connect. 
	       Range of value: 
		     constant bit rate    cbr
		     unspecified bit rate ubr
		     For V1.3:            nrtVbr
					  rtVbr
	       Default value: constant bit rate (cbr) . "
	--DEFAULT next-function-async     fsnVplEntryNext
	--DEFAULT get-function-async      fsnVplEntryGet
	::= { xldv11VplTpEntry 9 }

     xldv11VplTrafficDirection OBJECT-TYPE
	-- info-LEAF:    xldv11VplTrafficDirection
	-- info-TREE:    xldv11CallP
	-- info-ACC:     ro
	-- info-SYNTAX:  Xldv11TrafficDirection
	-- info-VALUE:   bidirectional, upstream, downstream (default: bidirectional)
	-- info-COMMENT: Identifies the traffic Direction.
	-- info-ROU:     GET db
	-- info-IMPL:    V1.2B:rw->V1.3B:rw V1.3N->
	-- info-VERCTRL: -
	SYNTAX        Xldv11TrafficDirection
	ACCESS        read-only
	STATUS        mandatory
	DESCRIPTION
	     " This attribute identifies the traffic direction.
	       Range of value: 
		     bidirectional, upstream, downstream.
	       Default value: bidirectional"
	--DEFAULT next-function-async     fsnVplEntryNext
	--DEFAULT get-function-async      fsnVplEntryGet
	::= { xldv11VplTpEntry 10 }

     xldv11VplTrafficPriority OBJECT-TYPE
	-- info-LEAF:    xldv11VplTrafficPriority
	-- info-TREE:    xldv11CallP
	-- info-ACC:     ro
	-- info-SYNTAX:  Xldv11TrafficPriority
	-- info-VALUE:   low, high(default: high)
	-- info-COMMENT: Identifies the traffic priority.
	-- info-ROU:     GET db
	-- info-IMPL:    V1.3A:rw->V1.3B:rw V1.3N->
	-- info-VERCTRL: -
	SYNTAX        Xldv11TrafficPriority
	ACCESS        read-only
	STATUS        mandatory
	DESCRIPTION
	     " This attribute identifies the traffic priority.
	       Range of value: low, high.
	       Default value: high"
	--DEFAULT next-function-async     fsnVplEntryNext
	--DEFAULT get-function-async      fsnVplEntryGet
	::= { xldv11VplTpEntry 11 }

     xldv11VplConnectivityPointer OBJECT-TYPE
	-- info-LEAF:    xldv11VplConnectivityPointer
	-- info-TREE:    xldv11CallP
	-- info-ACC:     ro
	-- info-SYNTAX:  Integer32
	-- info-VALUE:   -2147483648..2147483647
	-- info-COMMENT: Serves as a pointer to the instance of the
	-- info-COMMENT: VPL termination point managed entity instance
	-- info-COMMENT: (in the ATM NE) it is cross connected to.
	-- info-ROU:     GET db
	-- info-IMPL:    V1.0:rw->V1.3B:rw V1.3N->
	-- info-VERCTRL: -
	SYNTAX        Integer32
	ACCESS        read-only
	STATUS        mandatory
	DESCRIPTION
	     " This attribute serves as a pointer to the instance of the
	       VPL termination point managed entity instance (in the ATM
	       NE) it is cross connected to. "
	--DEFAULT next-function-async     fsnVplEntryNext
	--DEFAULT get-function-async      fsnVplEntryGet
	::= { xldv11VplTpEntry 12 }

     xldv11VplLineIndex OBJECT-TYPE
	-- info-LEAF:    xldv11VplLineIndex
	-- info-TREE:    xldv11CallP
	-- info-ACC:     ro
	-- info-SYNTAX:  Unsigned16
	-- info-VALUE:   0..65535
	-- info-COMMENT: Identifies the belonging line.
	-- info-ROU:     GET db
	-- info-IMPL:    V1.0:rw->V1.3B:rw V1.3N->
	-- info-VERCTRL: -
	SYNTAX        Unsigned16
	ACCESS        read-only
	STATUS        mandatory
	DESCRIPTION
	     " This value identifies the belonging line. "
	--DEFAULT next-function-async     fsnVplEntryNext
	--DEFAULT get-function-async      fsnVplEntryGet
	::= { xldv11VplTpEntry 13 }

     xldv11VplLineIndexLi OBJECT-TYPE
	-- info-LEAF:    xldv11VplLineIndexLi
	-- info-TREE:    xldv11CallP
	-- info-ACC:     ro
	-- info-SYNTAX:  Unsigned16
	-- info-VALUE:   0..65535
	-- info-COMMENT: Identifies the Line Index in the LI.
	-- info-ROU:     GET db
	-- info-IMPL:    V1.1U:rw->V1.3B:rw V1.3N->
	-- info-VERCTRL: -
	SYNTAX        Unsigned16
	ACCESS        read-only
	STATUS        mandatory
	DESCRIPTION
	     " This value identifies the line index in the LI. "
	--DEFAULT next-function-async     fsnVplEntryNext
	--DEFAULT get-function-async      fsnVplEntryGet
	::= { xldv11VplTpEntry 14 }

     xldv11VplSegmentEndPoint    OBJECT-TYPE
	-- info-LEAF:    xldv11VplSegmentEndPoint
	-- info-TREE:    xldv11CallP
	-- info-ACC:     ro
	-- info-SYNTAX:  INTEGER
	-- info-VALUE:   yes(1)..no (2)
	-- info-COMMENT: Specifies whether the VlpTp is a segment
	-- info-COMMENT: endpoint (yes) or a connecting point (no). 
	-- info-ROU:     GET db
	-- info-IMPL:    V1.2B:rw->V1.3B:rw V1.3N->
	-- info-VERCTRL: -
	SYNTAX        INTEGER { yes(1), 
				no (2)    }
	ACCESS        read-only
	STATUS        mandatory
	DESCRIPTION
	     "  This value specifies whether the VplTp is 
		a segment endpoint (yes) or a connecting point (no). "
	--DEFAULT next-function-async     fsnVplEntryNext
	--DEFAULT get-function-async      fsnVplEntryGet
	::= { xldv11VplTpEntry 15 }

     xldv11VplSustainableCellRateUpstream OBJECT-TYPE
	-- info-LEAF:    xldv11VplSustainableCellRateUpstream
	-- info-TREE:    xldv11CallP
	-- info-ACC:     ro
	-- info-SYNTAX:  Unsigned32
	-- info-VALUE:   0..2 Giga (default: 800 000)
	-- info-COMMENT: Sustainable upstream cell rate in cells/sec
	-- info-COMMENT: for nrtVbr traffic.
	-- info-ROU:     GET db
	-- info-IMPL:    V1.3A:rw->V1.3B:rw V1.3N->
	-- info-VERCTRL: -
	SYNTAX        Unsigned32
	ACCESS        read-only
	STATUS        mandatory
	DESCRIPTION
	     "  The sustainable upstream cell rate in cells/sec 
		for nrtVbr traffic.
		Default Value:   upstream: 800 000."
	--DEFAULT next-function-async     fsnVplEntryNext
	--DEFAULT get-function-async      fsnVplEntryGet
	::= { xldv11VplTpEntry  16 }

     xldv11VplSustainableCellRateDownstream OBJECT-TYPE
	-- info-LEAF:    xldv11VplSustainableCellRateDownstream
	-- info-TREE:    xldv11CallP
	-- info-ACC:     ro
	-- info-SYNTAX:  Unsigned32
	-- info-VALUE:   0.. 2 Giga (default: 8 Mega)
	-- info-COMMENT: Sustainable Downstream cell rate in cells/sec
	-- info-COMMENT: for nrtVbr traffic.
	-- info-ROU:     GET db
	-- info-IMPL:    V1.3A:rw->V1.3B:rw V1.3N->
	-- info-VERCTRL: -
	SYNTAX        Unsigned32
	ACCESS        read-only
	STATUS        mandatory
	DESCRIPTION
	     "  The sustainable downstream cell rate in cells/sec 
		for nrtVbr traffic.
		Default Value:   8 Mega"
	--DEFAULT next-function-async     fsnVplEntryNext
	--DEFAULT get-function-async      fsnVplEntryGet
	::= { xldv11VplTpEntry  17}

     xldv11VplMaximumBurstSizeUpstream OBJECT-TYPE
	-- info-LEAF:    xldv11VplMaximumBurstSizeUpstream
	-- info-TREE:    xldv11CallP
	-- info-ACC:     ro
	-- info-SYNTAX:  Integer32
	-- info-VALUE:   1..1500 (default: 32)
	-- info-COMMENT: The maximum upstream burst size tolerance in cells/sec
	-- info-COMMENT: for nrtVbr traffic.
	-- info-ROU:     GET db
	-- info-IMPL:    V1.3A:rw->V1.3B:rw V1.3N->
	-- info-VERCTRL: -
	SYNTAX        INTEGER(1..1500)
	ACCESS        read-only
	STATUS        mandatory
	DESCRIPTION
	     "  The maximum upstream burst size tolerance in cells/sec 
		for nrtVbr traffic.
		Default Value:  32."
	--DEFAULT next-function-async     fsnVplEntryNext
	--DEFAULT get-function-async      fsnVplEntryGet
	::= { xldv11VplTpEntry  18 }

     xldv11VplMaximumBurstSizeDownstream OBJECT-TYPE
	-- info-LEAF:    xldv11VplMaximumBurstSizeDownstream
	-- info-TREE:    xldv11CallP
	-- info-ACC:     ro
	-- info-SYNTAX:  Integer32
	-- info-VALUE:   1..18 800 (default: 32)
	-- info-COMMENT: The maximum downstream burst size tolerance in cells/sec
	-- info-COMMENT: for nrtVbr traffic.
	-- info-ROU:     GET db
	-- info-IMPL:    V1.3A:rw->V1.3B:rw V1.3N->
	-- info-VERCTRL: -
	SYNTAX        INTEGER(1..18800)
	ACCESS        read-only
	STATUS        mandatory
	DESCRIPTION
	     "  The maximum downstream burst size tolerance in cells/sec 
		for nrtVbr traffic.
		Default Value:  32."
	--DEFAULT next-function-async     fsnVplEntryNext
	--DEFAULT get-function-async      fsnVplEntryGet
	::= { xldv11VplTpEntry  19 }

	xldv11VplVpcIndex OBJECT-TYPE
	-- info-LEAF:    xldv11VplVpcIndex
	-- info-TREE:    xldv11Callp
	-- info-ACC:     ro
	-- info-SYNTAX:  Unsigned16
	-- info-VALUE:   0..65535
	-- info-COMMENT: Index of the related VpcTpTable entry.
	-- info-ROU:     GET db
	-- info-IMPL:    V1.1U:rw->V1.3B:rw V1.3N->
	-- info-VERCTRL: -
	SYNTAX        Unsigned16
	ACCESS        read-only
	STATUS        mandatory
	DESCRIPTION
	     "  The index of the related VpcTpTable entry. "
	--DEFAULT next-function-async     fsnVplEntryNext
	--DEFAULT get-function-async      fsnVplEntryGet
	::= { xldv11VplTpEntry  20 }
 
     xldv11VplAlarmSeverityIndex OBJECT-TYPE  -- continuity check
	-- info-LEAF:    xldv11VplAlarmSeverityIndex
	-- info-TREE:    xldv11CallP
	-- info-ACC:     rw
	-- info-SYNTAX:  Xldv11AlmSevProfileIndex
	-- info-VALUE:   1..40
	-- info-COMMENT: - 
	-- info-ROU:     GET db SET db
	-- info-IMPL:    V1.3A->
	-- info-VERCTRL: -
	SYNTAX        Xldv11AlmSevProfileIndex
	ACCESS        read-write
	STATUS        mandatory
	DESCRIPTION
	     " It is a pointer to the instance of the alarm severity
	       assignment profile managed entity that contains the severity
	       assignments for the alarms reported by this managed entity.
	       (Not implemented in XLD V1.0 and XLD V1.1U).  Default is 1. "
	--DEFAULT test-function-async     fsnVplEntryTest
	--DEFAULT next-function-async     fsnVplEntryNext
	--DEFAULT set-function-async      fsnVplEntrySet
	--DEFAULT get-function-async      fsnVplEntryGet
	::= { xldv11VplTpEntry 21 }

     xldv11VplAlarmFilteringIndex OBJECT-TYPE
	-- info-LEAF:    xldv11VplAlarmFilteringIndex
	-- info-TREE:    xldv11CallP
	-- info-ACC:     ro
	-- info-SYNTAX:  Xldv11AlmFiltProfileIndex
	-- info-VALUE:   1..40
	-- info-COMMENT: - 
	-- info-ROU:     GET db
	-- info-IMPL:    V1.x
	-- info-VERCTRL: -
	SYNTAX        Xldv11AlmFiltProfileIndex
	ACCESS        not-accessible
	STATUS        mandatory
	DESCRIPTION
	     " It is a pointer to the instance of the alarm filtering
	       assignment profile managed entity that contains the filtering
	       assignments for the alarms reported by this managed entity.
	       (Not implemented) "
	--DEFAULT next-function-async     fsnVplEntryNext
	--DEFAULT get-function-async      fsnVplEntryGet
	::= { xldv11VplTpEntry 22 }

	xldv11VplCvpIndexSource OBJECT-TYPE
	-- info-LEAF:    xldv11VplCvpIndexSource
	-- info-TREE:    xldv11Callp
	-- info-ACC:     ro
	-- info-SYNTAX:  INTEGER (1..4188)
	-- info-VALUE:   0..4096+92
	-- info-COMMENT: Index of the source for continuity check.
	-- info-COMMENT: related ContinuityCheckVplTpTable entry.
	-- info-COMMENT: Default 0
	-- info-ROU:     GET db
	-- info-IMPL:    V1.3B->
	-- info-VERCTRL: -
	SYNTAX        INTEGER (1..4188)
	ACCESS        read-only
	STATUS        mandatory
	DESCRIPTION
	     "  The index of continuity check source in the 
	     ContinuityCheckVplTpTable. Default 0."
	--DEFAULT next-function-async     fsnVplEntryNext
	--DEFAULT get-function-async      fsnVplEntryGet
	::= { xldv11VplTpEntry  23 }

	xldv11VplCvpIndexSink OBJECT-TYPE
	-- info-LEAF:    xldv11VplCvpIndexSink
	-- info-TREE:    xldv11Callp
	-- info-ACC:     ro
	-- info-SYNTAX:  INTEGER (1..4188)
	-- info-VALUE:   0..4096+92
	-- info-COMMENT: Index of the sink for continuity check.
	-- info-COMMENT: related ContinuityCheckVplTpTable entry.
	-- info-COMMENT: Default 0
	-- info-ROU:     GET db
	-- info-IMPL:    V1.3B->
	-- info-VERCTRL: -
	SYNTAX        INTEGER (1..4188)
	ACCESS        read-only
	STATUS        mandatory
	DESCRIPTION
	     "  The index of continuity check sink in the 
	     ContinuityCheckVplTpTable. "
	--DEFAULT next-function-async     fsnVplEntryNext
	--DEFAULT get-function-async      fsnVplEntryGet
	::= { xldv11VplTpEntry  24 }

     xldv11VplIndex OBJECT-TYPE
	-- info-LEAF:    xldv11VplIndex
	-- info-TREE:    xldv11Callp
	-- info-ACC:     ro
	-- info-SYNTAX:  INTEGER
	-- info-VALUE:   1..4096+92
	-- info-COMMENT: Identifies an entry in the VPL table.
	-- info-ROU:     GET db
	-- info-IMPL:    V1.0->
	-- info-VERCTRL: -
	SYNTAX        INTEGER (1..4188)
	ACCESS        read-only
	STATUS        mandatory
	DESCRIPTION
	     " A unique value to identify an entry in the VPL table. "
	--DEFAULT next-function-async     fsnVplEntryNext
	--DEFAULT get-function-async      fsnVplEntryGet
	::= { xldv11VplTpEntry 25 }

     xldv11VplLOCAlarm OBJECT-TYPE
	-- info-LEAF:    xldv11VplLOCAlarm
	-- info-TREE:    xldv11Callp
	-- info-ACC:     ro
	-- info-SYNTAX:  Xldv11TpAlarmState
	-- info-VALUE:   noAlarm(1), upstreamAlarm(2),
	-- info-VALUE:   downstreamAlarm(3), upAndDownstreamAlarm(4)
	-- info-COMMENT: indicates an LOC alarm and its direction
	-- info-ROU:     GET db
	-- info-IMPL:    V1.3N->
	-- info-VERCTRL: -
	SYNTAX        Xldv11TpAlarmState
	ACCESS        read-only
	STATUS        mandatory
	DESCRIPTION
	     " Indicates an LOC alarm and its direction. 
	     Range of values :
	     noAlarm(1), upstreamAlarm(2),
	     downstreamAlarm(3), upAndDownstreamAlarm(4) ."
	--DEFAULT next-function-async     fsnVplEntryNext
	--DEFAULT get-function-async      fsnVplEntryGet
	::= { xldv11VplTpEntry 26 }

     -- --------------------------------------------------------------
     --                        VPC TP Table
     -- --------------------------------------------------------------

     xldv11VpcTpTable OBJECT-TYPE
	-- info-NODE:    xldv11VpcTpTable
	-- info-TREE:    xldv11CallP
	-- info-ACC:     nac
	-- info-SYNTAX:  SEQUENCE OF Xldv11VpcTpEntry
	-- info-COMMENT: VpcTp table 
	-- info-IMPL:    V1.1U->
	-- info-VERCTRL: -
	SYNTAX        SEQUENCE OF Xldv11VpcTpEntry
	ACCESS        not-accessible
	STATUS        mandatory
	DESCRIPTION
	     " This table contains the entries for the termination points
	       of the VP connections."
	::= { xldv11CallP 4 }

     xldv11VpcTpEntry OBJECT-TYPE
	-- info-NODE:    xldv11VpcTpEntry
	-- info-TREE:    xldv11CallP
	-- info-INDEX:   xldv11VpcIndex
	-- info-ACC:     nac
	-- info-SYNTAX:  Xldv11VpcTpEntry
	-- info-COMMENT: - 
	-- info-IMPL:    V1.1U->
	-- info-VERCTRL: - 
	SYNTAX        Xldv11VpcTpEntry
	ACCESS        not-accessible
	STATUS        mandatory
	DESCRIPTION
	       "Each entry represents the point in the switch
	       where the VPC and its associated overhead (F4 OAM cells) are 
	       terminated or originated.
	       Instances of this managed entity may be created automatically
	       by the ATM NE or as a result of an ATM cross connect request.
	       Similarly instances of this managed entity may be deleted
	       automatically by the ATM NE or as a result of an ATM Cross
	       Connect release request.
	       Notifications : 
	       xldv11TrVpcTpRDI,
	       xldv11VpcTpAIS alarms when fault is detected or cleared.
	       xldv11TrStateChangeOper."
	INDEX         { xldv11VpcIndex }
	::= { xldv11VpcTpTable 1 }

     Xldv11VpcTpEntry ::=
	SEQUENCE { xldv11VpcOperationalState     Xldv11OperState,
		   xldv11VpcVpiValue             INTEGER,
		   xldv11VpcIfIndex              Unsigned16,
		   xldv11VpcHwUnitIndex          Unsigned16,
		   xldv11VpcAlarmSeverityIndex   Xldv11AlmSevProfileIndex,
		   xldv11VpcAlarmFilteringIndex  Xldv11AlmFiltProfileIndex,
		   xldv11VpcLineIndex            Unsigned16,
		   xldv11VpcLineIndexLi          Unsigned16,
		   xldv11VpcVplIndex             INTEGER,
		   xldv11VpcIndex                INTEGER,
		   xldv11VpcAISAlarm             Xldv11TpAlarmState,
		   xldv11VpcRDIAlarm             Xldv11TpAlarmState,
		   xldv11VpcLOCAlarm             Xldv11TpAlarmState,
		   xldv11VpcEmSpecific           Unsigned16
		   }

     xldv11VpcOperationalState OBJECT-TYPE
	-- info-LEAF:    xldv11VpcOperationalState
	-- info-TREE:    xldv11CallP
	-- info-ACC:     ro
	-- info-SYNTAX:  Xldv11OperState
	-- info-VALUE:   enabled, disabled
	-- info-COMMENT: - 
	-- info-ROU:     GET db
	-- info-IMPL:    V1.1U->
	-- info-VERCTRL: - 
	SYNTAX        Xldv11OperState
	ACCESS        read-only
	STATUS        mandatory
	DESCRIPTION
	     " This read-only attribute identifies whether or not the VPL
	       termination is capable of performing its normal functions
	       (in-service or out-of-service).
	       The range of values is enabled, disabled. "
	--DEFAULT next-function-async     fsnVpcEntryNext
	--DEFAULT get-function-async      fsnVpcEntryGet
	::= { xldv11VpcTpEntry 1 }

     xldv11VpcVpiValue OBJECT-TYPE
	-- info-LEAF:    xldv11VpcVpiValue
	-- info-TREE:    xldv11CallP
	-- info-ACC:     ro
	-- info-SYNTAX:  INTEGER
	-- info-VALUE:   0..4095
	-- info-COMMENT: - 
	-- info-ROU:     GET db
	-- info-IMPL:    V1.1U:rw->V1.3B V1.3N->
	-- info-VERCTRL: - 
	SYNTAX        INTEGER (0..4095)
	ACCESS        read-only
	STATUS        mandatory
	DESCRIPTION
	     " This attribute is the value of this VPC."
	--DEFAULT next-function-async     fsnVpcEntryNext
	--DEFAULT get-function-async      fsnVpcEntryGet
	::= { xldv11VpcTpEntry 2 }

     xldv11VpcIfIndex OBJECT-TYPE
	-- info-LEAF:    xldv11VpcIfIndex
	-- info-TREE:    xldv11CallP
	-- info-ACC:     ro
	-- info-SYNTAX:  Unsigned16
	-- info-VALUE:   -
	-- info-COMMENT: IfIndex of connected PPTP at LI*
	-- info-ROU:     GET db
	-- info-IMPL:    V1.1U:rw->V1.3B V1.3N->
	-- info-VERCTRL: - 
	SYNTAX        Unsigned16
	ACCESS        read-only
	STATUS        mandatory
	DESCRIPTION
	     " The TLM interface index of the connected PPTP in the LI."
	--DEFAULT next-function-async     fsnVpcEntryNext
	--DEFAULT get-function-async      fsnVpcEntryGet
	::= { xldv11VpcTpEntry 3 }

     xldv11VpcHwUnitIndex OBJECT-TYPE
	-- info-LEAF:    xldv11VpcHwUnitIndex
	-- info-TREE:    xldv11CallP
	-- info-ACC:     ro
	-- info-SYNTAX:  Unsigned16
	-- info-VALUE:   -
	-- info-COMMENT: HwUnitIndex of dependent PIU 
	-- info-ROU:     GET db
	-- info-IMPL:    V1.1U:rw->V1.3B V1.3N->
	-- info-VERCTRL: - 
	SYNTAX        Unsigned16 
	ACCESS        read-only
	STATUS        mandatory
	DESCRIPTION
	     " The unique identifier for hardware units,
	       here the HWM sublayer (CMU or LI*). " 
	--DEFAULT next-function-async     fsnVpcEntryNext
	--DEFAULT get-function-async      fsnVpcEntryGet
	::= { xldv11VpcTpEntry 4 }

     xldv11VpcAlarmSeverityIndex OBJECT-TYPE
	-- info-LEAF:    xldv11VpcAlarmSeverityIndex
	-- info-TREE:    xldv11CallP
	-- info-ACC:     rw
	-- info-SYNTAX:  Xldv11AlmSevProfileIndex
	-- info-VALUE:   1..40
	-- info-COMMENT: - 
	-- info-ROU:     GET db SET db
	-- info-IMPL:    V1.1U:ro->V1.3H:ro V1.3A->
	-- info-VERCTRL: -
	SYNTAX        Xldv11AlmSevProfileIndex
	ACCESS        read-write
	STATUS        mandatory
	DESCRIPTION
	     " It is a pointer to the instance of the alarm severity
	       assignment profile managed entity that contains the severity
	       assignments for the alarms reported by this managed entity.
	       (Not implemented in XLD V1.0 and XLD V1.1U).  Default is 1. "
	--DEFAULT test-function-async     fsnVpcEntryTest
	--DEFAULT next-function-async     fsnVpcEntryNext
	--DEFAULT set-function-async      fsnVpcEntrySet
	--DEFAULT get-function-async      fsnVpcEntryGet
	::= { xldv11VpcTpEntry 5 }

     xldv11VpcAlarmFilteringIndex OBJECT-TYPE
	-- info-LEAF:    xldv11VpcAlarmFilteringIndex
	-- info-TREE:    xldv11CallP
	-- info-ACC:     ro
	-- info-SYNTAX:  Xldv11AlmFiltProfileIndex
	-- info-VALUE:   1..40
	-- info-COMMENT: - 
	-- info-ROU:     GET db
	-- info-IMPL:    V1.x
	-- info-VERCTRL: -
	SYNTAX        Xldv11AlmFiltProfileIndex
	ACCESS        read-only
	STATUS        mandatory
	DESCRIPTION
	     " It is a pointer to the instance of the alarm filtering
	       assignment profile managed entity that contains the filtering
	       assignments for the alarms reported by this managed entity.
	       (Not implemented) "
	--DEFAULT next-function-async     fsnVpcEntryNext
	--DEFAULT get-function-async      fsnVpcEntryGet
	::= { xldv11VpcTpEntry 6 }

     xldv11VpcLineIndex OBJECT-TYPE
	-- info-LEAF:    xldv11VpcLineIndex
	-- info-TREE:    xldv11CallP
	-- info-ACC:     ro
	-- info-SYNTAX:  Unsigned16
	-- info-VALUE:   -
	-- info-COMMENT: Identifies the line within ONU and NTAD*
	-- info-ROU:     GET db
	-- info-IMPL:    V1.1U:rw->V1.3B V1.3N->
	-- info-VERCTRL: - 
	SYNTAX        Unsigned16
	ACCESS        read-only
	STATUS        mandatory
	DESCRIPTION
	     " This value identifies the belonging line. "
	--DEFAULT next-function-async     fsnVpcEntryNext
	--DEFAULT get-function-async      fsnVpcEntryGet
	::= { xldv11VpcTpEntry 7 }

     xldv11VpcLineIndexLi OBJECT-TYPE
	-- info-LEAF:    xldv11VpcLineIndexLi
	-- info-TREE:    xldv11CallP
	-- info-ACC:     ro
	-- info-SYNTAX:  Unsigned16
	-- info-VALUE:   -
	-- info-COMMENT: Identifies the line within the LI*
	-- info-ROU:     GET db
	-- info-IMPL:    V1.1U:rw->V1.3B V1.3N->
	-- info-VERCTRL: - 
	SYNTAX        Unsigned16
	ACCESS        read-only
	STATUS        mandatory
	DESCRIPTION
	     " This value identifies the line index in the LI. "
	--DEFAULT next-function-async     fsnVpcEntryNext
	--DEFAULT get-function-async      fsnVpcEntryGet
	::= { xldv11VpcTpEntry 8 }
 
	xldv11VpcVplIndex OBJECT-TYPE
	-- info-LEAF:    xldv11VpcVplIndex
	-- info-TREE:    xldv11Callp
	-- info-ACC:     ro
	-- info-SYNTAX:  INTEGER
	-- info-VALUE:   1..4188
	-- info-COMMENT: Index of related VplTp-Table entry
	-- info-ROU:     GET db
	-- info-IMPL:    V1.1U:rw->V1.3B V1.3N->
	-- info-VERCTRL: - 
	SYNTAX        INTEGER (1..4188)
	ACCESS        read-only
	STATUS        mandatory
	DESCRIPTION
	     "  The index of the related VplTpTable entry. "
	--DEFAULT next-function-async     fsnVpcEntryNext
	--DEFAULT get-function-async      fsnVpcEntryGet
	::= { xldv11VpcTpEntry  9 }

     xldv11VpcIndex OBJECT-TYPE
	-- info-LEAF:    xldv11VpcIndex
	-- info-TREE:    xldv11CallP
	-- info-ACC:     ro
	-- info-SYNTAX:  INTEGER
	-- info-VALUE:   1..4196+92
	-- info-COMMENT: - 
	-- info-ROU:     GET db
	-- info-IMPL:    V1.1U->
	-- info-VERCTRL: - 
	SYNTAX        INTEGER (1..4188)
	ACCESS        read-only
	STATUS        mandatory
	DESCRIPTION
	     " A unique value to identify an entry in the VPC TP table. "
	--DEFAULT next-function-async     fsnVpcEntryNext
	--DEFAULT get-function-async      fsnVpcEntryGet
	::= { xldv11VpcTpEntry 10 }

     xldv11VpcAISAlarm OBJECT-TYPE
	-- info-LEAF:    xldv11VpcAISAlarm
	-- info-TREE:    xldv11Callp
	-- info-ACC:     ro
	-- info-SYNTAX:  Xldv11TpAlarmState
	-- info-VALUE:   noAlarm(1), upstreamAlarm(2),
	-- info-VALUE:   downstreamAlarm(3), upAndDownstreamAlarm(4)
	-- info-COMMENT: indicates an AIS alarm and its direction
	-- info-ROU:     GET db
	-- info-IMPL:    V1.3N->
	-- info-VERCTRL: -
	SYNTAX        Xldv11TpAlarmState
	ACCESS        read-only
	STATUS        mandatory
	DESCRIPTION
	     " Indicates an AIS alarm and its direction. 
	     Range of values :
	     noAlarm(1), upstreamAlarm(2),
	     downstreamAlarm(3), upAndDownstreamAlarm(4) ."
	--DEFAULT next-function-async     fsnVpcEntryNext
	--DEFAULT get-function-async      fsnVpcEntryGet
	::= { xldv11VpcTpEntry 11 }

     xldv11VpcRDIAlarm OBJECT-TYPE
	-- info-LEAF:    xldv11VpcRDIAlarm
	-- info-TREE:    xldv11Callp
	-- info-ACC:     ro
	-- info-SYNTAX:  Xldv11TpAlarmState
	-- info-VALUE:   noAlarm(1), upstreamAlarm(2),
	-- info-VALUE:   downstreamAlarm(3), upAndDownstreamAlarm(4)
	-- info-COMMENT: indicates an RDI alarm and its direction
	-- info-ROU:     GET db
	-- info-IMPL:    V1.3N->
	-- info-VERCTRL: -
	SYNTAX        Xldv11TpAlarmState
	ACCESS        read-only
	STATUS        mandatory
	DESCRIPTION
	     " Indicates an RDI alarm and its direction. 
	     Range of values :
	     noAlarm(1), upstreamAlarm(2),
	     downstreamAlarm(3), upAndDownstreamAlarm(4) ."
	--DEFAULT next-function-async     fsnVpcEntryNext
	--DEFAULT get-function-async      fsnVpcEntryGet
	::= { xldv11VpcTpEntry 12 }
     
     xldv11VpcLOCAlarm OBJECT-TYPE
	-- info-LEAF:    xldv11VpcLOCAlarm
	-- info-TREE:    xldv11Callp
	-- info-ACC:     ro
	-- info-SYNTAX:  Xldv11TpAlarmState
	-- info-VALUE:   noAlarm(1), upstreamAlarm(2),
	-- info-VALUE:   downstreamAlarm(3), upAndDownstreamAlarm(4)
	-- info-COMMENT: indicates an LOC alarm and its direction
	-- info-ROU:     GET db
	-- info-IMPL:    V1.3N->
	-- info-VERCTRL: -
	SYNTAX        Xldv11TpAlarmState
	ACCESS        read-only
	STATUS        mandatory
	DESCRIPTION
	     " Indicates an LOC alarm and its direction. 
	     Range of values :
	     noAlarm(1), upstreamAlarm(2),
	     downstreamAlarm(3), upAndDownstreamAlarm(4) ."
	--DEFAULT next-function-async     fsnVpcEntryNext
	--DEFAULT get-function-async      fsnVpcEntryGet
	::= { xldv11VpcTpEntry 13 }

     xldv11VpcEmSpecific OBJECT-TYPE
	-- info-LEAF:    xldv11VpcEmSpecific
	-- info-TREE:    xldv11CallP
	-- info-ACC:     rw
	-- info-SYNTAX:  Unsigned16
	-- info-VALUE:   Default 0
	-- info-COMMENT: Elmenet Manager 45020 specific attribute
	-- info-ROU:     GET db SET db
	-- info-IMPL:    V1.3N->
	-- info-VERCTRL: -
	SYNTAX        Unsigned16
	ACCESS        read-write
	STATUS        mandatory
	DESCRIPTION
	     " EM 45020 specific attribute. Default 0. "
	--DEFAULT test-function-async     fsnVpcEntryTest
	--DEFAULT next-function-async     fsnVpcEntryNext
	--DEFAULT set-function-async      fsnVpcEntrySet
	--DEFAULT get-function-async      fsnVpcEntryGet
	::= { xldv11VpcTpEntry 14 }

     -- --------------------------------------------------------------
     --                   VCC TP Table (XLDV1.1L)
     -- --------------------------------------------------------------

     xldv11VccTpTable OBJECT-TYPE
	-- info-NODE:    xldv11VccTpTable
	-- info-TREE:    xldv11CallP
	-- info-ACC:     nac
	-- info-SYNTAX:  SEQUENCE OF Xldv11VccTpEntry
	-- info-COMMENT: VccTp table
	-- info-IMPL:    V1.1U->
	-- info-VERCTRL: -
	SYNTAX        SEQUENCE OF Xldv11VccTpEntry
	ACCESS        not-accessible
	STATUS        mandatory
	DESCRIPTION
	     " This table contains the entries for the termination points
	       of the VC connections."
	::= { xldv11CallP 5 }

     xldv11VccTpEntry OBJECT-TYPE
	-- info-NODE:    xldv11VccTpEntry
	-- info-TREE:    xldv11CallP
	-- info-INDEX:   xldv11VccIndex
	-- info-ACC:     nac
	-- info-SYNTAX:  Xldv11VccTpEntry
	-- info-COMMENT: VccTp table entry
	-- info-IMPL:    V1.1U->
	-- info-VERCTRL: -
	SYNTAX        Xldv11VccTpEntry
	ACCESS        not-accessible
	STATUS        mandatory
	DESCRIPTION
	       "Each entry represents the point in the switch
	       where the VCC and its associated overhead (F4 OAM cells) are 
	       terminated or originated.
	       Instances of this managed entity may be created automatically
	       by the ATM NE or as a result of an Vcl cross connect request.
	       Similarly instances of this managed entity may be deleted
	       automatically by the ATM NE or as a result of an Vcl Cross
	       Connect delete request.
	       Notifications : 
		 xldv11TrStateChangeOper, 
		 xldv11TrObjCreate,
		 xldv11TrObjDelete.
		 xldv11TrVccTpRDI,
		 xldv11VccTpAIS alarms when fault is detected or cleared."
	INDEX         { xldv11VccIndex }
	::= { xldv11VccTpTable 1 }

     Xldv11VccTpEntry ::=
	SEQUENCE { xldv11VccOperationalState     Xldv11OperState,
		   xldv11VccVciValue             INTEGER,
		   xldv11VccVpcIndex             INTEGER,
		   xldv11VccHwUnitIndex          Unsigned16,
		   xldv11VccAlarmSeverityIndex   Xldv11AlmSevProfileIndex,
		   xldv11VccAlarmFilteringIndex  Xldv11AlmFiltProfileIndex,
		   xldv11VccLineIndex            Unsigned16,
		   xldv11VccLineIndexLi          Unsigned16,
		   xldv11VccIndex                INTEGER,
		   xldv11VccAISAlarm             Xldv11TpAlarmState,
		   xldv11VccRDIAlarm             Xldv11TpAlarmState
		   }

     xldv11VccOperationalState OBJECT-TYPE
	-- info-LEAF:    xldv11VccOperationalState
	-- info-TREE:    xldv11CallP
	-- info-ACC:     ro
	-- info-SYNTAX:  Xldv11OperState
	-- info-VALUE:   enabled, disabled
	-- info-COMMENT: -
	-- info-ROU:     GET db
	-- info-IMPL:    V1.1U->
	-- info-VERCTRL: -
	SYNTAX        Xldv11OperState
	ACCESS        read-only
	STATUS        mandatory
	DESCRIPTION
	     " This read-only attribute identifies whether or not the VPL
	       termination is capable of performing its normal functions
	       (in-service or out-of-service).
	       The range of values is enabled(1), disabled(2). "
	--DEFAULT next-function-async     fsnVccEntryNext
	--DEFAULT get-function-async      fsnVccEntryGet
	::= { xldv11VccTpEntry 1 }

     xldv11VccVciValue OBJECT-TYPE
	-- info-LEAF:    xldv11VccVciValue
	-- info-TREE:    xldv11CallP
	-- info-ACC:     ro
	-- info-SYNTAX:  INTEGER
	-- info-VALUE:   0..65535
	-- info-COMMENT: Identifies the VCI value of the VC link
	-- info-ROU:     GET db
	-- info-IMPL:    V1.1U:rw->V1.3B V1.3N->
	-- info-VERCTRL: -
	SYNTAX        INTEGER (1..65535)
	ACCESS        read-only
	STATUS        mandatory
	DESCRIPTION
	     " This attribute identifies the VCI value associated with the
	       VC link being terminated."
	--DEFAULT next-function-async     fsnVccEntryNext
	--DEFAULT get-function-async      fsnVccEntryGet
	::= { xldv11VccTpEntry 2 }

     xldv11VccVpcIndex OBJECT-TYPE
	-- info-LEAF:    xldv11VccVpcIndex
	-- info-TREE:    xldv11CallP
	-- info-ACC:     ro
	-- info-SYNTAX:  INTEGER
	-- info-VALUE:   1..4188
	-- info-COMMENT: Index of the related VpcTp
	-- info-ROU:     GET db
	-- info-IMPL:    V1.1U:rw->V1.3B V1.3N->
	-- info-VERCTRL: -
	SYNTAX        INTEGER (1..4188)
	ACCESS        read-only
	STATUS        mandatory
	DESCRIPTION
	     " This attribute serves as pointer to the related VPC
	     and describes the xldv11VpcIndex."
	--DEFAULT next-function-async     fsnVccEntryNext
	--DEFAULT get-function-async      fsnVccEntryGet
	::= { xldv11VccTpEntry 3 }

     xldv11VccHwUnitIndex OBJECT-TYPE
	-- info-LEAF:    xldv11VccHwUnitIndex
	-- info-TREE:    xldv11CallP
	-- info-ACC:     ro
	-- info-SYNTAX:  Unsigned16
	-- info-VALUE:   -
	-- info-COMMENT: HwUnitIndex of the dependent PIU (LI*)
	-- info-ROU:     GET db
	-- info-IMPL:    V1.1U:rw->V1.3B V1.3N->
	-- info-VERCTRL: -
	SYNTAX        Unsigned16
	ACCESS        read-only
	STATUS        mandatory
	DESCRIPTION
	     " The unique identifier for hardware units,
	       here the HWM sublayer (CMU or LI*). " 
	--DEFAULT next-function-async     fsnVccEntryNext
	--DEFAULT get-function-async      fsnVccEntryGet
	::= { xldv11VccTpEntry 4 }

     xldv11VccAlarmSeverityIndex OBJECT-TYPE
	-- info-LEAF:    xldv11VccAlarmSeverityIndex
	-- info-TREE:    xldv11CallP
	-- info-ACC:     rw
	-- info-SYNTAX:  Xldv11AlmSevProfileIndex
	-- info-VALUE:   1..40
	-- info-COMMENT: -
	-- info-ROU:     GET db SET db
	-- info-IMPL:    V1.1U:ro->V1.3H:ro V1.3A->
	-- info-VERCTRL: -
	SYNTAX        Xldv11AlmSevProfileIndex
	ACCESS        read-write
	STATUS        mandatory
	DESCRIPTION
	     " It is a pointer to the instance of the alarm severity
	       assignment profile managed entity that contains the severity
	       assignments for the alarms reported by this managed entity.
	       Default is 1. 
	       (Not implemented in XLD V1.0 and XLD V1.1U). "
	--DEFAULT test-function-async     fsnVccEntryTest
	--DEFAULT next-function-async     fsnVccEntryNext
	--DEFAULT set-function-async      fsnVccEntrySet
	--DEFAULT get-function-async      fsnVccEntryGet
	::= { xldv11VccTpEntry 5 }

     xldv11VccAlarmFilteringIndex OBJECT-TYPE
	-- info-LEAF:    xldv11VccAlarmFilteringIndex
	-- info-TREE:    xldv11CallP
	-- info-ACC:     ro
	-- info-SYNTAX:  Xldv11AlmFiltProfileIndex
	-- info-VALUE:   1..40
	-- info-COMMENT: -
	-- info-ROU:     GET db
	-- info-IMPL:    V1.x
	-- info-VERCTRL: -
	SYNTAX        Xldv11AlmFiltProfileIndex
	ACCESS        read-only
	STATUS        mandatory
	DESCRIPTION
	     " It is a pointer to the instance of the alarm filtering
	       assignment profile managed entity that contains the filtering
	       assignments for the alarms reported by this managed entity.
	       (Not implemented in XLD V1.0 and XLD V1.1U). "
	--DEFAULT next-function-async     fsnVccEntryNext
	--DEFAULT get-function-async      fsnVccEntryGet
	::= { xldv11VccTpEntry 6 }

     xldv11VccLineIndex OBJECT-TYPE
	-- info-LEAF:    xldv11VccLineIndex
	-- info-TREE:    xldv11CallP
	-- info-ACC:     ro
	-- info-SYNTAX:  Unsigned16
	-- info-VALUE:   -
	-- info-COMMENT: Identifies the line within ONU and NTAD*
	-- info-ROU:     GET db
	-- info-IMPL:    V1.1U:rw->V1.3B V1.3N->
	-- info-VERCTRL: -
	SYNTAX        Unsigned16
	ACCESS        read-only
	STATUS        mandatory
	DESCRIPTION
	     " This value identifies the belonging line in the ONU and NT*. "
	--DEFAULT next-function-async     fsnVccEntryNext
	--DEFAULT get-function-async      fsnVccEntryGet
	::= { xldv11VccTpEntry 7 }

     xldv11VccLineIndexLi OBJECT-TYPE
	-- info-LEAF:    xldv11VccLineIndexLi
	-- info-TREE:    xldv11CallP
	-- info-ACC:     ro
	-- info-SYNTAX:  Unsigned16
	-- info-VALUE:   -
	-- info-COMMENT: Identifies the line within the LI*
	-- info-ROU:     GET db
	-- info-IMPL:    V1.1U:rw->V1.3B V1.3N->
	-- info-VERCTRL: -
	SYNTAX        Unsigned16
	ACCESS        read-only
	STATUS        mandatory
	DESCRIPTION
	     " This value identifies the line index in the LI. "
	--DEFAULT next-function-async     fsnVccEntryNext
	--DEFAULT get-function-async      fsnVccEntryGet
	::= { xldv11VccTpEntry 8 }

     xldv11VccIndex OBJECT-TYPE
	-- info-LEAF:    xldv11VccIndex
	-- info-TREE:    xldv11CallP
	-- info-ACC:     ro
	-- info-SYNTAX:  INTEGER
	-- info-VALUE:   1..4096
	-- info-COMMENT: -
	-- info-ROU:     GET db SET db
	-- info-IMPL:    V1.1U->
	-- info-VERCTRL: -
	SYNTAX        INTEGER (1..4096)
	ACCESS        read-only
	STATUS        mandatory
	DESCRIPTION
	     " A unique value to identify an entry in the VCC TP table. "
	--DEFAULT next-function-async     fsnVccEntryNext
	--DEFAULT get-function-async      fsnVccEntryGet
	::= { xldv11VccTpEntry 9 }

     xldv11VccAISAlarm OBJECT-TYPE
	-- info-LEAF:    xldv11VccAISAlarm
	-- info-TREE:    xldv11Callp
	-- info-ACC:     ro
	-- info-SYNTAX:  Xldv11TpAlarmState
	-- info-VALUE:   noAlarm(1), upstreamAlarm(2),
	-- info-VALUE:   downstreamAlarm(3), upAndDownstreamAlarm(4)
	-- info-COMMENT: indicates an AIS alarm and its direction
	-- info-ROU:     GET db
	-- info-IMPL:    V1.3N->
	-- info-VERCTRL: -
	SYNTAX        Xldv11TpAlarmState
	ACCESS        read-only
	STATUS        mandatory
	DESCRIPTION
	     " Indicates an AIS alarm and its direction. 
	     Range of values :
	     noAlarm(1), upstreamAlarm(2),
	     downstreamAlarm(3), upAndDownstreamAlarm(4) ."
	--DEFAULT next-function-async     fsnVccEntryNext
	--DEFAULT get-function-async      fsnVccEntryGet
	::= { xldv11VccTpEntry 10 }

     xldv11VccRDIAlarm OBJECT-TYPE
	-- info-LEAF:    xldv11VccRDIAlarm
	-- info-TREE:    xldv11Callp
	-- info-ACC:     ro
	-- info-SYNTAX:  Xldv11TpAlarmState
	-- info-VALUE:   noAlarm(1), upstreamAlarm(2),
	-- info-VALUE:   downstreamAlarm(3), upAndDownstreamAlarm(4)
	-- info-COMMENT: indicates an RDI alarm and its direction
	-- info-ROU:     GET db
	-- info-IMPL:    V1.3N->
	-- info-VERCTRL: -
	SYNTAX        Xldv11TpAlarmState
	ACCESS        read-only
	STATUS        mandatory
	DESCRIPTION
	     " Indicates an RDI alarm and its direction. 
	     Range of values :
	     noAlarm(1), upstreamAlarm(2),
	     downstreamAlarm(3), upAndDownstreamAlarm(4) ."
	--DEFAULT next-function-async     fsnVccEntryNext
	--DEFAULT get-function-async      fsnVccEntryGet
	::= { xldv11VccTpEntry 11 }
     
     -- --------------------------------------------------------------
     --                       VCX Table
     -- --------------------------------------------------------------

     -- This table is valid from version XLDV1.2B.
     --

     xldv11VcCrossConnectTable OBJECT-TYPE
	-- info-NODE:    xldv11VcCrossConnectTable
	-- info-TREE:    xldv11CallP
	-- info-ACC:     nac
	-- info-SYNTAX:  SEQUENCE OF Xldv11VcCrossConnectEntry
	-- info-COMMENT: VC crossconect table
	-- info-IMPL:    V1.2B->
	-- info-VERCTRL: -
	SYNTAX        SEQUENCE OF Xldv11VcCrossConnectEntry
	ACCESS        not-accessible
	STATUS        mandatory
	DESCRIPTION
	     " The VC cross connect table for Virtual Channel
		point-to-point cross connections. 
	       This managed entity is used to represent
	       the VC-cross-connect relationship between two termination
	       points.
	       Instances of this managed entity shall be automatically
	       created and deleted by the management system based on
	       VCX Connect and VCX Disconnect actions performed on
	       an instance of the VC Cross Connect Control managed
	       entity. They are downloaded after an ONU reload."
	::= { xldv11CallP 6 }

     xldv11VcCrossConnectEntry OBJECT-TYPE
	-- info-NODE:    xldv11VcCrossConnectEntry
	-- info-TREE:    xldv11CallP
	-- info-INDEX:   xldv11VcxIndex
	-- info-ACC:     nac
	-- info-SYNTAX:  Xldv11VcCrossConnectEntry
	-- info-COMMENT: VccTp table entry
	-- info-IMPL:    V1.2B->
	-- info-VERCTRL: -
	SYNTAX        Xldv11VcCrossConnectEntry
	ACCESS        not-accessible
	STATUS        mandatory
	DESCRIPTION
	     " An entry in the VC cross connect table.
	       Notifications : xldv11TrStateChangeOper."
	INDEX         { xldv11VcxIndex }
	::= { xldv11VcCrossConnectTable 1 }

     Xldv11VcCrossConnectEntry ::=
	SEQUENCE { xldv11VcxOperationalState   Xldv11OperState,
		   xldv11VcxTerminationPointA  INTEGER,
		   xldv11VcxTerminationPointZ  INTEGER,
		   xldv11VcxLineIndex          Unsigned16,
		   xldv11VcxLineIndexLi        Unsigned16,
		   xldv11VcxEthVpcIndex        INTEGER,
		   xldv11VcxEthVccIndex        INTEGER,
		   xldv11VcxVpcNniIndex        Unsigned16,
		   xldv11VcxVpcUniIndex        Unsigned16,
		   xldv11VcxIndex              INTEGER,
		   xldv11VcxAlarmState         Xldv11CallpAlarmState }

     xldv11VcxOperationalState OBJECT-TYPE
	-- info-LEAF:    xldv11VcxOperationalState
	-- info-TREE:    xldv11CallP
	-- info-ACC:     ro
	-- info-SYNTAX:  Xldv11OperState
	-- info-VALUE:   enabled, disabled
	-- info-COMMENT: -
	-- info-ROU:     GET db
	-- info-IMPL:    V1.2B->
	-- info-VERCTRL: -
	SYNTAX        Xldv11OperState
	ACCESS        read-only
	STATUS        mandatory
	DESCRIPTION
	     " This attribute identifies whether or not this instance of
	       the VC Cross Connection managed entity is capable of
	       performing its normal function ( i.e. switching cells ).
	       Altering this attribute is without reporting this state
	       change via the trap 'xldv11TrStateChangeOper'.
	       Range of value: enabled, disabled . "
	--DEFAULT next-function-async     fsnVcxEntryNext
	--DEFAULT get-function-async      fsnVcxEntryGet
	::= { xldv11VcCrossConnectEntry 1 }

     xldv11VcxTerminationPointA OBJECT-TYPE
	-- info-LEAF:    xldv11VcxTerminationPointA
	-- info-TREE:    xldv11CallP
	-- info-ACC:     ro
	-- info-SYNTAX:  INTEGER (1..4096)
	-- info-VALUE:   1..4096
	-- info-COMMENT: -
	-- info-ROU:     GET db
	-- info-IMPL:    V1.2B:rw->V1.3B V1.3N->
	-- info-VERCTRL: -
	SYNTAX        INTEGER (1..4096)
	ACCESS        read-only
	STATUS        mandatory
	DESCRIPTION
	     " For a point-to-point cross connect this attribute identifies
	       the instance of the VCL termination point that represents
	       the VCL at the LE side. "
	--DEFAULT next-function-async     fsnVcxEntryNext
	--DEFAULT get-function-async      fsnVcxEntryGet
	::= { xldv11VcCrossConnectEntry 2 }

     xldv11VcxTerminationPointZ OBJECT-TYPE
	-- info-LEAF:    xldv11VcxTerminationPointZ
	-- info-TREE:    xldv11CallP
	-- info-ACC:     ro
	-- info-SYNTAX:  INTEGER (1..4096)
	-- info-VALUE:   1..4096
	-- info-COMMENT: -
	-- info-ROU:     GET db
	-- info-IMPL:    V1.2B:rw->V1.3B V1.3N->
	-- info-VERCTRL: -
	SYNTAX        INTEGER (1..4096)
	ACCESS        read-only
	STATUS        mandatory
	DESCRIPTION
	     " For a point-to-point cross connect this attribute identifies
	       the instance of the VCL termination point that represents
	       the VCL at the NT side. "
	--DEFAULT next-function-async     fsnVcxEntryNext
	--DEFAULT get-function-async      fsnVcxEntryGet
	::= { xldv11VcCrossConnectEntry 3 }

     xldv11VcxLineIndex OBJECT-TYPE
	-- info-LEAF:    xldv11VcxLineIndex
	-- info-TREE:    xldv11CallP
	-- info-ACC:     ro
	-- info-SYNTAX:  Unsigned16
	-- info-VALUE:   -
	-- info-COMMENT: -
	-- info-ROU:     GET db
	-- info-IMPL:    V1.2B:rw->V1.3B V1.3N->
	-- info-VERCTRL: -
	SYNTAX        Unsigned16
	ACCESS        read-only
	STATUS        mandatory
	DESCRIPTION
	     " This value identifies objects in the ONU and NT*
	       belonging to the same line. "
	--DEFAULT next-function-async     fsnVcxEntryNext
	--DEFAULT get-function-async      fsnVcxEntryGet
	::= { xldv11VcCrossConnectEntry 4 }

     xldv11VcxLineIndexLi OBJECT-TYPE
	-- info-LEAF:    xldv11VcxLineIndexLi
	-- info-TREE:    xldv11CallP
	-- info-ACC:     ro
	-- info-SYNTAX:  Unsigned16
	-- info-VALUE:   -
	-- info-COMMENT: -
	-- info-ROU:     GET db
	-- info-IMPL:    V1.2B:rw->V1.3B V1.3N->
	-- info-VERCTRL: -
	SYNTAX        Unsigned16
	ACCESS        read-only
	STATUS        mandatory
	DESCRIPTION
	     " This value identifies the line index of the VciUni
	       within the LI"
	--DEFAULT next-function-async     fsnVcxEntryNext
	--DEFAULT get-function-async      fsnVcxEntryGet
	::= { xldv11VcCrossConnectEntry 5 }

     xldv11VcxEthVpcIndex OBJECT-TYPE
	-- info-LEAF:    xldv11VcxEthVpcIndex
	-- info-TREE:    xldv11CallP
	-- info-ACC:     ro
	-- info-SYNTAX:  INTEGER
	-- info-VALUE:   0..4188
	-- info-COMMENT: -
	-- info-ROU:     GET db
	-- info-IMPL:    V1.2B:rw->V1.3B V1.3N->
	-- info-VERCTRL: -
	SYNTAX        INTEGER (0..4188)
	ACCESS        read-only
	STATUS        mandatory
	DESCRIPTION
	     "  used to address the corresponding entry 
		in the VpcTpTable. Default is 0. "
	--DEFAULT next-function-async     fsnVcxEntryNext
	--DEFAULT get-function-async      fsnVcxEntryGet
	::= { xldv11VcCrossConnectEntry 6 }

     xldv11VcxEthVccIndex OBJECT-TYPE
	-- info-LEAF:    xldv11VcxEthVccIndex
	-- info-TREE:    xldv11CallP
	-- info-ACC:     ro
	-- info-SYNTAX:  INTEGER
	-- info-VALUE:   0..4096
	-- info-COMMENT: -
	-- info-ROU:     GET db
	-- info-IMPL:    V1.2B:rw->V1.3B V1.3N->
	-- info-VERCTRL: -
	SYNTAX        INTEGER (0..4096)
	ACCESS        read-only
	STATUS        mandatory
	DESCRIPTION
	     "  used to address the corresponding entry 
		in the VccTP Table. Default is 0. "
	--DEFAULT next-function-async     fsnVcxEntryNext
	--DEFAULT get-function-async      fsnVcxEntryGet
	::= { xldv11VcCrossConnectEntry 7 }

     xldv11VcxVpcNniIndex OBJECT-TYPE
	-- info-LEAF:    xldv11VcxVpcNniIndex
	-- info-TREE:    xldv11CallP
	-- info-ACC:     ro
	-- info-SYNTAX:  Unsigned16
	-- info-VALUE:   -
	-- info-COMMENT: -
	-- info-ROU:     GET db
	-- info-IMPL:    V1.2B:rw->V1.3B V1.3N->
	-- info-VERCTRL: -
	SYNTAX        Unsigned16
	ACCESS        read-only
	STATUS        mandatory
	DESCRIPTION
	     "  used to address the corresponding entry 
		in the VpcTpTable. Default is 0. "
	--DEFAULT next-function-async     fsnVcxEntryNext
	--DEFAULT get-function-async      fsnVcxEntryGet
	::= { xldv11VcCrossConnectEntry 8 }

     xldv11VcxVpcUniIndex OBJECT-TYPE
	-- info-LEAF:    xldv11VcxVpcUniIndex
	-- info-TREE:    xldv11CallP
	-- info-ACC:     ro
	-- info-SYNTAX:  Unsigned16
	-- info-VALUE:   -
	-- info-COMMENT: -
	-- info-ROU:     GET db
	-- info-IMPL:    V1.2B:rw->V1.3B V1.3N->
	-- info-VERCTRL: -
	SYNTAX        Unsigned16
	ACCESS        read-only
	STATUS        mandatory
	DESCRIPTION
	     "  used to address the corresponding entry 
		in the VccTP Table. Default is 0. "
	--DEFAULT next-function-async     fsnVcxEntryNext
	--DEFAULT get-function-async      fsnVcxEntryGet
	::= { xldv11VcCrossConnectEntry 9 }

     xldv11VcxIndex   OBJECT-TYPE
	-- info-LEAF:    xldv11VcxIndex
	-- info-TREE:    xldv11CallP
	-- info-ACC:     ro
	-- info-SYNTAX:  INTEGER
	-- info-VALUE:   1..2048
	-- info-COMMENT: -
	-- info-ROU:     GET db
	-- info-IMPL:    V1.2B->
	-- info-VERCTRL: -
	SYNTAX        INTEGER (1..2048)
	ACCESS        read-only
	STATUS        mandatory
	DESCRIPTION
	     "  unique number to identify an entry in the 
		VcCrossConnect Table"
	--DEFAULT next-function-async     fsnVcxEntryNext
	--DEFAULT get-function-async      fsnVcxEntryGet
	::= { xldv11VcCrossConnectEntry 10 }

     xldv11VcxAlarmState OBJECT-TYPE
	-- info-LEAF:    xldv11VcxAlarmState
	-- info-TREE:    xldv11CallP
	-- info-ACC:     ro
	-- info-SYNTAX:  Xldv11CallpAlarmState
	-- info-VALUE:   noAlarm(1), alarmPresent(2)
	-- info-COMMENT: indicates whether for the cross connect
	-- info-COMMENT: an alarm is present or not
	-- info-ROU:     GET db
	-- info-IMPL:    V1.3N->
	-- info-VERCTRL: -
	SYNTAX        Xldv11CallpAlarmState
	ACCESS        read-only
	STATUS        mandatory
	DESCRIPTION
	     " This attribute indicates whether for the cross connect
	       an alarm is present or not. "
	--DEFAULT next-function-async     fsnVcxEntryNext
	--DEFAULT get-function-async      fsnVcxEntryGet
	::= { xldv11VcCrossConnectEntry 11 }

     -- --------------------------------------------------------------
     --                        VCL TP Table
     -- --------------------------------------------------------------

     -- This table is valid from version XLDV1.2b
     --

     xldv11VclTpTable OBJECT-TYPE
	-- info-NODE:    xldv11VclTpTable
	-- info-TREE:    xldv11CallP
	-- info-ACC:     nac
	-- info-SYNTAX:  SEQUENCE OF Xldv11VclTpEntry
	-- info-COMMENT: VclTp table
	-- info-IMPL:    V1.2B->
	-- info-VERCTRL: -
	SYNTAX        SEQUENCE OF Xldv11VclTpEntry
	ACCESS        not-accessible
	STATUS        mandatory
	DESCRIPTION
	     " This table contains the entries for the VC links."
	::= { xldv11CallP 7 }

     xldv11VclTpEntry OBJECT-TYPE
	-- info-NODE:    xldv11VclTpEntry
	-- info-TREE:    xldv11CallP
	-- info-INDEX:   xldv11VclIndex
	-- info-ACC:     nac
	-- info-SYNTAX:  Xldv11VclTpEntry
	-- info-VALUE:   -
	-- info-COMMENT: VclTp entry
	-- info-ROU:     -
	-- info-IMPL:    V1.2B->
	-- info-VERCTRL: -
	SYNTAX        Xldv11VclTpEntry
	ACCESS        not-accessible
	STATUS        mandatory
	DESCRIPTION
	     " The entries represent the termination of VCLs on an ATM NE.
	       An instance of the VC Cross Connection managed entity may be
	       used to relate two instances of the VCL Termination Point
	       managed entity (i.e. for point-to-point cross connection).
	       Instances of this managed entity may be created automatically
	       by the ATM NE or as a result of an VC cross connect request.
	       Similarly instances of this managed entity may be deleted
	       automatically by the ATM NE or as a result of an VC  Cross
	       Connect release request.
	       Notifications: xldv11TrStateChangeOper."
	INDEX         { xldv11VclIndex }
	::= { xldv11VclTpTable 1 }

     Xldv11VclTpEntry ::=
	SEQUENCE { xldv11VclOperationalState          Xldv11OperState,
		   xldv11VclVpiValue                  INTEGER,
		   xldv11VclVciValue                  INTEGER,
		   xldv11VclHwUnitIndex               Unsigned16,
		   xldv11VclIfIndex                   Unsigned16,
		   xldv11VclPeakCellRateUpstream      Unsigned32,
		   xldv11VclPeakCellRateDownstream    Unsigned32,
		   xldv11VclCellDelayVariationToleranceUpstream    INTEGER,
		   xldv11VclCellDelayVariationToleranceDownstream  INTEGER,
		   xldv11VclTrafficType               Xldv11TrafficType,
		   xldv11VclTrafficDirection          Xldv11TrafficDirection,
		   xldv11VclTrafficPriority           Xldv11TrafficPriority,
		   xldv11VclConnectivityPointer       Unsigned16,
		   xldv11VclLineIndex                 Unsigned16,
		   xldv11VclLineIndexLi               Unsigned16,
		   xldv11VclSegmentEndPoint           INTEGER,
		   xldv11VclSustainableCellRateUpstream   Unsigned32,
		   xldv11VclSustainableCellRateDownstream Unsigned32,
		   xldv11VclMaximumBurstSizeUpstream      INTEGER,
		   xldv11VclMaximumBurstSizeDownstream    INTEGER,
		   xldv11VclAlarmSeverityIndex            Xldv11AlmSevProfileIndex,
		   xldv11VclAlarmFilteringIndex           Xldv11AlmFiltProfileIndex,
		   xldv11VclCvcIndexSource                Unsigned16, -- continuity check
		   xldv11VclCvcIndexSink                  Unsigned16, -- continuity check
		   xldv11VclIndex                         INTEGER,
		   xldv11VclLOCAlarm                  Xldv11TpAlarmState
		   }

     xldv11VclOperationalState OBJECT-TYPE
	-- info-LEAF:    xldv11VclOperationalState
	-- info-TREE:    xldv11CallP
	-- info-ACC:     ro
	-- info-SYNTAX:  Xldv11OperState
	-- info-VALUE:   enabled, disabled
	-- info-COMMENT: -
	-- info-ROU:     GET db
	-- info-IMPL:    V1.2B->
	-- info-VERCTRL: -
	SYNTAX        Xldv11OperState
	ACCESS        read-only
	STATUS        mandatory
	DESCRIPTION
	     " This read-only attribute identifies whether or not the VCL
	       termination is capable of performing its normal functions
	       (in-service or out-of-service).
	       The range of values is enabled, disabled . "
	--DEFAULT next-function-async     fsnVclEntryNext
	--DEFAULT get-function-async      fsnVclEntryGet
	::= { xldv11VclTpEntry 1 }

     xldv11VclVpiValue OBJECT-TYPE
	-- info-LEAF:    xldv11VclVpiValue
	-- info-TREE:    xldv11CallP
	-- info-ACC:     ro
	-- info-SYNTAX:  INTEGER
	-- info-VALUE:   0..4095
	-- info-COMMENT: -
	-- info-ROU:     GET db
	-- info-IMPL:    V1.2B:rw->V1.3B V1.3N->
	-- info-VERCTRL: -
	SYNTAX        INTEGER (0..4095)
	ACCESS        read-only
	STATUS        mandatory
	DESCRIPTION
	     " This attribute identifies the VCI value associated with the
	       VP link being terminated. "
	--DEFAULT next-function-async     fsnVclEntryNext
	--DEFAULT get-function-async      fsnVclEntryGet
	::= { xldv11VclTpEntry 2 }

     xldv11VclVciValue OBJECT-TYPE
	-- info-LEAF:    xldv11VclVciValue
	-- info-TREE:    xldv11CallP
	-- info-ACC:     ro
	-- info-SYNTAX:  INTEGER
	-- info-VALUE:   0..65535
	-- info-COMMENT: -
	-- info-ROU:     GET db
	-- info-IMPL:    V1.2B:rw->V1.3B V1.3N->
	-- info-VERCTRL: -
	SYNTAX        INTEGER (0..65535)
	ACCESS        read-only
	STATUS        mandatory
	DESCRIPTION
	     " This attribute identifies the VCI value associated with the
	       VC link being terminated. "
	--DEFAULT next-function-async     fsnVclEntryNext
	--DEFAULT get-function-async      fsnVclEntryGet
	::= { xldv11VclTpEntry 3 }

     xldv11VclHwUnitIndex OBJECT-TYPE
	-- info-LEAF:    xldv11VclHwUnitIndex
	-- info-TREE:    xldv11CallP
	-- info-ACC:     ro
	-- info-SYNTAX:  Unsigned16
	-- info-VALUE:   -
	-- info-COMMENT: HwUnitIndex of the dependent PIU (CMU or LI*)
	-- info-ROU:     GET db
	-- info-IMPL:    V1.2B:rw->V1.3B V1.3N->
	-- info-VERCTRL: -
	SYNTAX        Unsigned16 
	ACCESS        read-only
	STATUS        mandatory
	DESCRIPTION
	     " The unique identifier for hardware units,
	       here the HWM sublayer (CMU or LI*). " 
	--DEFAULT next-function-async     fsnVclEntryNext
	--DEFAULT get-function-async      fsnVclEntryGet
	::= { xldv11VclTpEntry 4 }

     xldv11VclIfIndex OBJECT-TYPE
	-- info-LEAF:    xldv11VclIfIndex
	-- info-TREE:    xldv11CallP
	-- info-ACC:     ro
	-- info-SYNTAX:  Unsigned16
	-- info-VALUE:   -
	-- info-COMMENT: IfIndex of the connected PPTP at LI*
	-- info-ROU:     GET db
	-- info-IMPL:    V1.2B:rw->V1.3B V1.3N->
	-- info-VERCTRL: -
	SYNTAX        Unsigned16 
	ACCESS        read-only
	STATUS        mandatory
	DESCRIPTION
	     " The CALLP interface index of the connected PPTP 
	     in the LI. "
	--DEFAULT next-function-async     fsnVclEntryNext
	--DEFAULT get-function-async      fsnVclEntryGet
	::= { xldv11VclTpEntry 5 }

     xldv11VclPeakCellRateUpstream OBJECT-TYPE
	-- info-LEAF:    xldv11VclPeakCellRateUpstream
	-- info-TREE:    xldv11CallP
	-- info-ACC:     ro
	-- info-SYNTAX:  Unsigned32
	-- info-VALUE:   0..2 Giga 
	-- info-VALUE:   default: 800 000
	-- info-COMMENT: Identifies the upstream peak cell rate of the
	-- info-COMMENT: VC cross connect. 
	-- info-ROU:     GET db
	-- info-IMPL:    V1.2B:rw->V1.3B V1.3N->
	-- info-VERCTRL: -
	SYNTAX        Unsigned32
	ACCESS        read-only
	STATUS        mandatory
	DESCRIPTION
	     "  This attribute identifies the upstream peak cell rate 
		in bit/sec of the VC cross connect.
		Default value: 800 000 "
	--DEFAULT next-function-async     fsnVclEntryNext
	--DEFAULT get-function-async      fsnVclEntryGet
	::= { xldv11VclTpEntry 6 }

     xldv11VclPeakCellRateDownstream OBJECT-TYPE
	-- info-LEAF:    xldv11VclPeakCellRateDownstream
	-- info-TREE:    xldv11CallP
	-- info-ACC:     ro
	-- info-SYNTAX:  Unsigned32
	-- info-VALUE:   0..2 Giga (default: 2 000 000)
	-- info-COMMENT: Identifies the downstream peak cell rate of the
	-- info-COMMENT: VC cross connect. 
	-- info-ROU:     GET db
	-- info-IMPL:    V1.2B:rw->V1.3B V1.3N->
	-- info-VERCTRL: -
	SYNTAX        Unsigned32
	ACCESS        read-only
	STATUS        mandatory
	DESCRIPTION
	     "  This attribute identifies the downstream peak cell rate 
		in bit/sec of the VC cross connect.
		Default value: 2 000 000 "
	--DEFAULT next-function-async     fsnVclEntryNext
	--DEFAULT get-function-async      fsnVclEntryGet
	::= { xldv11VclTpEntry 7 }

     xldv11VclCellDelayVariationToleranceUpstream OBJECT-TYPE
	-- info-LEAF:    xldv11VclCellDelayVariationToleranceUpstream
	-- info-TREE:    xldv11CallP
	-- info-ACC:     ro
	-- info-SYNTAX:  INTEGER
	-- info-VALUE:   200..360,000,000 (default: 360,000,000)
	-- info-COMMENT: -
	-- info-ROU:     GET db
	-- info-IMPL:    V1.2B:rw->V1.3B V1.3N->
	-- info-VERCTRL: -
	SYNTAX        INTEGER(200..360000000)
	ACCESS        read-only
	STATUS        mandatory
	DESCRIPTION
	     "  This attribute identifies the upstream cell delay
	     variation (in nsec) of the VC cross connect. "
	--DEFAULT next-function-async     fsnVclEntryNext
	--DEFAULT get-function-async      fsnVclEntryGet
	::= { xldv11VclTpEntry 8 }

     xldv11VclCellDelayVariationToleranceDownstream OBJECT-TYPE
	-- info-LEAF:    xldv11VclCellDelayVariationToleranceDownstream
	-- info-TREE:    xldv11CallP
	-- info-ACC:     ro
	-- info-SYNTAX:  INTEGER
	-- info-VALUE:   200..360,000,000 (default: 200)
	-- info-COMMENT: -
	-- info-ROU:     GET db
	-- info-IMPL:    V1.2B:rw->V1.3B V1.3N->
	-- info-VERCTRL: -
	SYNTAX        INTEGER(200..360000000)
	ACCESS        read-only
	STATUS        mandatory
	DESCRIPTION
	     "  This attribute identifies the downstream cell delay
	     variation (in nsec) of the VC cross connect. "
	--DEFAULT next-function-async     fsnVclEntryNext
	--DEFAULT get-function-async      fsnVclEntryGet
	::= { xldv11VclTpEntry 9 }

     xldv11VclTrafficType OBJECT-TYPE
	-- info-LEAF:    xldv11VclTrafficType
	-- info-TREE:    xldv11CallP
	-- info-ACC:     ro
	-- info-SYNTAX:  Xldv11TrafficType
	-- info-VALUE:   cbr(V1.2B->), ubr(V1.2B->)
	-- info-VALUE:   nrtVbr(V1.3A->), rtVbr(V1.3A->)
	-- info-COMMENT: -
	-- info-ROU:     GET db
	-- info-IMPL:    V1.2B:rw->V1.3B V1.3N->
	-- info-VERCTRL: -
	SYNTAX        Xldv11TrafficType
	ACCESS        read-only
	STATUS        mandatory
	DESCRIPTION
	     " This attribute identifies the traffic type of the
	       VC cross connect. 
	       Range of value: 
		     constant bit rate    cbr
		     unspecified bit rate ubr
	       For V1.3:
		     non real time variable traffic nrtVbr,
		     real time variable traffic  rtVbr.
	       Default value: constant bit rate (cbr) . "
	--DEFAULT next-function-async     fsnVclEntryNext
	--DEFAULT get-function-async      fsnVclEntryGet
	::= { xldv11VclTpEntry 10 }

     xldv11VclTrafficDirection OBJECT-TYPE
	-- info-LEAF:    xldv11VclTrafficDirection
	-- info-TREE:    xldv11CallP
	-- info-ACC:     ro
	-- info-SYNTAX:  Xldv11TrafficDirection
	-- info-VALUE:   bidirectional, upstream, downstream
	-- info-COMMENT: -
	-- info-ROU:     GET db
	-- info-IMPL:    V1.2B:rw->V1.3B V1.3N->
	-- info-VERCTRL: -
	SYNTAX        Xldv11TrafficDirection
	ACCESS        read-only
	STATUS        mandatory
	DESCRIPTION
	     " This attribute identifies the traffic Direction
	       Range of value: bidirectional, upstream, downstream.
	       Default value: bidirectional. "
	--DEFAULT next-function-async     fsnVclEntryNext
	--DEFAULT get-function-async      fsnVclEntryGet
	::= { xldv11VclTpEntry 11 }

     xldv11VclTrafficPriority OBJECT-TYPE
	-- info-LEAF:    xldv11VclTrafficPriority
	-- info-TREE:    xldv11CallP
	-- info-ACC:     ro
	-- info-SYNTAX:  Xldv11TrafficPriority
	-- info-VALUE:   low, high(default: high)
	-- info-COMMENT: Identifies the traffic priority.
	-- info-ROU:     GET db
	-- info-IMPL:    V1.3A->
	-- info-VERCTRL: -
	SYNTAX        Xldv11TrafficPriority
	ACCESS        read-only
	STATUS        mandatory
	DESCRIPTION
	     " This attribute identifies the traffic Priority
	       Range of value: low, high.
	       Default value: high. "
	--DEFAULT next-function-async     fsnVclEntryNext
	--DEFAULT get-function-async      fsnVclEntryGet
	::= { xldv11VclTpEntry 12 }

     xldv11VclConnectivityPointer OBJECT-TYPE
	-- info-LEAF:    xldv11VclConnectivityPointer
	-- info-TREE:    xldv11CallP
	-- info-ACC:     ro
	-- info-SYNTAX:  Unsigned16
	-- info-VALUE:   -
	-- info-COMMENT: pointer to connected VclTp*
	-- info-ROU:     GET db
	-- info-IMPL:    V1.2B:rw->V1.3B V1.3N->
	-- info-VERCTRL: -
	SYNTAX        Unsigned16
	ACCESS        read-only
	STATUS        mandatory
	DESCRIPTION
	     " This attribute serves as a pointer to the instance of the
	       VCL termination point managed entity instance (in the ATM
	       NE) it is cross connected to. "
	--DEFAULT next-function-async     fsnVclEntryNext
	--DEFAULT get-function-async      fsnVclEntryGet
	::= { xldv11VclTpEntry 13 }

     xldv11VclLineIndex OBJECT-TYPE
	-- info-LEAF:    xldv11VclLineIndex
	-- info-TREE:    xldv11CallP
	-- info-ACC:     ro
	-- info-SYNTAX:  Unsigned16
	-- info-VALUE:   -
	-- info-COMMENT: -
	-- info-ROU:     GET db
	-- info-IMPL:    V1.2B:rw->V1.3B V1.3N->
	-- info-VERCTRL: -
	SYNTAX        Unsigned16
	ACCESS        read-only
	STATUS        mandatory
	DESCRIPTION
	     " This value identifies the belonging line. "
	--DEFAULT next-function-async     fsnVclEntryNext
	--DEFAULT get-function-async      fsnVclEntryGet
	::= { xldv11VclTpEntry 14 }

     xldv11VclLineIndexLi OBJECT-TYPE
	-- info-LEAF:    xldv11VclLineIndexLi
	-- info-TREE:    xldv11CallP
	-- info-ACC:     ro
	-- info-SYNTAX:  Unsigned16
	-- info-VALUE:   -
	-- info-COMMENT: -
	-- info-ROU:     GET db
	-- info-IMPL:    V1.2B:rw->V1.3B V1.3N->
	-- info-VERCTRL: -
	SYNTAX        Unsigned16
	ACCESS        read-only
	STATUS        mandatory
	DESCRIPTION
	     " This value identifies the Line Index in the LI. "
	--DEFAULT next-function-async     fsnVclEntryNext
	--DEFAULT get-function-async      fsnVclEntryGet
	::= { xldv11VclTpEntry 15 }

     xldv11VclSegmentEndPoint    OBJECT-TYPE
	-- info-LEAF:    xldv11VclSegmentEndPoint
	-- info-TREE:    xldv11CallP
	-- info-ACC:     ro
	-- info-SYNTAX:  INTEGER
	-- info-VALUE:   1..2 
	-- info-COMMENT: segmentEnd point yes(1), connecting point no(2)
	-- info-ROU:     GET db
	-- info-IMPL:    V1.2B:rw->V1.3B V1.3N->
	-- info-VERCTRL: -
	SYNTAX        INTEGER { yes(1), 
				no (2)    }
	ACCESS        read-only
	STATUS        mandatory
	DESCRIPTION
	     "  This value specifies whether the VclTp is 
		a segment endpoint (yes) or a connecting point (no). "
	--DEFAULT next-function-async     fsnVclEntryNext
	--DEFAULT get-function-async      fsnVclEntryGet
	::= { xldv11VclTpEntry 16 }

     xldv11VclSustainableCellRateUpstream OBJECT-TYPE
	-- info-LEAF:    xldv11VclSustainableCellRateUpstream
	-- info-TREE:    xldv11CallP
	-- info-ACC:     ro
	-- info-SYNTAX:  Unsigned32
	-- info-VALUE:   0..2 Giga (default: 800 000)
	-- info-COMMENT: Sustainable cell upstream rate in cells/sec
	-- info-COMMENT: for nrtVbr traffic.
	-- info-ROU:     GET db
	-- info-IMPL:    V1.3A->
	-- info-VERCTRL: -
	SYNTAX        Unsigned32
	ACCESS        read-only
	STATUS        mandatory
	DESCRIPTION
	     "  The sustainable upstream cell rate in cells/sec 
		for nrtVbr traffic.
		Default Value:  800 000"
	--DEFAULT next-function-async     fsnVclEntryNext
	--DEFAULT get-function-async      fsnVclEntryGet
	::= { xldv11VclTpEntry  17 }

     xldv11VclSustainableCellRateDownstream OBJECT-TYPE
	-- info-LEAF:    xldv11VclSustainableCellRateDownstream
	-- info-TREE:    xldv11CallP
	-- info-ACC:     ro
	-- info-SYNTAX:  Unsigned32
	-- info-VALUE:   0..2 Giga (default: 8 Mega)
	-- info-COMMENT: Sustainable downstream cell rate in cells/sec
	-- info-COMMENT: for nrtVbr traffic.
	-- info-ROU:     GET db
	-- info-IMPL:    V1.3A->
	-- info-VERCTRL: -
	SYNTAX        Unsigned32
	ACCESS        read-only
	STATUS        mandatory
	DESCRIPTION
	     "  The sustainable downstream cell rate in cells/sec 
		for nrtVbr traffic.
		Default Value:  8 Mega"
	--DEFAULT next-function-async     fsnVclEntryNext
	--DEFAULT get-function-async      fsnVclEntryGet
	::= { xldv11VclTpEntry  18 }

     xldv11VclMaximumBurstSizeUpstream  OBJECT-TYPE
	-- info-LEAF:    xldv11VclMaximumBurstSizeUpstream 
	-- info-TREE:    xldv11CallP
	-- info-ACC:     ro
	-- info-SYNTAX:  Integer32
	-- info-VALUE:   1..1500 (default: 32)
	-- info-COMMENT: -
	-- info-ROU:     GET db
	-- info-IMPL:    V1.3A->
	-- info-VERCTRL: -
	SYNTAX        INTEGER(1..1500)
	ACCESS        read-only
	STATUS        mandatory
	DESCRIPTION
	     "  The maximum upstream burst size tolerance in cells/sec
		for nrtVbr traffic.
		Default Value: 32."
	--DEFAULT next-function-async     fsnVclEntryNext
	--DEFAULT get-function-async      fsnVclEntryGet
	::= { xldv11VclTpEntry  19 }

     xldv11VclMaximumBurstSizeDownstream  OBJECT-TYPE
	-- info-LEAF:    xldv11VclMaximumBurstSizeDownstream 
	-- info-TREE:    xldv11CallP
	-- info-ACC:     ro
	-- info-SYNTAX:  Integer32
	-- info-VALUE:   1..18 800 (default: 32)
	-- info-COMMENT: -
	-- info-ROU:     GET db
	-- info-IMPL:    V1.3A->
	-- info-VERCTRL: -
	SYNTAX        INTEGER(1..18800)
	ACCESS        read-only
	STATUS        mandatory
	DESCRIPTION
	     "  The maximum downstream burst size tolerance in cells/sec
		for nrtVbr traffic.
		Default Value:  32."
	--DEFAULT next-function-async     fsnVclEntryNext
	--DEFAULT get-function-async      fsnVclEntryGet
	::= { xldv11VclTpEntry  20 }

     xldv11VclAlarmSeverityIndex OBJECT-TYPE
	-- info-LEAF:    xldv11VclAlarmSeverityIndex
	-- info-TREE:    xldv11CallP
	-- info-ACC:     rw
	-- info-SYNTAX:  Xldv11AlmSevProfileIndex
	-- info-VALUE:   1..40
	-- info-COMMENT: - 
	-- info-ROU:     GET db SET db
	-- info-IMPL:    V1.3A->
	-- info-VERCTRL: V1.1U->V1.2B: GET db SET blocked
	SYNTAX        Xldv11AlmSevProfileIndex
	ACCESS        read-write
	STATUS        mandatory
	DESCRIPTION
	     " It is a pointer to the instance of the alarm severity
	       assignment profile managed entity that contains the severity
	       assignments for the alarms reported by this managed entity.
	       (Not implemented in XLD V1.0 and XLD V1.1U).  Default is 1. "
	--DEFAULT test-function-async     fsnVclEntryTest
	--DEFAULT next-function-async     fsnVclEntryNext
	--DEFAULT set-function-async      fsnVclEntrySet
	--DEFAULT get-function-async      fsnVclEntryGet
	::= { xldv11VclTpEntry 21 }

     xldv11VclAlarmFilteringIndex OBJECT-TYPE
	-- info-LEAF:    xldv11VclAlarmFilteringIndex
	-- info-TREE:    xldv11CallP
	-- info-ACC:     ro
	-- info-SYNTAX:  Xldv11AlmFiltProfileIndex
	-- info-VALUE:   1..40
	-- info-COMMENT: - 
	-- info-ROU:     GET db
	-- info-IMPL:    V1.x
	-- info-VERCTRL: -
	SYNTAX        Xldv11AlmFiltProfileIndex
	ACCESS        not-accessible
	STATUS        mandatory
	DESCRIPTION
	     " It is a pointer to the instance of the alarm filtering
	       assignment profile managed entity that contains the filtering
	       assignments for the alarms reported by this managed entity.
	       (Not implemented) "
	--DEFAULT next-function-async     fsnVclEntryNext
	--DEFAULT get-function-async      fsnVclEntryGet
	::= { xldv11VclTpEntry 22 }

	xldv11VclCvcIndexSource OBJECT-TYPE
	-- info-LEAF:    xldv11VclCvcIndexSource
	-- info-TREE:    xldv11Callp
	-- info-ACC:     ro
	-- info-SYNTAX:  Unsigned16
	-- info-VALUE:   0..65535
	-- info-COMMENT: Index of the source for continuity check.
	-- info-COMMENT: related ContinuityCheckVclTpTable entry.
	-- info-ROU:     GET db
	-- info-IMPL:    V1.3B->
	-- info-VERCTRL: V1.1U->V1.3A: GET db SET blocked
	SYNTAX        Unsigned16
	ACCESS        read-only
	STATUS        mandatory
	DESCRIPTION
	     "  The index of continuity check source in the 
	     xldv11ContinuityCheckVclTpTable. "
	--DEFAULT next-function-async     fsnVclEntryNext
	--DEFAULT get-function-async      fsnVclEntryGet
	::= { xldv11VclTpEntry  23 }

	xldv11VclCvcIndexSink OBJECT-TYPE
	-- info-LEAF:    xldv11VclCvcIndexSink
	-- info-TREE:    xldv11Callp
	-- info-ACC:     ro
	-- info-SYNTAX:  Unsigned16
	-- info-VALUE:   0..65535
	-- info-COMMENT: Index of the sink for continuity check.
	-- info-COMMENT: related ContinuityCheckVclTpTable entry.
	-- info-ROU:     GET db
	-- info-IMPL:    V1.3B->
	-- info-VERCTRL: V1.1U->V1.3A: GET db SET blocked
	SYNTAX        Unsigned16
	ACCESS        read-only
	STATUS        mandatory
	DESCRIPTION
	     "  The index of continuity check sink in the 
	     xldv11ContinuityCheckVclTpTable. "
	--DEFAULT next-function-async     fsnVclEntryNext
	--DEFAULT get-function-async      fsnVclEntryGet
	::= { xldv11VclTpEntry  24 }

     xldv11VclIndex OBJECT-TYPE
	-- info-LEAF:    xldv11VclIndex
	-- info-TREE:    xldv11CallP
	-- info-ACC:     ro
	-- info-SYNTAX:  INTEGER
	-- info-VALUE:   1..4096
	-- info-COMMENT: -
	-- info-ROU:     GET db
	-- info-IMPL:    V1.2B->
	-- info-VERCTRL: -
	SYNTAX        INTEGER (1..4096)
	ACCESS        read-only
	STATUS        mandatory
	DESCRIPTION
	     " A unique value to identify an entry in the VCL table. "
	--DEFAULT next-function-async     fsnVclEntryNext
	--DEFAULT get-function-async      fsnVclEntryGet
	::= { xldv11VclTpEntry 25 }

     xldv11VclLOCAlarm OBJECT-TYPE
	-- info-LEAF:    xldv11VclLOCAlarm
	-- info-TREE:    xldv11Callp
	-- info-ACC:     ro
	-- info-SYNTAX:  Xldv11TpAlarmState
	-- info-VALUE:   noAlarm(1), upstreamAlarm(2),
	-- info-VALUE:   downstreamAlarm(3), upAndDownstreamAlarm(4)
	-- info-COMMENT: indicates an LOC alarm and its direction
	-- info-ROU:     GET db
	-- info-IMPL:    V1.3N->
	-- info-VERCTRL: -
	SYNTAX        Xldv11TpAlarmState
	ACCESS        read-only
	STATUS        mandatory
	DESCRIPTION
	     " Indicates an LOC alarm and its direction. 
	     Range of values :
	     noAlarm(1), upstreamAlarm(2),
	     downstreamAlarm(3), upAndDownstreamAlarm(4) ."
	--DEFAULT next-function-async     fsnVclEntryNext
	--DEFAULT get-function-async      fsnVclEntryGet
	::= { xldv11VclTpEntry 26 }

     -- --------------------------------------------------------------
     --                        SDVB NT Table 
     -- --------------------------------------------------------------

     -- This table is valid for version XLDV1.1U only and not implemented in later
     -- snmpAgent versions.
     --

     xldv11SdvNtTable OBJECT-TYPE
	-- info-NODE:    xldv11SdvNtTable
	-- info-TREE:    xldv11CallP
	-- info-ACC:     nac
	-- info-SYNTAX:  SEQUENCE OF Xldv11SdvNtEntry
	-- info-COMMENT: SdvNt table
	-- info-IMPL:    V1.1U
	-- info-VERCTRL: -
	SYNTAX        SEQUENCE OF Xldv11SdvNtEntry
	ACCESS        not-accessible
	STATUS        mandatory
	DESCRIPTION
	     " This table contains the entries for each NT describing
	       the allowance flag for the SDVB feature."
	::= { xldv11CallP 8 }

     xldv11SdvNtEntry OBJECT-TYPE
	-- info-NODE:    xldv11SdvNtEntry
	-- info-TREE:    xldv11CallP
	-- info-INDEX:   xldv11HwUnitIndex
	-- info-ACC:     nac
	-- info-SYNTAX:  Xldv11SdvNtEntry
	-- info-COMMENT: allowance flag per NT for SDVB feature
	-- info-IMPL:    V1.1U
	-- info-VERCTRL: -
	SYNTAX        Xldv11SdvNtEntry
	ACCESS        not-accessible
	STATUS        mandatory
	DESCRIPTION
	     " The entries represent the allowance flag per NT for 
	       the SDVB feature.
	       Notifications: none "
	INDEX         { xldv11HwUnitIndex }
	::= { xldv11SdvNtTable 1 }


      Xldv11SdvNtEntry ::=
	SEQUENCE { xldv11SdvNtSwitch   INTEGER  }


     xldv11SdvNtSwitch OBJECT-TYPE
	-- info-LEAF:    xldv11SdvNtSwitch
	-- info-TREE:    xldv11CallP
	-- info-ACC:     rw
	-- info-SYNTAX:  INTEGER
	-- info-VALUE:   1..2
	-- info-COMMENT: SDVB allowance on(1), off(2)
	-- info-ROU:     GET db SET cp
	-- info-IMPL:    V1.1U
	-- info-VERCTRL: -
	SYNTAX        INTEGER { on(1),
				off(2) }
	ACCESS        read-write
	STATUS        mandatory
	DESCRIPTION
	     " This attribute specifies the allowance for the SDVB
	       service. Range of values is on, off.
	       Default value is off."
	--DEFAULT test-function-async     fsnSdvNtEntryTest
	--DEFAULT next-function-async     fsnSdvNtEntryNext
	--DEFAULT set-function-async      fsnSdvNtEntrySet
	--DEFAULT get-function-async      fsnSdvNtEntryGet
	::= { xldv11SdvNtEntry 1 }


     -- --------------------------------------------------------------
     --                  SDVB Configuration subgroup 
     -- --------------------------------------------------------------


     xldv11SdvConfig OBJECT IDENTIFIER ::= { xldv11CallP 9 }
	-- info-NODE:    xldv11SdvConfig
	-- info-TREE:    xldv11CallP
	-- info-ACC:     nac
	-- info-IMPL:    V1.1U
	-- info-VERCTRL: -

     xldv11SdvCfgVpiNni OBJECT-TYPE
	-- info-LEAF:    xldv11SdvCfgVpiNni
	-- info-TREE:    xldv11CallP
	-- info-ACC:     rw
	-- info-SYNTAX:  INTEGER
	-- info-VALUE:   0..4095
	-- info-COMMENT: -
	-- info-ROU:     GET db SET cp
	-- info-IMPL:    V1.1U
	-- info-VERCTRL: -
	SYNTAX        INTEGER (0..4095)
	ACCESS        read-write
	STATUS        mandatory
	DESCRIPTION
	     " This attribute specifies the value for the VpiNni
	       used for SDVB service. Default value is 0.
	       Notifications: 
	       xldv11TrAttributeValueChange when value is changed. "
	--DEFAULT test-function-async     fsnSdvConfigTest
	--DEFAULT next-function-async     fsnSdvConfigNext
	--DEFAULT set-function-async      fsnSdvConfigSet
	--DEFAULT get-function-async      fsnSdvConfigGet
	::= { xldv11SdvConfig 1 }

     -- --------------------------------------------------------------
     --                        ETHERNET CONFIG Table 
     -- --------------------------------------------------------------

     -- This table is valid for version XLDV1.2a.
     --

     xldv11EthernetConfigTable OBJECT-TYPE
	-- info-NODE:    xldv11EthernetConfigTable
	-- info-TREE:    xldv11CallP
	-- info-ACC:     nac
	-- info-SYNTAX:  SEQUENCE OF Xldv11EthernetConfigEntry
	-- info-COMMENT: Ethernet configuration table
	-- info-IMPL:    V1.2A->
	-- info-VERCTRL: -
	SYNTAX        SEQUENCE OF Xldv11EthernetConfigEntry
	ACCESS        not-accessible
	STATUS        mandatory
	DESCRIPTION
	     " This table contains the entries for Ethernet Configuration
		of the System"

	::= { xldv11CallP 10 }

     xldv11EthernetConfigEntry OBJECT-TYPE
	-- info-NODE:    xldv11EthernetConfigEntry
	-- info-TREE:    xldv11CallP
	-- info-INDEX:   xldv11IfIndex
	-- info-ACC:     nac
	-- info-SYNTAX:  Xldv11EthernetConfigEntry
	-- info-COMMENT: -
	-- info-IMPL:    V1.2A->
	-- info-VERCTRL: -
	SYNTAX        Xldv11EthernetConfigEntry
	ACCESS        not-accessible
	STATUS        mandatory
	DESCRIPTION
	     " The entries represent the possible attributes for the 
	       Ethernet Config Table.
	       Notifications : none. "
	INDEX         { xldv11IfIndex }
	::= { xldv11EthernetConfigTable 1 }

      Xldv11EthernetConfigEntry ::=
	SEQUENCE { xldv11EthMode              Xldv11EthNtMode,
		   xldv11EthVpiUniValue               INTEGER,
		   xldv11EthVciUniValue               INTEGER,
		   xldv11EthVciTrafficType    Xldv11TrafficType,
		   xldv11EthVciPeakCellRateUpstream  Unsigned32,
		   xldv11EthE164Isp           OCTET STRING,
		   xldv11EthIpAddressNt       IpAddress,
		   xldv11EthIpAddressSubnetMaskNt IpAddress,
		   xldv11EthIpAddressCo               IpAddress,
		   xldv11EthIpAddressSubnetMaskCo IpAddress,
		   xldv11EthIpAddressRemoteRouter IpAddress,
		   xldv11EthSustainableCellRateUpstream Unsigned32,
		   xldv11EthMaximumBurstSizeUpstream INTEGER }

     xldv11EthMode    OBJECT-TYPE
	-- info-LEAF:    xldv11EthMode
	-- info-TREE:    xldv11CallP
	-- info-ACC:     ro
	-- info-SYNTAX:  Xldv11EthNtMode
	-- info-VALUE:   bridging(V1.2A->), routing(V1.2A->)
	-- info-VALUE:   default: bridging
	-- info-COMMENT: operating mode of Ethernet NT
	-- info-ROU:     GET db
	-- info-IMPL:    V1.2A->
	-- info-VERCTRL: -
	SYNTAX        Xldv11EthNtMode 
	ACCESS        read-only
	STATUS        mandatory
	DESCRIPTION
	      " The operational mode of the ethernet configuration:
		Available modes: bridging, routing
		for V1.2A only bridging and routing.
		Default: bridging"
	--DEFAULT get-function-async      fsnEthConfigEntryGet
	--DEFAULT next-function-async     fsnEthConfigEntryNext
	::= { xldv11EthernetConfigEntry 1 }

     xldv11EthVpiUniValue    OBJECT-TYPE
	-- info-LEAF:    xldv11EthVpiUniValue
	-- info-TREE:    xldv11CallP
	-- info-ACC:     ro
	-- info-SYNTAX:  INTEGER
	-- info-VALUE:   64..4095
	-- info-COMMENT: -
	-- info-ROU:     GET db
	-- info-IMPL:    V1.2A->
	-- info-VERCTRL: -
	SYNTAX           INTEGER (64..4095)
	ACCESS           read-only
	STATUS           mandatory
	DESCRIPTION
	      " The VPI Value of the VP for UserTrafic,
		valid for all modes"
	--DEFAULT get-function-async      fsnEthConfigEntryGet
	--DEFAULT next-function-async     fsnEthConfigEntryNext
	::= { xldv11EthernetConfigEntry 2 }

     xldv11EthVciUniValue    OBJECT-TYPE
	-- info-LEAF:    xldv11EthVciUniValue 
	-- info-TREE:    xldv11CallP
	-- info-ACC:     ro
	-- info-SYNTAX:  INTEGER
	-- info-VALUE:   0..65535
	-- info-COMMENT: -
	-- info-ROU:     GET db
	-- info-IMPL:    V1.2A->
	-- info-VERCTRL: -
	SYNTAX            INTEGER (0..65535)
	ACCESS            read-only
	STATUS            mandatory
	DESCRIPTION
	      " The VCI Value of the signalling VC,
		valid for all modes"
	--DEFAULT get-function-async      fsnEthConfigEntryGet
	--DEFAULT next-function-async     fsnEthConfigEntryNext
	::= { xldv11EthernetConfigEntry 3 }

     xldv11EthVciTrafficType          OBJECT-TYPE
	-- info-LEAF:    xldv11EthVciTrafficType
	-- info-TREE:    xldv11CallP
	-- info-ACC:     ro
	-- info-SYNTAX:  Xldv11TrafficType
	-- info-VALUE:   cbr(V1.2A->), ubr(V1.2A->)
	-- info-VALUE:   nrtVbr(V1.3A->), rtVbr(V1.3A->)
	-- info-COMMENT: -
	-- info-ROU:     GET db
	-- info-IMPL:    V1.2A->
	-- info-VERCTRL: -
	SYNTAX            Xldv11TrafficType
	ACCESS            read-only
	STATUS            mandatory
	DESCRIPTION
	     " This traffic type of the Eth Vci.
	       Range of value:
		     constant bit rate    cbr
		     unspecified bit rate ubr
	       For V1.3:
		     non real time variable traffic nrtVbr,
		     real time variable traffic  rtVbr.
	       Default value: constant bit rate (cbr) . "
	--DEFAULT get-function-async      fsnEthConfigEntryGet
	--DEFAULT next-function-async     fsnEthConfigEntryNext
	::= { xldv11EthernetConfigEntry 4 }

     xldv11EthVciPeakCellRateUpstream  OBJECT-TYPE
	-- info-LEAF:    xldv11EthVciPeakCellRateUpstream
	-- info-TREE:    xldv11CallP
	-- info-ACC:     ro
	-- info-SYNTAX:  Unsigned32
	-- info-VALUE:   0..2 Giga 
	-- info-VALUE:   (default: 800 000)
	-- info-COMMENT: Identifies the peak cell rate of the
	-- info-COMMENT: VC cross connect. 
	-- info-COMMENT: unit bit/sec
	-- info-ROU:     GET db
	-- info-IMPL:    V1.2A->
	-- info-VERCTRL: -
	SYNTAX           Unsigned32
	ACCESS           read-only
	STATUS           mandatory
	DESCRIPTION
	     " This read-write attribute identifies the upstream peak cell rate
	       in bit/sec of the Eth Vci. Default value is 800 000 ."
	--DEFAULT get-function-async      fsnEthConfigEntryGet
	--DEFAULT next-function-async     fsnEthConfigEntryNext
	::= { xldv11EthernetConfigEntry 5 }

     xldv11EthE164Isp     OBJECT-TYPE
	-- info-LEAF:    xldv11EthE164Isp
	-- info-TREE:    xldv11CallP
	-- info-ACC:     ro
	-- info-SYNTAX:  OCTET STRING
	-- info-VALUE:   -
	-- info-COMMENT: -
	-- info-ROU:     GET db
	-- info-IMPL:    V1.2A->
	-- info-VERCTRL: -
	SYNTAX            OCTET STRING ( SIZE (0..20) ) 
	ACCESS            read-only
	STATUS            mandatory
	DESCRIPTION
	      " The telephon number of the Internet Service Provider,
		parameter for ipForwarding - mode"
	--DEFAULT get-function-async      fsnEthConfigEntryGet
	--DEFAULT next-function-async     fsnEthConfigEntryNext
	::= { xldv11EthernetConfigEntry 6 }

     xldv11EthIpAddressNt   OBJECT-TYPE
	-- info-LEAF:    xldv11EthIpAddressNt 
	-- info-TREE:    xldv11CallP
	-- info-ACC:     ro
	-- info-SYNTAX:  IpAddress
	-- info-VALUE:   -
	-- info-COMMENT: -
	-- info-ROU:     GET db
	-- info-IMPL:    V1.2A->
	-- info-VERCTRL: -
	SYNTAX           IpAddress
	ACCESS           read-only
	STATUS           mandatory
	DESCRIPTION
	      " The IP Address of the NT,
		parameter for ipForwarding - mode
		Default: 0.0.0.0"
	--DEFAULT get-function-async      fsnEthConfigEntryGet
	--DEFAULT next-function-async     fsnEthConfigEntryNext
	::= { xldv11EthernetConfigEntry 7 }

     xldv11EthIpAddressSubnetMaskNt   OBJECT-TYPE
	-- info-LEAF:    xldv11EthIpAddressSubnetMaskNt
	-- info-TREE:    xldv11CallP
	-- info-ACC:     ro
	-- info-SYNTAX:  IpAddress
	-- info-VALUE:   -
	-- info-COMMENT: -
	-- info-ROU:     GET db
	-- info-IMPL:    V1.2A->
	-- info-VERCTRL: -
	SYNTAX           IpAddress
	ACCESS           read-only
	STATUS           mandatory
	DESCRIPTION
	      " The subnet mask of the NT ,
		parameter for ipForwarding - mode.
		Default: 0.0.0.0"
	--DEFAULT get-function-async      fsnEthConfigEntryGet
	--DEFAULT next-function-async     fsnEthConfigEntryNext
	::= { xldv11EthernetConfigEntry 8 }


     xldv11EthIpAddressCo   OBJECT-TYPE
	-- info-LEAF:    xldv11EthIpAddressCo
	-- info-TREE:    xldv11CallP
	-- info-ACC:     ro
	-- info-SYNTAX:  IpAddress
	-- info-VALUE:   -
	-- info-COMMENT: -
	-- info-ROU:     GET db
	-- info-IMPL:    V1.2A->
	-- info-VERCTRL: -
	SYNTAX           IpAddress
	ACCESS           read-only
	STATUS           mandatory
	DESCRIPTION
	      " The IP Address of the destination NT (office side),
		parameter for ipForwarding - mode.
		Default: 0.0.0.0"
	--DEFAULT get-function-async      fsnEthConfigEntryGet
	--DEFAULT next-function-async     fsnEthConfigEntryNext
	::= { xldv11EthernetConfigEntry 9 }

     xldv11EthIpAddressSubnetMaskCo   OBJECT-TYPE
	-- info-LEAF:    xldv11EthIpAddressSubnetMaskCo
	-- info-TREE:    xldv11CallP
	-- info-ACC:     ro
	-- info-SYNTAX:  IpAddress
	-- info-VALUE:   -
	-- info-COMMENT: -
	-- info-ROU:     GET db
	-- info-IMPL:    V1.2A->
	-- info-VERCTRL: -
	SYNTAX            IpAddress
	ACCESS            read-only
	STATUS            mandatory
	DESCRIPTION
	      " The subnet mask of the CO  ,
		parameter for ipForwarding - mode.
		Default: 0.0.0.0"
	--DEFAULT get-function-async      fsnEthConfigEntryGet
	--DEFAULT next-function-async     fsnEthConfigEntryNext
	::= { xldv11EthernetConfigEntry 10 }

     xldv11EthIpAddressRemoteRouter    OBJECT-TYPE
	-- info-LEAF:    xldv11EthIpAddressRemoteRouter 
	-- info-TREE:    xldv11CallP
	-- info-ACC:     ro
	-- info-SYNTAX:  IpAddress
	-- info-VALUE:   -
	-- info-COMMENT: -
	-- info-ROU:     GET db
	-- info-IMPL:    V1.2A->
	-- info-VERCTRL: -
	SYNTAX            IpAddress
	ACCESS            read-only
	STATUS            mandatory
	DESCRIPTION
	      " The subnet mask of the ISP router  ,
		parameter for ipForwarding - mode.
		Default: 0.0.0.0"
	--DEFAULT get-function-async      fsnEthConfigEntryGet
	--DEFAULT next-function-async     fsnEthConfigEntryNext
	::= { xldv11EthernetConfigEntry 11 }

     xldv11EthSustainableCellRateUpstream OBJECT-TYPE
	-- info-LEAF:    xldv11EthSustainableCellRateUpstream
	-- info-TREE:    xldv11CallP
	-- info-ACC:     ro
	-- info-SYNTAX:  Unsigned32
	-- info-VALUE:   0.. 2 Giga (default: 800 000)
	-- info-COMMENT: -
	-- info-ROU:     GET db
	-- info-IMPL:    V1.3A->
	-- info-VERCTRL: -
	SYNTAX        Unsigned32
	ACCESS        read-only
	STATUS        mandatory
	DESCRIPTION
	     "  The upstream sustainable cell rate in cells/sec
		for nrtVbr traffic.
		Default Value: 800 000."
	--DEFAULT next-function-async     fsnEthConfigEntryNext
	--DEFAULT get-function-async      fsnEthConfigEntryGet
	::= { xldv11EthernetConfigEntry 12 }

     xldv11EthMaximumBurstSizeUpstream OBJECT-TYPE
	-- info-LEAF:    xldv11EthMaximumBurstSizeUpstream 
	-- info-TREE:    xldv11CallP
	-- info-ACC:     ro
	-- info-SYNTAX:  Integer32
	-- info-VALUE:   1..1500 (default: 32)
	-- info-COMMENT: -
	-- info-ROU:     GET db
	-- info-IMPL:    V1.3A->
	-- info-VERCTRL: -
	SYNTAX        INTEGER(1..1500)
	ACCESS        read-only
	STATUS        mandatory
	DESCRIPTION
	     "  The upstream maximum burst size tolerance in cells/sec
		for nrtVbr traffic.
		Default Value:   32."
	--DEFAULT next-function-async     fsnEthConfigEntryNext
	--DEFAULT get-function-async      fsnEthConfigEntryGet
	::= { xldv11EthernetConfigEntry 13 }

       -- --------------------------------------------------------------
       --                        CONTINUITY CHECK  
       -- --------------------------------------------------------------
       
       -- --------------------------------------------------------------
       --             Continuity Check Configuration Table for VplTps
       -- --------------------------------------------------------------
  
       -- This table is valid for version XLDV1.3B.
       --
       
       xldv11ContinuityCheckVplTpTable OBJECT-TYPE
	  -- info-NODE:    xldv11ContinuityCheckVplTpTable
	  -- info-TREE:    xldv11CallP
	  -- info-ACC:     nac
	  -- info-SYNTAX:  SEQUENCE OF Xldv11ContinuityCheckVplTpEntry
	  -- info-COMMENT: continuity check configuration table for VplTp
	  -- info-COMMENT: Entries are created when Vpl cross connects
	  -- info-COMMENT: with enabled continuity check are created. 
	  -- info-COMMENT: Entries are deleted when the continuity check is disabled 
	  -- info-COMMENT: (via xldv11ContinuityCheckControl) ."
	  -- info-IMPL:    V1.3B: rw V1.3N: ro
	  -- info-VERCTRL: -
	SYNTAX        SEQUENCE OF Xldv11ContinuityCheckVplTpEntry
	ACCESS        not-accessible
	STATUS        mandatory
	DESCRIPTION
	     " This table augments the xldv11VplTpTable with attributes
	     concerning the continuity check on Vpl connections.
	     Entries in this table are created when Vpl cross connects with
	     enabled continuity check are created. 
	     Entries are deleted when the continuity check is disabled 
	     (via xldv11ContinuityCheckControl) ."
  
	::= { xldv11CallP 11 }
  
       xldv11ContinuityCheckVplTpEntry OBJECT-TYPE
	  -- info-NODE:    xldv11ContinuityCheckVplTpEntry
	  -- info-TREE:    xldv11CallP
	  -- info-INDEX:   xldv11CvpIndex, xldv11CvpEndpointType
	  -- info-ACC:     nac
	  -- info-SYNTAX:  Xldv11ContinuityCheckVplTpEntry
	  -- info-COMMENT: -
	  -- info-IMPL:    V1.3B->
	  -- info-VERCTRL: -
	  SYNTAX        Xldv11ContinuityCheckVplTpEntry
	ACCESS        not-accessible
	STATUS        mandatory
	DESCRIPTION
	     " The entry represents the attributes of an enabled
	       continuity check at a VplTp.
		 Notifications : none. "
	INDEX         { xldv11CvpIndex, xldv11CvpEndpointType }
	::= { xldv11ContinuityCheckVplTpTable 1 }
  
  
	Xldv11ContinuityCheckVplTpEntry ::=
	SEQUENCE { xldv11CvpIndex                     Unsigned16,
		   xldv11CvpEndpointType          Xldv11EndpointType,
		   xldv11CvpTestType                  INTEGER,
		   xldv11CvpOperationalState          Xldv11OperState,
		   xldv11CvpVplTpIndex                INTEGER }
  
       xldv11CvpIndex    OBJECT-TYPE
	  -- info-LEAF:    xldv11CvpIndex
	  -- info-TREE:    xldv11CallP
	  -- info-ACC:     ro
	  -- info-SYNTAX:  Unsigned16
	  -- info-VALUE:   0..65535
	  -- info-COMMENT: A unique value to identify the source or sink
	  -- info-COMMENT: for continuity check on a Vpl connection
	  -- info-ROU:     GET db
	  -- info-IMPL:    V1.3B->
	  -- info-VERCTRL: -
	SYNTAX        Unsigned16
	ACCESS        read-only
	STATUS        mandatory
	DESCRIPTION
	      " A unique value to identify the source or sink
	      for continuity check on a Vpl connection. "
	--DEFAULT get-function-async      fsnCvpEntryGet
	--DEFAULT next-function-async     fsnCvpEntryNext
	::= { xldv11ContinuityCheckVplTpEntry 1 }
  
     xldv11CvpEndpointType OBJECT-TYPE
	-- info-LEAF:    xldv11CvpEndpointType
	-- info-TREE:    xldv11CallP
	-- info-ACC:     ro
	-- info-SYNTAX:  Xldv11EndpointType
	-- info-VALUE:   source (1), sink (2)
	-- info-COMMENT: used as index to select 
	-- info-COMMENT: a source or sink
	-- info-ROU:     GET db
	-- info-IMPL:    V1.3B->
	-- info-VERCTRL: -
	SYNTAX        Xldv11EndpointType
	ACCESS        read-only
	STATUS        mandatory
	DESCRIPTION
	     " This attribute selects the endpoint type source or sink
	     for countinuity check . "
	--DEFAULT get-function-async      fsnCvpEntryGet
	--DEFAULT next-function-async     fsnCvpEntryNext
	::= { xldv11ContinuityCheckVplTpEntry 2 }

       xldv11CvpTestType OBJECT-TYPE
	  -- info-LEAF:    xldv11CvpTestType
	  -- info-TREE:    xldv11CallP
	  -- info-ACC:     ro
	  -- info-SYNTAX:  INTEGER
	  -- info-VALUE:   segment(1), endToEnd(2) 
	  -- info-COMMENT: Type of continuity check
	  -- info-ROU:     GET db
	  -- info-IMPL:    V1.3B->
	  -- info-VERCTRL: -
	SYNTAX        INTEGER { segment      (1),
				endToEnd     (2) }
	ACCESS        read-only
	STATUS        mandatory
	DESCRIPTION
	     " The type of continuity check segment or endToEnd ."    
	  --DEFAULT next-function-async     fsnCvpEntryNext
	  --DEFAULT get-function-async      fsnCvpEntryGet
	::= { xldv11ContinuityCheckVplTpEntry 3 }
  
       xldv11CvpOperationalState OBJECT-TYPE
	  -- info-LEAF:    xldv11CvpOperationalState
	  -- info-TREE:    xldv11CallP
	  -- info-ACC:     ro
	  -- info-SYNTAX:  Xldv11OperState
	  -- info-VALUE:   enabled(1)..disabled(2)
	  -- info-COMMENT: Identifies whether or not the continuity check is
	  -- info-COMMENT: enabled or disabled.
	  -- info-ROU:     GET db
	  -- info-IMPL:    V1.3B->
	  -- info-VERCTRL: -
	SYNTAX        Xldv11OperState
	ACCESS        read-only
	STATUS        mandatory
	DESCRIPTION
	     " This read-only attribute identifies whether or not a
	     continuitycheck is enabled on the VPL/VCL termination point."
	  --DEFAULT next-function-async     fsnCvpEntryNext
	  --DEFAULT get-function-async      fsnCvpEntryGet
	::= { xldv11ContinuityCheckVplTpEntry 4 }
  
       xldv11CvpVplTpIndex    OBJECT-TYPE
	  -- info-LEAF:    xldv11CvpVplTpIndex
	  -- info-TREE:    xldv11CallP
	  -- info-ACC:     ro
	  -- info-SYNTAX:  INTEGER   
	  -- info-VALUE:   1..4096+48
	  -- info-COMMENT: Index of the related VplTp
	  -- info-ROU:     GET db
	  -- info-IMPL:    V1.3N->
	  -- info-VERCTRL: -
	SYNTAX        INTEGER (1..4144)
	ACCESS        read-only
	STATUS        mandatory
	DESCRIPTION
	      " Index of the related VplTp ."
	--DEFAULT get-function-async      fsnCvpEntryGet
	--DEFAULT next-function-async     fsnCvpEntryNext
	::= { xldv11ContinuityCheckVplTpEntry 5 }

       -- --------------------------------------------------------------
       --             Continuity Check Configuration Table for VclTps
       -- --------------------------------------------------------------
       --
       -- This table is valid for version XLDV1.3B.
       --
  
       xldv11ContinuityCheckVclTpTable OBJECT-TYPE
	  -- info-NODE:    xldv11ContinuityCheckVclTpTable
	  -- info-TREE:    xldv11CallP
	  -- info-ACC:     nac
	  -- info-SYNTAX:  SEQUENCE OF Xldv11ContinuityCheckVclTpEntry
	  -- info-COMMENT: continuity check configuration table for VclTp
	  -- info-COMMENT: Entries are created when Vcl cross connects
	  -- info-COMMENT: with enabled continuity check are created. 
	  -- info-COMMENT: Entries are deleted when the continuity check is disabled 
	  -- info-COMMENT: (via xldv11ContinuityCheckControl).
	  -- info-IMPL:    V1.3B: rw V1.3N->: ro
	  -- info-VERCTRL: -
	SYNTAX        SEQUENCE OF Xldv11ContinuityCheckVclTpEntry
	ACCESS        not-accessible
	STATUS        mandatory
	DESCRIPTION
	     " This table augments the xldv11VclTpTable with attributes
	     concerning the continuity check on Vcl connections.
	     Entries in this table are created when Vcl cross connects with
	     enabled continuity check are created. 
	     Entries are deleted when the continuity check is disabled 
	     (via xldv11ContinuityCheckControl) ."
	::= { xldv11CallP 12 }
  
       xldv11ContinuityCheckVclTpEntry OBJECT-TYPE
	  -- info-NODE:    xldv11ContinuityCheckVclTpEntry
	  -- info-TREE:    xldv11CallP
	  -- info-INDEX:   xldv11CvcIndex,xldv11CvcEndpointType
	  -- info-ACC:     nac
	  -- info-SYNTAX:  Xldv11ContinuityCheckVclTpEntry
	  -- info-COMMENT: -
	  -- info-IMPL:    V1.3B->
	  -- info-VERCTRL: -
	  SYNTAX        Xldv11ContinuityCheckVclTpEntry
	ACCESS        not-accessible
	STATUS        mandatory
	DESCRIPTION
	     " The entry represents the attributes of an enabled
	       continuity check at a VclTp.
		 Notifications : none. "
	INDEX         { xldv11CvcIndex, xldv11CvcEndpointType }
	::= { xldv11ContinuityCheckVclTpTable 1 }
  
  
	Xldv11ContinuityCheckVclTpEntry ::=
	SEQUENCE { xldv11CvcIndex                 Unsigned16,
		   xldv11CvcEndpointType          Xldv11EndpointType,
		   xldv11CvcTestType              INTEGER,
		   xldv11CvcOperationalState      Xldv11OperState,
		   xldv11CvcVclTpIndex            INTEGER }
  
       xldv11CvcIndex    OBJECT-TYPE
	  -- info-LEAF:    xldv11CvcIndex
	  -- info-TREE:    xldv11CallP
	  -- info-ACC:     ro
	  -- info-SYNTAX:  Unsigned16
	  -- info-VALUE:   0..65535
	  -- info-COMMENT: A unique value to identify the source or sink
	  -- info-COMMENT: for continuity check on a Vcl connection
	  -- info-ROU:     GET db
	  -- info-IMPL:    V1.3B->
	  -- info-VERCTRL: -
	SYNTAX        Unsigned16
	ACCESS        read-only
	STATUS        mandatory
	DESCRIPTION
	      " A unique value to identify the source or sink
	      for continuity check on a Vcl connection. "
	--DEFAULT get-function-async      fsnCvcEntryGet
	--DEFAULT next-function-async     fsnCvcEntryNext
	::= { xldv11ContinuityCheckVclTpEntry 1 }
  
     xldv11CvcEndpointType OBJECT-TYPE
	-- info-LEAF:    xldv11CvcEndpointType
	-- info-TREE:    xldv11CallP
	-- info-ACC:     ro
	-- info-SYNTAX:  Xldv11EndpointType
	-- info-VALUE:   source (1), sink (2)
	-- info-COMMENT: used as index to select 
	-- info-COMMENT: a source or sink
	-- info-ROU:     GET db
	-- info-IMPL:    V1.3B->
	-- info-VERCTRL: -
	SYNTAX        Xldv11EndpointType
	ACCESS        read-only
	STATUS        mandatory
	DESCRIPTION
	     " This attribute selects the endpoint type source or sink
	     for countinuity check . "
	--DEFAULT get-function-async      fsnCvcEntryGet
	--DEFAULT next-function-async     fsnCvcEntryNext
	::= { xldv11ContinuityCheckVclTpEntry 2 }

       xldv11CvcTestType OBJECT-TYPE
	  -- info-LEAF:    xldv11CvcTestType
	  -- info-TREE:    xldv11CallP
	  -- info-ACC:     ro
	  -- info-SYNTAX:  INTEGER
	  -- info-VALUE:   segment(1), endToEnd(2) 
	  -- info-COMMENT: Type of continuity check
	  -- info-ROU:     GET db
	  -- info-IMPL:    V1.3B->
	  -- info-VERCTRL: -
	SYNTAX        INTEGER { segment      (1),
				endToEnd     (2) }
	ACCESS        read-only
	STATUS        mandatory
	DESCRIPTION
	     " The type of continuity check segment or endToEnd ."    
	  --DEFAULT next-function-async     fsnCvcEntryNext
	  --DEFAULT get-function-async      fsnCvcEntryGet
	::= { xldv11ContinuityCheckVclTpEntry 3 }
  
       xldv11CvcOperationalState OBJECT-TYPE
	  -- info-LEAF:    xldv11CvcOperationalState
	  -- info-TREE:    xldv11CallP
	  -- info-ACC:     ro
	  -- info-SYNTAX:  Xldv11OperState
	  -- info-VALUE:   enabled(1)..disabled(2)
	  -- info-COMMENT: Identifies whether or not the continuity check is
	  -- info-COMMENT: enabled or disabled.
	  -- info-ROU:     GET db
	  -- info-IMPL:    V1.3B->
	  -- info-VERCTRL: -
	SYNTAX        Xldv11OperState
	ACCESS        read-only
	STATUS        mandatory
	DESCRIPTION
	     " This read-only attribute identifies whether or not a
	     continuitycheck is enabled on the VPL/VCL termination point."
	  --DEFAULT next-function-async     fsnCvcEntryNext
	  --DEFAULT get-function-async      fsnCvcEntryGet
	::= { xldv11ContinuityCheckVclTpEntry 4 }
       
       xldv11CvcVclTpIndex    OBJECT-TYPE
	  -- info-LEAF:    xldv11CvcVclTpIndex
	  -- info-TREE:    xldv11CallP
	  -- info-ACC:     ro
	  -- info-SYNTAX:  INTEGER   
	  -- info-VALUE:   1..4096
	  -- info-COMMENT: Index of the related VclTp
	  -- info-ROU:     GET db
	  -- info-IMPL:    V1.3N->
	  -- info-VERCTRL: -
	SYNTAX        INTEGER (1..4096)
	ACCESS        read-only
	STATUS        mandatory
	DESCRIPTION
	      " Index of the related VclTp ."
	--DEFAULT get-function-async      fsnCvcEntryGet
	--DEFAULT next-function-async     fsnCvcEntryNext
	::= { xldv11ContinuityCheckVclTpEntry 5 }

       -- --------------------------------------------------------------
       --                    continuity check control group
       -- --------------------------------------------------------------
  
       xldv11ContinuityCheckControl OBJECT IDENTIFIER ::= { xldv11CallP 13 }
	  -- info-NODE:    xldv11ContinuityCheckControl
	  -- info-TREE:    xldv11CallP 
	  -- info-ACC:     nac
	  -- info-COMMENT: Control group for activating/deactivating
	  -- info-COMMENT: the continuity check at the source/sink of 
	  -- info-COMMENT: a VPL or VCL connection.
	  -- info-IMPL:    V1.3B->
  
       -- This group handles the TMN control request for activating/deactivating 
       -- the continuity check function .
       --
  
       xldv11CocControlReq OBJECT-TYPE
	  -- info-LEAF:    xldv11CocControlReq
	  -- info-TREE:    xldv11CallP
	  -- info-ACC:     rw
	  -- info-SYNTAX:  Xldv11ControlReq
	  -- info-VALUE:   noRequest(command), continuityCheckRequest(command)  
	  -- info-VALUE:   paramFaulty, continuityCheckBusy, continuityCheckReject 
	  -- info-VALUE:   requestBusy(V1.3N->),setDataFailed(V1.3N->),
	  -- info-VALUE:   aswTimeout(V1.3N->),
	  -- info-COMMENT: Command to activate a continuity check (continuityCheckRequest)
	  -- info-COMMENT: or to deactivate a running test (noRequest).
	  -- info-ROU:     GET db  SET cp 
	  -- info-IMPL:    V1.3B->
	  -- info-VERCTRL: V1.1U->V1.3B: GET db SET blocked
	SYNTAX        Xldv11ControlReq
	ACCESS        read-write
	STATUS        mandatory
	DESCRIPTION
	     " Marks the received command to activate a continuity check
	       (continuityCheckRequest) or to deactivate (noRequest).
	       Reject reasons are faulty parameters from the SNMP agent
	       (response: paramFaulty, commExecStarted, continuityCheckReject) or a
	       continuityi check request while a running continuity check 
	       (response: continuityCheckBusy).
		 Notifications : none ."
	--DEFAULT test-function-async     fsnCocTest
	--DEFAULT next-function-async     fsnCocNext
	--DEFAULT set-function-async      fsnCocSet
	--DEFAULT get-function-async      fsnCocGet
	::= { xldv11ContinuityCheckControl 1 }
  
       xldv11CocControlStatus OBJECT-TYPE
	  -- info-LEAF:    xldv11CocControlStatus
	  -- info-TREE:    xldv11CallP
	  -- info-ACC:     ro
	  -- info-SYNTAX:  Xldv11ControlStatus
	  -- info-VALUE:   requestIdle(1), requestBusy(2), requestPassed(3)
	  -- info-VALUE:   requestFailed(4)
	  -- info-COMMENT: Control status of command.
	  -- info-ROU:     GET db
	  -- info-IMPL:    V1.3B->
	  -- info-VERCTRL: -
	SYNTAX        Xldv11ControlStatus
	ACCESS        read-only
	STATUS        mandatory
	DESCRIPTION
	     " The status of the control request. The value requestIdle will be
	       set after startup/recovery or after a running test was aborted by
	       the SNMP manager.
	       Range of value:
		  requestIdle,
		  requestBusy,
		  requestPassed,
		  requestFailed . "
	--DEFAULT next-function-async     fsnCocNext
	--DEFAULT get-function-async      fsnCocGet
	::= { xldv11ContinuityCheckControl 2 }
  
       xldv11CocEndpointType OBJECT-TYPE
	  -- info-LEAF:    xldv11CocEndpointType
	  -- info-TREE:    xldv11CallP
	  -- info-ACC:     rw
	  -- info-SYNTAX:  Xldv11EndpointType
	  -- info-VALUE:   source (1), sink (2)
	  -- info-VALUE:   both (3)
	  -- info-COMMENT: specifies whether the source or sink
	  -- info-COMMENT: should be enabled/disabled for continuity check
	  -- info-ROU:     GET db  SET db 
	  -- info-IMPL:    V1.3B->
	  -- info-VERCTRL: -
	SYNTAX        Xldv11EndpointType
	ACCESS        read-write
	STATUS        mandatory
	DESCRIPTION
	     " This attribute specifies whether the source or sink of a
	     should be enabled/disabled for countinuity check . "
	--DEFAULT test-function-async     fsnCocTest
	--DEFAULT next-function-async     fsnCocNext
	--DEFAULT set-function-async      fsnCocSet
	--DEFAULT get-function-async      fsnCocGet
	::= { xldv11ContinuityCheckControl 3 }
       
       xldv11CocOamLevel OBJECT-TYPE
	  -- info-LEAF:    xldv11CocOamLevel
	  -- info-TREE:    xldv11CallP
	  -- info-ACC:     rw
	  -- info-SYNTAX:  INTEGER
	  -- info-VALUE:   f4 (4), f5 (5)
	  -- info-COMMENT: The OAM level for continuity check on VP/VC level
	  -- info-ROU:     GET db  SET db 
	  -- info-IMPL:    V1.3B->
	  -- info-VERCTRL: -
	SYNTAX        INTEGER { f4 (4),
				f5 (5)  }
	ACCESS        read-write
	STATUS        mandatory
	DESCRIPTION
	     " The OAM level for continuity check. "
	--DEFAULT test-function-async     fsnCocTest
	--DEFAULT next-function-async     fsnCocNext
	--DEFAULT set-function-async      fsnCocSet
	--DEFAULT get-function-async      fsnCocGet
	::= { xldv11ContinuityCheckControl 4 }
       
       xldv11CocTestType OBJECT-TYPE
	  -- info-LEAF:    xldv11CocTestType
	  -- info-TREE:    xldv11CallP
	  -- info-ACC:     rw
	  -- info-SYNTAX:  INTEGER
	  -- info-VALUE:   segment(1), endToEnd(2) 
	  -- info-COMMENT: Type of continuity check
	  -- info-ROU:     GET db  SET db 
	  -- info-IMPL:    V1.3B->
	  -- info-VERCTRL: -
	SYNTAX        INTEGER { segment      (1),
				endToEnd     (2) }
	ACCESS        read-write
	STATUS        mandatory
	DESCRIPTION
	     " The type of continuity check segment or endToEnd ."    
	--DEFAULT test-function-async     fsnCocTest
	--DEFAULT next-function-async     fsnCocNext
	--DEFAULT set-function-async      fsnCocSet
	--DEFAULT get-function-async      fsnCocGet
	::= { xldv11ContinuityCheckControl 5 }
       
       xldv11CocIfIndex OBJECT-TYPE
	  -- info-LEAF:    xldv11CocIfIndex
	  -- info-TREE:    xldv11CallP
	  -- info-ACC:     rw
	  -- info-SYNTAX:  Unsigned16
	  -- info-VALUE:   0..65535
	  -- info-COMMENT: If it is ifIndex of a LU* PPTP 
	  -- info-COMMENT: then xldv11CocVpi is the  VPINni
	  -- info-COMMENT: and xldv11CocVci is the  VCINni.
	  -- info-COMMENT: If it is ifIndex of a LI* PPTP 
	  -- info-COMMENT: then xldv11CocVpi is the  VPIUni
	  -- info-COMMENT: and xldv11CocVci is the  VCINni.
	  -- info-ROU:     GET db  SET db
	  -- info-IMPL:    V1.3B->
	  -- info-VERCTRL: V1.3N->: ifIndex of LU PPTP always
	SYNTAX        Unsigned16
	ACCESS        read-write
	STATUS        mandatory
	DESCRIPTION
	       " If it is the ifIndex of a LU* PPTP then the 
	       continuity check at the VPINni side should be 
	       enabled/disabled.
	       If it is the ifIndex of a LI* PPTP then the 
	       continuity check at the VPIUni side should be
	       enabled/disabled.
	       V1.3-> : only ifIndex of LU possible as currently 
	       continuity check to feeder side is supported. "
	--DEFAULT test-function-async     fsnCocTest
	--DEFAULT next-function-async     fsnCocNext
	--DEFAULT set-function-async      fsnCocSet
	--DEFAULT get-function-async      fsnCocGet
	::= { xldv11ContinuityCheckControl 6 }
  
       xldv11CocVpi OBJECT-TYPE
	  -- info-LEAF:    xldv11CocVpi
	  -- info-TREE:    xldv11CallP
	  -- info-ACC:     rw
	  -- info-SYNTAX:  INTEGER
	  -- info-VALUE:   0..4095
	  -- info-COMMENT: Identifies the VPI which shall be tested
	  -- info-ROU:     GET db  SET db
	  -- info-IMPL:    V1.3B->
	  -- info-VERCTRL: -
	SYNTAX        INTEGER (0..4095)
	ACCESS        read-write
	STATUS        mandatory
	DESCRIPTION
	     " Identifies the VPI which shall be tested. "
	--DEFAULT test-function-async     fsnCocTest
	--DEFAULT next-function-async     fsnCocNext
	--DEFAULT set-function-async      fsnCocSet
	--DEFAULT get-function-async      fsnCocGet
	::= { xldv11ContinuityCheckControl 7 }
  
       xldv11CocVci OBJECT-TYPE
	  -- info-LEAF:    xldv11CocVci
	  -- info-TREE:    xldv11CallP
	  -- info-ACC:     rw
	  -- info-SYNTAX:  Unsigned16
	  -- info-VALUE:   0..65535
	  -- info-COMMENT: Identifies the VCI which shall be tested
	  -- info-ROU:     GET db  SET db
	  -- info-IMPL:    V1.3B->
	  -- info-VERCTRL: -
	SYNTAX        Unsigned16
	ACCESS        read-write
	STATUS        mandatory
	DESCRIPTION
	     " Identifies the VCI which shall be tested. "
	--DEFAULT test-function-async     fsnCocTest
	--DEFAULT next-function-async     fsnCocNext
	--DEFAULT set-function-async      fsnCocSet
	--DEFAULT get-function-async      fsnCocGet
	::= { xldv11ContinuityCheckControl 8 }
  
     xldv11CocControlReqResult OBJECT-TYPE
	-- info-LEAF:    xldv11CocControlReqResult
	-- info-TREE:    xldv11CallP
	-- info-ACC:     ro
	-- info-SYNTAX:  Xldv11ControlReq
	-- info-VALUE:   see xldv11CocControlReq
	-- info-COMMENT: specifies the result of user command
	-- info-ROU:     GET db
	-- info-IMPL:    V1.3N->
	-- info-VERCTRL: -
	SYNTAX        Xldv11ControlReq
	ACCESS        read-only
	STATUS        mandatory
	DESCRIPTION
	     " This read-only attribute informs about the result of 
	     the last user command."
	--DEFAULT next-function-async     fsnCocNext
	--DEFAULT get-function-async      fsnCocGet
	::= { xldv11ContinuityCheckControl 9 }

     xldv11CocControlTimeStamp OBJECT-TYPE
        -- info-LEAF:    xldv11CocControlTimeStamp
        -- info-TREE:    xldv11CallP
        -- info-ACC:     ro
        -- info-SYNTAX:  TimeTicks
        -- info-VALUE:   0..2Giga
        -- info-COMMENT: specifies the time stamp in seconds
        -- info-COMMENT: of the last command
        -- info-COMMENT: (end of command)
        -- info-ROU:     GET db
	-- info-IMPL:    V1.3N->
        -- info-VERCTRL: -
        SYNTAX        TimeTicks
        ACCESS        read-only
        STATUS        mandatory
        DESCRIPTION
           " This read-only attribute informs about the time stamp
             of the last command (end of command)."
        --DEFAULT next-function-async     fsnCocNext
        --DEFAULT get-function-async      fsnCocGet
        ::= { xldv11ContinuityCheckControl 10 }

       -- --------------------------------------------------------------
       --            Inband TMN Vpi/Vci configuration
       -- --------------------------------------------------------------
       --
       -- This group holds the configuration data for inband TMN
       --
       xldv11InbandTmn OBJECT IDENTIFIER ::= { xldv11CallP 14 }
	  -- info-NODE:    xldv11InbandTmn
	  -- info-TREE:    xldv11CallP
	  -- info-ACC:     nac
	  -- info-COMMENT: Inband TMN configuration object
	  -- info-IMPL:    V1.3N->
       
       -- This group holds the configuration data for inband TMN
       xldv11InbandVpiCurrent OBJECT-TYPE
	  -- info-LEAF:    xldv11InbandVpiCurrent
	  -- info-TREE:    xldv11CallP
	  -- info-ACC:     ro
	  -- info-SYNTAX:  INTEGER
	  -- info-VALUE:   0..4095
	  -- info-COMMENT: the current Vpi value of inband TMN
	  -- info-ROU:     GET db
	  -- info-IMPL:    V1.3N->
	  -- info-VERCTRL: -
	SYNTAX        INTEGER (0..4095)
	ACCESS        read-only
	STATUS        mandatory
	DESCRIPTION
	     " Identifies the current VPI value of inband TMN channel. "
	--DEFAULT next-function-async     fsnInbNext
	--DEFAULT get-function-async      fsnInbGet
	::= { xldv11InbandTmn 1 }
  
       xldv11InbandVciCurrent OBJECT-TYPE
	  -- info-LEAF:    xldv11InbandVciCurrent
	  -- info-TREE:    xldv11CallP
	  -- info-ACC:     ro
	  -- info-SYNTAX:  INTEGER
	  -- info-VALUE:   0..65535
	  -- info-COMMENT: the current Vci value of inband TMN
	  -- info-ROU:     GET db
	  -- info-IMPL:    V1.3N->
	  -- info-VERCTRL: -
	SYNTAX        INTEGER (0..65535)
	ACCESS        read-only
	STATUS        mandatory
	DESCRIPTION
	     " Identifies the current Vci value of inband TMN channel. "
	--DEFAULT next-function-async     fsnInbNext
	--DEFAULT get-function-async      fsnInbGet
	::= { xldv11InbandTmn 2 }

       xldv11InbandVpiConfig OBJECT-TYPE
	  -- info-LEAF:    xldv11InbandVpiConfig
	  -- info-TREE:    xldv11CallP
	  -- info-ACC:     ro
	  -- info-SYNTAX:  INTEGER
	  -- info-VALUE:   0..4095
	  -- info-COMMENT: the configured Vpi value of inband TMN.
	  -- info-COMMENT: effective only after reload
	  -- info-ROU:     GET db
	  -- info-IMPL:    V1.3N->
	  -- info-VERCTRL: -
	SYNTAX        INTEGER (0..4095)
	ACCESS        read-only
	STATUS        mandatory
	DESCRIPTION
	     " Identifies the configured Vpi value of inband TMN channel
	     which becomes effective only after reload. "
	--DEFAULT next-function-async     fsnInbNext
	--DEFAULT get-function-async      fsnInbGet
	::= { xldv11InbandTmn 3 }
  
       xldv11InbandVciConfigured OBJECT-TYPE
	  -- info-LEAF:    xldv11InbandVciConfigured
	  -- info-TREE:    xldv11CallP
	  -- info-ACC:     ro
	  -- info-SYNTAX:  INTEGER
	  -- info-VALUE:   0..65535
	  -- info-COMMENT: the configured Vci value of inband TMN.
	  -- info-COMMENT: effective only after reload
	  -- info-ROU:     GET db
	  -- info-IMPL:    V1.3N->
	  -- info-VERCTRL: -
	SYNTAX        INTEGER (0..65535)
	ACCESS        read-only
	STATUS        mandatory
	DESCRIPTION
	     " Identifies the configured Vci value of inband TMN channel
	     which becomes effective only after reload. "
	--DEFAULT next-function-async     fsnInbNext
	--DEFAULT get-function-async      fsnInbGet
	::= { xldv11InbandTmn 4 }

     -- ==============================================================
     --      H a r d w a r e   M a i n t e n a n c e   G r o u p
     -- ==============================================================
     --
     -- The managed entities are valid from XLDV1.1U.
     --

     -- XLDV1.1U :
     --    An instance of this managed entity shall be automatically
     --    created by the ATM NE immediately after system
     --    initialization is complete.
     --    In state locked the manager can overwrites the value of the
     --    attribute xldv11PiuType using the command createHwUnit of 
     --    xldv11HwuControl.
     -- XLDV1.x : 
     --    An instance of this managed entity shall be automatically
     --    created by the ATM NE immediately after system
     --    initialization is complete and immediately following the 
     --    insertion of the plugIn unit into the equipment slot.
     --    Instances can also be created or deleted by the manager
     --    (createHwUnit, deleteHwu) ."


     -- --------------------------------------------------------------
     --                         ATM NE subgroup
     -- --------------------------------------------------------------

     xldv11AtmNe OBJECT IDENTIFIER ::= { xldv11Hwm 1 }      -- (XLDV1.1U)
	-- info-NODE:    xldv11AtmNe
	-- info-TREE:    xldv11Hwm
	-- info-ACC:     nac
	-- info-IMPL:    V1.0->
	-- info-VERCTRL: -

     xldv11NeLocation OBJECT-TYPE
	-- info-LEAF:    xldv11NeLocation
	-- info-TREE:    xldv11Hwm
	-- info-ACC:     rw
	-- info-SYNTAX:  OCTET STRING ( SIZE (0..80) )
	-- info-VALUE:   -
	-- info-COMMENT: Describes the location of the NetElement
	-- info-ROU:     GET db  SET db
	-- info-IMPL:    V1.0->
	-- info-VERCTRL: -
	SYNTAX        OCTET STRING ( SIZE (0..80) )
	ACCESS        read-write
	STATUS        mandatory
	DESCRIPTION
	     " Describes the location of the NetElement, e.g. Hofmannstr. 51 . "
	--DEFAULT test-function-async     fsnNeTest
	--DEFAULT next-function-async     fsnNeNext
	--DEFAULT set-function-async      fsnNeSet
	--DEFAULT get-function-async      fsnNeGet
	::= { xldv11AtmNe 1 }

     xldv11NeVendor   OBJECT-TYPE
	-- info-LEAF:    xldv11NeVendor
	-- info-TREE:    xldv11Hwm
	-- info-ACC:     ro
	-- info-SYNTAX:  DisplayString
	-- info-VALUE:   -
	-- info-COMMENT: Contains the vendor of the NetElement
	-- info-ROU:     GET db
	-- info-IMPL:    V1.0->
	-- info-VERCTRL: -
	SYNTAX        DisplayString
	ACCESS        read-only
	STATUS        mandatory
	DESCRIPTION
	     " Contains the vendor of the NetElement, e.g. Siemens AG . "
	--DEFAULT next-function-async     fsnNeNext
	--DEFAULT get-function-async      fsnNeGet
	::= { xldv11AtmNe 2 }

     xldv11NeVersion  OBJECT-TYPE
	-- info-LEAF:    xldv11NeVersion
	-- info-TREE:    xldv11Hwm
	-- info-ACC:     ro
	-- info-SYNTAX:  DisplayString
	-- info-VALUE:   -
	-- info-COMMENT: Contains the version of the NetElement
	-- info-ROU:     GET db
	-- info-IMPL:    V1.0->
	-- info-VERCTRL: -
	SYNTAX        DisplayString
	ACCESS        read-only
	STATUS        mandatory
	DESCRIPTION
	     " Contains the version of the NetElement, e.g. XLD V1.1U . "
	--DEFAULT next-function-async     fsnNeNext
	--DEFAULT get-function-async      fsnNeGet
	::= { xldv11AtmNe 3 }

     xldv11NeExternalTime  OBJECT-TYPE
	-- info-LEAF:    xldv11NeExternalTime
	-- info-TREE:    xldv11Hwm
	-- info-ACC:     rw
	-- info-SYNTAX:  TimeTicks
	-- info-VALUE:   0..4Giga
	-- info-COMMENT: Contains the external Time of the NetElement
	-- info-ROU:     GET sn SET sn
	-- info-IMPL:    V1.0->
	-- info-VERCTRL: -
	SYNTAX        TimeTicks
	ACCESS        read-write
	STATUS        mandatory
	DESCRIPTION
	     " Contains the external Time of the NetElement. The TMN-OS sets this time after
	       firsttime power up, coldstart, warmstart or reload and refreshes the time in a
	       period of 24h . "
	--DEFAULT test-function-async     fsnNeTest
	--DEFAULT next-function-async     fsnNeNext
	--DEFAULT set-function-async      fsnNeSet
	--DEFAULT get-function-async      fsnNeGet
	::= { xldv11AtmNe 4 }

     xldv11NeTimeZone  OBJECT-TYPE
	-- info-LEAF:    xldv11NeTimeZone
	-- info-TREE:    xldv11Hwm
	-- info-ACC:     rw
	-- info-SYNTAX:  OCTET STRING ( SIZE (0..10) )
	-- info-VALUE:   ex.: 97-12-06 13:43:56
	-- info-COMMENT: Contains the TimeZone of the NetElement
	-- info-ROU:     GET db  SET db
	-- info-IMPL:    V1.0->
	-- info-VERCTRL: -
	SYNTAX        OCTET STRING ( SIZE (0..10) ) 
	ACCESS        read-write
	STATUS        mandatory
	DESCRIPTION
	     " Contains the TimeZone of the NetElement, e.g. CET . "
	--DEFAULT test-function-async     fsnNeTest
	--DEFAULT next-function-async     fsnNeNext
	--DEFAULT set-function-async      fsnNeSet
	--DEFAULT get-function-async      fsnNeGet
	::= { xldv11AtmNe 5 }

     xldv11NeDescriptorFileName  OBJECT-TYPE
	-- info-LEAF:    xldv11NeDescriptorFileName
	-- info-TREE:    xldv11Hwm
	-- info-ACC:     ro
	-- info-SYNTAX:  DisplayString
	-- info-VALUE:   -
	-- info-COMMENT: Contains the name of the descriptor file
	-- info-ROU:     GET db
	-- info-IMPL:    V1.0->
	-- info-VERCTRL: -
	SYNTAX        DisplayString
	ACCESS        read-only
	STATUS        mandatory
	DESCRIPTION
	     " Contains the name of the descriptor file. Initialized after
	       reload by SW upgrade . "
	--DEFAULT next-function-async     fsnNeNext
	--DEFAULT get-function-async      fsnNeGet
	::= { xldv11AtmNe 6 }

     xldv11NeExternalTime45020  OBJECT-TYPE
	-- info-LEAF:    xldv11NeExternalTime45020
	-- info-TREE:    xldv11Hwm
	-- info-ACC:     rw
	-- info-SYNTAX:  TimeTicks
	-- info-VALUE:   0..4Giga
	-- info-COMMENT: Contains the external Time of the NetElement. Basis is
	-- info-COMMENT: 1. January 1999, 0:00. Unit = [seconds].
	-- info-ROU:     GET sn SET sn
	-- info-IMPL:    V1.3N->
	-- info-VERCTRL: -
	SYNTAX        TimeTicks
	ACCESS        read-write
	STATUS        mandatory
	DESCRIPTION
	     " Contains the external Time of the NetElement. The TMN-45020 sets this time after
	       firsttime power up, coldstart, warmstart or reload and refreshes the time in a
	       period of 24h . The basis is 1. January 1999, 0:00"
	--DEFAULT test-function-async     fsnNeTest
	--DEFAULT next-function-async     fsnNeNext
	--DEFAULT set-function-async      fsnNeSet
	--DEFAULT get-function-async      fsnNeGet
	::= { xldv11AtmNe 7 }


     -- --------------------------------------------------------------
     --               Hardware Unit Table (XLDV1.1U)
     -- --------------------------------------------------------------

     xldv11HwUnitTable OBJECT-TYPE
	-- info-NODE:    xldv11HwUnitTable
	-- info-TREE:    xldv11Hwm
	-- info-ACC:     nac
        -- info-SYNTAX:  SEQUENCE OF Xldv11HwUnitEntry
	-- info-COMMENT: The XLD hardware unit table. This table models
	-- info-COMMENT: the Equipment, Equipment Holder and Plug-In Unit
	-- info-COMMENT: management entities.
	-- info-IMPL:    V1.0->
	-- info-VERCTRL: -
	SYNTAX        SEQUENCE OF Xldv11HwUnitEntry
	ACCESS        not-accessible
	STATUS        mandatory
	DESCRIPTION
	     " The XLD hardware unit table. This table models the Equipment,
	       Equipment Holder and Plug-In Unit management entities . "
	::= { xldv11Hwm 2 }

     xldv11HwUnitEntry OBJECT-TYPE
	-- info-NODE:    xldv11HwUnitEntry
	-- info-TREE:    xldv11Hwm
	-- info-INDEX:   xldv11HwUnitIndex
	-- info-ACC:     nac
	-- info-COMMENT: An entry in the xldv11HwUnitTable.
	-- info-IMPL:    V1.0->
	-- info-VERCTRL: -
	SYNTAX        Xldv11HwUnitEntry
	ACCESS        not-accessible
	STATUS        mandatory
	DESCRIPTION
	     " An entry in the xldv11HwUnitTable.
	       Notifications : none. "
	INDEX { xldv11HwUnitIndex }
	::= { xldv11HwUnitTable 1 }

     Xldv11HwUnitEntry ::=
	SEQUENCE { xldv11HwUnitIndex    Unsigned16,
		   xldv11HwUnitType     Xldv11HwUnitType }

     xldv11HwUnitIndex OBJECT-TYPE
	-- info-LEAF:    xldv11HwUnitIndex
	-- info-TREE:    xldv11Hwm
	-- info-ACC:     ro
	-- info-SYNTAX:  Unsigned16
	-- info-VALUE:   0..65535
	-- info-COMMENT: A unique value to identify a hardware unit.
	-- info-ROU:     GET db
	-- info-IMPL:    V1.0->
	-- info-VERCTRL: -
	SYNTAX        Unsigned16
	ACCESS        read-only
	STATUS        mandatory
	DESCRIPTION
	     " A unique value to identify a hardware unit within
	       the ATM agent. It is used as index for the tables
	       xldv11HwEquipTable, xldv11HwEquipHolderTable and
	       xldv11HwPlugInUnitTable . "
	--DEFAULT next-function-async     fsnHwUnitEntryNext
	--DEFAULT get-function-async      fsnHwUnitEntryGet
	::= { xldv11HwUnitEntry 1 }

     xldv11HwUnitType OBJECT-TYPE
	-- info-LEAF:    xldv11HwUnitType
	-- info-TREE:    xldv11Hwm
	-- info-ACC:     ro
	-- info-SYNTAX:  Xldv11HwUnitType
	-- info-VALUE:   equipment(1), equipmentHolder(2), plugInUnit(3)
	-- info-COMMENT: General type of the hardware unit.
	-- info-ROU:     GET db
	-- info-IMPL:    V1.0->
	-- info-VERCTRL: -
	SYNTAX        Xldv11HwUnitType
	ACCESS        read-only
	STATUS        mandatory
	DESCRIPTION
	     " Identifies the general type of this hardware unit.
	       The values are equipment, equipmentHolder and plugInUnit . "
	--DEFAULT next-function-async     fsnHwUnitEntryNext
	--DEFAULT get-function-async      fsnHwUnitEntryGet
	::= { xldv11HwUnitEntry 2 }


     -- --------------------------------------------------------------
     --            Hardware Containment Table (XLDV1.1U)
     -- --------------------------------------------------------------

     xldv11HwContainmentTable OBJECT-TYPE
	-- info-NODE:    xldv11HwContainmentTable
	-- info-TREE:    xldv11Hwm
	-- info-ACC:     nac
	-- info-SYNTAX:  SEQUENCE OF Xldv11HwContainmentEntry
	-- info-COMMENT: The hardware unit containment table.
	-- info-IMPL:    V1.0->
	SYNTAX        SEQUENCE OF Xldv11HwContainmentEntry
	ACCESS        not-accessible
	STATUS        mandatory
	DESCRIPTION
	     " The hardware unit containment table. This table describes
	       the containment relationships that maintain between Equipment,
	       Equipment Holder and Plug-In Unit entities . "
	::= { xldv11Hwm 3 }

     xldv11HwContainmentEntry OBJECT-TYPE
	-- info-NODE:    xldv11HwContainmentEntry
	-- info-TREE:    xldv11Hwm
	-- info-INDEX:   xldv11HwContainingUnitIndex, xldv11HwContainedUnitAddr
	-- info-ACC:     nac
	-- info-SYNTAX:  Xldv11HwContainmentEntry
	-- info-COMMENT: An entry in the hardware unit containment table.
	-- info-IMPL:    V1.0->
	-- info-VERCTRL: -
	SYNTAX        Xldv11HwContainmentEntry
	ACCESS        not-accessible
	STATUS        mandatory
	DESCRIPTION
	     " An entry in the hardware unit containment table. Each entry
	       of this type identifies two hardware units, one of which is
	       contained directly within the other .
	       Notifications : none. "
	INDEX { xldv11HwContainingUnitIndex,
		xldv11HwContainedUnitAddr }
	::= { xldv11HwContainmentTable 1 }

     Xldv11HwContainmentEntry ::=
	SEQUENCE { xldv11HwContainingUnitIndex Unsigned16,
		   xldv11HwContainedUnitAddr   INTEGER,
		   xldv11HwContainedUnitIndex  Unsigned16 }

     xldv11HwContainingUnitIndex OBJECT-TYPE
	-- info-LEAF:    xldv11HwContainingUnitIndex
	-- info-TREE:    xldv11Hwm
	-- info-ACC:     ro
	-- info-SYNTAX:  Unsigned16
	-- info-VALUE:   0..65535
	-- info-COMMENT: Index of the containing hardware unit.
	-- info-ROU:     GET db
	-- info-IMPL:    V1.0->
	-- info-VERCTRL: -
	SYNTAX        Unsigned16
	ACCESS        read-only
	STATUS        mandatory
	DESCRIPTION
	     " The index, in the xldv11HwUnitTable, of the containing hardware
	       unit in this pair . "
	--DEFAULT next-function-async     fsnHwContEntryNext
	--DEFAULT get-function-async      fsnHwContEntryGet
	::= { xldv11HwContainmentEntry 1 }

     xldv11HwContainedUnitAddr OBJECT-TYPE
	-- info-LEAF:    xldv11HwContainedUnitAddr
	-- info-TREE:    xldv11Hwm
	-- info-ACC:     ro
	-- info-SYNTAX:  INTEGER
	-- info-VALUE:   1..512
	-- info-COMMENT: Index of the contained HW unit.
	-- info-ROU:     GET db
	-- info-IMPL:    V1.0->
	-- info-VERCTRL: -
	SYNTAX        INTEGER (1..512)
	ACCESS        read-only
	STATUS        mandatory
	DESCRIPTION
	     " A number uniquely identifying, within the containing hardware
	       unit, the contained unit.
	       Contained unit should be addressed starting at 1. If the
	       contained component is an Equipment Holder, this object
	       represents its physical location (e.g.  slot number). If a
	       single piece of Equipment contains both Equipment Holder and
	       other Equipment objects, the Equipment Holders should have
	       the lowest-valued addresses, so this relationship can be
	       maintained. A Plug-In Unit always has an address of 1 .  "
	--DEFAULT next-function-async     fsnHwContEntryNext
	--DEFAULT get-function-async      fsnHwContEntryGet

	::= { xldv11HwContainmentEntry 2 }

     xldv11HwContainedUnitIndex OBJECT-TYPE
	-- info-LEAF:    xldv11HwContainedUnitIndex
	-- info-TREE:    xldv11Hwm
	-- info-ACC:     ro
	-- info-SYNTAX:  Unsigned16
	-- info-VALUE:   0..65535
	-- info-COMMENT: Index of the contained HW unit. 
	-- info-ROU:     GET db
	-- info-IMPL:    V1.0->
	-- info-VERCTRL: -
	SYNTAX        Unsigned16
	ACCESS        read-only
	STATUS        mandatory
	DESCRIPTION
	     " The index, in the xldv11HwUnitTable, of the contained hardware
	       unit in this pair. "
	--DEFAULT next-function-async     fsnHwContEntryNext
	--DEFAULT get-function-async      fsnHwContEntryGet
	::= { xldv11HwContainmentEntry 3 }


     -- --------------------------------------------------------------
     --                  Hardware Equipment Table
     -- --------------------------------------------------------------

     xldv11HwEquipTable OBJECT-TYPE
	-- info-NODE:    xldv11HwEquipTable
	-- info-TREE:    xldv11Hwm
	-- info-ACC:     nac
	-- info-SYNTAX:  SEQUENCE OF Xldv11HwEquipEntry
	-- info-COMMENT: The hardware equipment table.
	-- info-IMPL:    V1.0->
	-- info-VERCTRL: -
	SYNTAX        SEQUENCE OF Xldv11HwEquipEntry
	ACCESS        not-accessible
	STATUS        mandatory
	DESCRIPTION
	     " The hardware equipment table. "
	::= { xldv11Hwm 4 }

     xldv11HwEquipEntry OBJECT-TYPE
	-- info-NODE:    xldv11HwEquipEntry
	-- info-TREE:    xldv11Hwm
	-- info-INDEX:   xldv11HwUnitIndex
	-- info-ACC:     nac
	-- info-SYNTAX:  Xldv11HwEquipEntry
	-- info-COMMENT: Entry of the HW equipment table.
	-- info-IMPL:    V1.0->
	-- info-VERCTRL: -
	SYNTAX        Xldv11HwEquipEntry
	ACCESS        not-accessible
	STATUS        mandatory
	DESCRIPTION
	     " The entries represent the various manageable physical
	       components of the ATM NE that are not modelled via the
	       Plug-In Unit managed entity.
	       An instance of this managed entity shall be automati-
	       cally created by the ATM NE immediately following the
	       initialization/installation of the externally
	       manageable physical component in the ATM NE.
	       Notifications : xldv11TrObjCreate (V1.1),
	       xldv11TrObjDelete (V1.1)."
	INDEX         { xldv11HwUnitIndex }
	::= { xldv11HwEquipTable 1 }

     Xldv11HwEquipEntry ::=
	SEQUENCE { xldv11EquType               DisplayString,
		   xldv11EquLocation           OCTET STRING,
		   xldv11EquUserLabel          OCTET STRING,
		   xldv11EquConnectedPiuIndex  Unsigned16,
		   xldv11EquConnectedPiuPort   INTEGER }

     xldv11EquType OBJECT-TYPE
	-- info-LEAF:    xldv11EquType
	-- info-TREE:    xldv11Hwm
	-- info-ACC:     ro
	-- info-SYNTAX:  DisplayString (SIZE (0..10))
	-- info-VALUE:   onu, ntAdsl, ntVdsl, ntCpe
	-- info-COMMENT: Type of equipment.
	-- info-ROU:     GET db
	-- info-IMPL:    V1.0->
	-- info-VERCTRL: -
	SYNTAX        DisplayString (SIZE (0..10))
	ACCESS        read-only
	STATUS        mandatory
	DESCRIPTION
	     " This attribute indicates wheather the equipment is an ONU,
	       ntAdsl, ntVdsl or a ntCpe ( customer premise equipment) . "
	--DEFAULT next-function-async     fsnEquEntryNext
	--DEFAULT get-function-async      fsnEquEntryGet
	::= { xldv11HwEquipEntry 1 }

     xldv11EquLocation OBJECT-TYPE
	-- info-LEAF:    xldv11EquLocation
	-- info-TREE:    xldv11Hwm
	-- info-ACC:     rw
	-- info-SYNTAX:  OCTET STRING ( SIZE (0..80) )
	-- info-VALUE:   e.g.: "Rack 23"
	-- info-COMMENT: Location of equipment.
	-- info-ROU:     GET db  SET db
	-- info-IMPL:    V1.0->
	-- info-VERCTRL: -
	SYNTAX        OCTET STRING ( SIZE (0..80) )
	ACCESS        read-write
	STATUS        mandatory
	DESCRIPTION
	     " This attribute identifies the specific or general location of the
	       ATM NE component . "
	--DEFAULT test-function-async     fsnEquEntryTest
	--DEFAULT next-function-async     fsnEquEntryNext
	--DEFAULT set-function-async      fsnEquEntrySet
	--DEFAULT get-function-async      fsnEquEntryGet
	::= { xldv11HwEquipEntry 2 }

     xldv11EquUserLabel OBJECT-TYPE
	-- info-LEAF:    xldv11EquUserLabel
	-- info-TREE:    xldv11Hwm
	-- info-ACC:     rw
	-- info-SYNTAX:  OCTET STRING ( SIZE (0..80) )
	-- info-VALUE:   e.g.: "XLD Testbed"
	-- info-COMMENT: User friendly name of the equipment.
	-- info-ROU:     GET db  SET db
	-- info-IMPL:    V1.0->
	-- info-VERCTRL: -
	SYNTAX        OCTET STRING ( SIZE (0..80) )
	ACCESS        read-write
	STATUS        mandatory
	DESCRIPTION
	     " This attribute is used to assign a user friendly name to the
	       associated managed entity . "
	--DEFAULT test-function-async     fsnEquEntryTest
	--DEFAULT next-function-async     fsnEquEntryNext
	--DEFAULT set-function-async      fsnEquEntrySet
	--DEFAULT get-function-async      fsnEquEntryGet
	::= { xldv11HwEquipEntry 3 }

     xldv11EquConnectedPiuIndex OBJECT-TYPE
	-- info-LEAF:    xldv11EquConnectedPiuIndex
	-- info-TREE:    xldv11Hwm
	-- info-ACC:     ro
	-- info-SYNTAX:  Unsigned16
	-- info-VALUE:   0..65535
	-- info-COMMENT: default = 0.
	-- info-COMMENT: 0 in case of ONU.
	-- info-COMMENT: Hw unit index of connected PIU (in case of NT).
	-- info-ROU:     GET db
	-- info-IMPL:    V1.x->
	-- info-VERCTRL: V1.1U->: GET db
	SYNTAX        Unsigned16
	ACCESS        read-only
	STATUS        mandatory
	DESCRIPTION
	     " This attribute is used to show the PIU to which the NT is
	       connencted (HwUnitIndex) . In case of ONU value is 0."
	--DEFAULT next-function-async     fsnEquEntryNext
	--DEFAULT get-function-async      fsnEquEntryGet
	::= { xldv11HwEquipEntry 4 }

     xldv11EquConnectedPiuPort OBJECT-TYPE
	-- info-LEAF:    xldv11EquConnectedPiuPort
	-- info-TREE:    xldv11Hwm
	-- info-ACC:     ro
	-- info-SYNTAX:  INTEGER
	-- info-VALUE:   0..255
	-- info-COMMENT: default = 0.
	-- info-COMMENT: The port ID of the connected PIU.
	-- info-ROU:     GET db
	-- info-IMPL:    V1.x->
	-- info-VERCTRL: V1.1U->: GET db
	SYNTAX        INTEGER (0..255)
	ACCESS        read-only
	STATUS        mandatory
	DESCRIPTION
	     " This attribute is used to show the PIU port to which the NT is
	       connencted.
	       Default value: 0 . "
	--DEFAULT next-function-async     fsnEquEntryNext
	--DEFAULT get-function-async      fsnEquEntryGet
	::= { xldv11HwEquipEntry 5 }


     -- --------------------------------------------------------------
     --             Hardware Equipment Holder Table
     -- --------------------------------------------------------------

     xldv11HwEquipHolderTable OBJECT-TYPE
	-- info-NODE:    xldv11HwEquipHolderTable
	-- info-TREE:    xldv11Hwm
	-- info-ACC:     nac
	-- info-SYNTAX:  SEQUENCE OF Xldv11HwEquipHolderEntry
	-- info-COMMENT: Euqipment holder table.
	-- info-IMPL:    V1.0->
	-- info-VERCTRL: -
	SYNTAX        SEQUENCE OF Xldv11HwEquipHolderEntry
	ACCESS        not-accessible
	STATUS        mandatory
	DESCRIPTION
	     " The equipment holder entry table . "
	::= { xldv11Hwm 5 }

     xldv11HwEquipHolderEntry OBJECT-TYPE
	-- info-NODE:    xldv11HwEquipHolderEntry
	-- info-TREE:    xldv11Hwm
	-- info-INDEX:   xldv11HwUnitIndex
	-- info-ACC:     nac
	-- info-SYNTAX:  Xldv11HwEquipHolderEntry
	-- info-COMMENT: Entry of the equipment holder table.
	-- info-IMPL:    V1.0->
	-- info-VERCTRL: -
	SYNTAX        Xldv11HwEquipHolderEntry
	ACCESS        not-accessible
	STATUS        mandatory
	DESCRIPTION
	     " The entries represent physical resources of the ATM NE
	       holding other physical resources. Examples of resources
	       represented by instances of this managed entity are
	       shelves and slots.
	       An instance of this managed entity shall exist for each
	       shelf and slot of the ATM NE. Instances shall be auto-
	       matically created and reported by the ATM NE once
	       system initialization is complete.
	       Notifications : xldv11TrObjCreate (V1.1),
	       xldv11TrObjDelete (V1.1),
	       xldv11TrSwVersionSet when xldv11EqhSwVersion,
	       xldv11EqhMnemoCode,xldv11EqhFwItemNumber set."
	INDEX         { xldv11HwUnitIndex }
	::= { xldv11HwEquipHolderTable 1 }

     Xldv11HwEquipHolderEntry ::=
	SEQUENCE { xldv11EqhType            Xldv11EqhType,
		   xldv11EqhAccPiuTypes     DisplayString,
		   xldv11EqhSlotStatus      Xldv11SlotStatus,
		   xldv11EqhSwVersion       OCTET STRING,
		   xldv11EqhMnemoCode       OCTET STRING,
		   xldv11EqhFwCode          OCTET STRING,
		   xldv11EqhRiMnemoCode     DisplayString,
		   xldv11EqhRiFwItemNumber  DisplayString,
		   xldv11EqhRiFwIssue       DisplayString,
		   xldv11EqhRiHwItemNumber  DisplayString,
		   xldv11EqhRiHwIssue       DisplayString, 
		   xldv11EqhRiSerialNumber  DisplayString
		   } 


     xldv11EqhType OBJECT-TYPE
	-- info-LEAF:    xldv11EqhType
	-- info-TREE:    xldv11Hwm
	-- info-ACC:     ro
	-- info-SYNTAX:  Xldv11EqhType
	-- info-COMMENT: Type of the equipment holder.
	-- info-VALUE:   slot( V1.0->), basicShelf( V1.1U->), 
	-- info-VALUE:   extendedShelf( V1.1U->), ntAdslShelf( V1.1U->), 
	-- info-VALUE:   cpeShelf(V1.3A->) 
	-- info-VALUE:   ntVdslShelf(V1.x->) 
	-- info-COMMENT: Type of the equipment holder.
	-- info-ROU:     GET db
	-- info-IMPL:    V1.0->
	-- info-VERCTRL: -
	SYNTAX        Xldv11EqhType
	ACCESS        read-only
	STATUS        mandatory
	DESCRIPTION
	     " Attribute to indicate whether the equipment holder
	       instance is being used to represent a .. (see values).
	       The range of values is:
	       basicShelf     (for ONU),
	       extendedShelf  (for ONU),
	       ntAdslShelf    (for NT),
	       cpeShelf       (for CPE customer premise equipment),
	       ntVdslShelf    (for NT),
	       slot . "
	--DEFAULT test-function-async     fsnEqhEntryTest
	--DEFAULT next-function-async     fsnEqhEntryNext
	--DEFAULT set-function-async      fsnEqhEntrySet
	--DEFAULT get-function-async      fsnEqhEntryGet
	::= { xldv11HwEquipHolderEntry 1 }

     xldv11EqhAccPiuTypes OBJECT-TYPE
	-- info-LEAF:    xldv11EqhAccPiuTypes
	-- info-TREE:    xldv11Hwm
	-- info-ACC:     ro
	-- info-SYNTAX:  DisplayString (SIZE (0..200))
	-- info-VALUE:   'LU155:OM', 'UPL:A', 'POSUA:2P', 'POSUA:2I',
	-- info-VALUE:   'CMU:A', 'SUAD:16',
	-- info-VALUE:   'LTAD:1P', 'LTAD:2P', 'LTAD:2I',
	-- info-VALUE:   'NTAD:1P', 'NTAD:1I', 'LI25:1', 
	-- info-VALUE:   XLDV1.1U->: 'LUPON:O', 'LI25:2', 'LIETH25:11', 'PSAM:A'
	-- info-VALUE:   XLDV1.2->: 'LU155:OL', 'CMU:B', 'SUAD:16T',
	-- info-VALUE:   XLDV1.3->: 'CMU:C', 'LU155:C', 'LUDSX3:C' , 'CPE'
	-- info-VALUE:   XLDV1.x->: 'POSUV:4', 'SUVD:4', 'NTVD:1'
	-- info-COMMENT: Accepted PIU Types.
	-- info-ROU:     GET db
	-- info-IMPL:    V1.0->
	-- info-VERCTRL: -
	SYNTAX        DisplayString (SIZE (0..200))
	ACCESS        read-only
	STATUS        mandatory
	DESCRIPTION
	     " This attribute identifies the types of Plug-In Units to be
	       supported by this slot. They are separated by newline
	       characters. That means 'CR LF'.
	       This attribute only supplies if the Equipment holder
	       instance represents a slot.
	       Possible strings are the following:
	       'LU155:OM', 'UPL:A',
	       'POSUA:2P', 'POSUA:2I', 'CMU:A',
	       'SUAD:16', 'LTAD:1P', 'LTAD:2P', 'LTAD:2I',
	       'NTAD:1P', 'NTAD:1I', 'LI25:1', 'LIETH:1',
		additionals for XLDV1.1U :
		'LUPON:O', 'LI25:2', 'LIETH25:11', 'PSAM:A'
		additionals for XLDV1.2 :
		'LU155:OL', 'CMU:B', 'SUAD:16T', 
		additionals for XLDV1.3 :
		'CMU:C', 'LU155:C', 'LUDSX3:C' , 'CPE'
		additionals for XLDV1.x :
		'POSUV:4', 'SUVD:4', 'NTVD:1' . "
	--DEFAULT next-function-async     fsnEqhEntryNext
	--DEFAULT get-function-async      fsnEqhEntryGet
	::= { xldv11HwEquipHolderEntry 2 }

     xldv11EqhSlotStatus OBJECT-TYPE
	-- info-LEAF:    xldv11EqhSlotStatus
	-- info-TREE:    xldv11Hwm
	-- info-ACC:     ro
	-- info-SYNTAX:  Xldv11SlotStatus
	-- info-VALUE:   unknown(0), used(1), empty(2)
	-- info-COMMENT: Indicates whether a slot is empty or used.
	-- info-ROU:     GET hm
	-- info-IMPL:    V1.0->
	-- info-VERCTRL: ->
	SYNTAX        Xldv11SlotStatus
	ACCESS        read-only
	STATUS        mandatory
	DESCRIPTION
	     " Indicates whether a slot is empty or used.
	       This attribute only supplies if the Equipment holder
	       instance represents a slot.
	       The range of values is:
	       used,
	       empty,
	       unknown . Default is unknown."
	--DEFAULT next-function-async     fsnEqhEntryNext
	--DEFAULT get-function-async      fsnEqhEntryGet
	::= { xldv11HwEquipHolderEntry 3 }

     xldv11EqhSwVersion OBJECT-TYPE
	-- info-LEAF:    xldv11EqhSwVersion
	-- info-TREE:    xldv11Hwm
	-- info-ACC:     ro
	-- info-SYNTAX:  OCTET STRING ( SIZE (0..50) )
	-- info-VALUE:   Version of SW load
	-- info-COMMENT: Identifies the software load of this PIU.
	-- info-ROU:     GET db
	-- info-IMPL:    V1.1U->V1.3B:rw V1.3N->
	-- info-VERCTRL: -
	SYNTAX        OCTET STRING ( SIZE (0..50) )
	ACCESS        read-only
	STATUS        mandatory
	DESCRIPTION
	     " This attribute identifies the software load, if there
	       is any, which is currently designated as the one to
	       be loaded to the plug-in-unit whenever an automatic
	       reload of software is needed.
	       This attribute only applies if the equipment holder
	       instance represents a slot.
	       Default value for not loadable units is \0 . "
	--DEFAULT next-function-async     fsnEqhEntryNext
	--DEFAULT get-function-async      fsnEqhEntryGet
	::= { xldv11HwEquipHolderEntry 4 }

     xldv11EqhMnemoCode OBJECT-TYPE
	-- info-LEAF:    xldv11EqhMnemoCode
	-- info-TREE:    xldv11Hwm
	-- info-ACC:     ro
	-- info-SYNTAX:  OCTET STRING ( SIZE (0..19) )
	-- info-VALUE:   Mnemo Code of PIU.
	-- info-COMMENT: Specifies the mnemo code used to retrieve the SW
	-- info-COMMENT: loadfile for the PIU.
	-- info-ROU:     GET db
	-- info-IMPL:    V1.1U->V1.3B:rw V1.3N->
	-- info-VERCTRL: -
	SYNTAX        OCTET STRING ( SIZE (0..19) )
	ACCESS        read-only
	STATUS        mandatory
	DESCRIPTION
	     " This attribute specifies the mnemo code used to retrieve the SW
	       loadfile for the plug-in unit.
	       Default value for not loadable units is \0 . "
	--DEFAULT next-function-async     fsnEqhEntryNext
	--DEFAULT get-function-async      fsnEqhEntryGet
	::= { xldv11HwEquipHolderEntry 5 }

     xldv11EqhFwCode OBJECT-TYPE
	-- info-LEAF:    xldv11EqhFwCode
	-- info-TREE:    xldv11Hwm
	-- info-ACC:     ro
	-- info-SYNTAX:  OCTET STRING ( SIZE (0..20) )
	-- info-VALUE:   FW code
	-- info-COMMENT: Specifies the FW code used to retrieve the SW
	-- info-COMMENT: loadfile for the plug-in unit.
	-- info-ROU:     GET db
	-- info-IMPL:    V1.1U->V1.3B:rw V1.3N->
	-- info-VERCTRL: - 
	SYNTAX        OCTET STRING ( SIZE (0..20) )
	ACCESS        read-only
	STATUS        mandatory
	DESCRIPTION
	     " This attribute specifies the FW code used to retrieve the SW
	       loadfile for the plug-in unit.
	       Default value for not loadable units is \0 . "
	--DEFAULT next-function-async     fsnEqhEntryNext
	--DEFAULT get-function-async      fsnEqhEntryGet
	::= { xldv11HwEquipHolderEntry 6 }

     xldv11EqhRiMnemoCode OBJECT-TYPE
	-- info-LEAF:    xldv11EqhRiMnemoCode
	-- info-TREE:    xldv11Hwm
	-- info-ACC:     ro
	-- info-SYNTAX:  DisplayString (SIZE (0..20))
	-- info-VALUE:   Default: "\0"
	-- info-COMMENT: Specifies the mnemo code of the currently plugged PIU.
	-- info-ROU:     GET hm
	-- info-IMPL:    V1.0->
	-- info-VERCTRL: - 
	SYNTAX        DisplayString (SIZE (0..20))
	ACCESS        read-only
	STATUS        mandatory
	DESCRIPTION
	     " This attribute specifies the mnemo code of the currently plugged
	       PIU. Default value is \0 . "
	--DEFAULT next-function-async     fsnEqhEntryNext
	--DEFAULT get-function-async      fsnEqhEntryGet
	::= { xldv11HwEquipHolderEntry 7 }

     xldv11EqhRiFwItemNumber OBJECT-TYPE
	-- info-LEAF:    xldv11EqhRiFwItemNumber
	-- info-TREE:    xldv11Hwm
	-- info-ACC:     ro
	-- info-SYNTAX:  DisplayString (SIZE (0..20))
	-- info-VALUE:   Default: "\0"
	-- info-COMMENT: Specifies the FW item number of the currently plugged PIU.
	-- info-ROU:     GET hm
	-- info-IMPL:    V1.0->
	-- info-VERCTRL: -
	SYNTAX        DisplayString (SIZE (0..20))
	ACCESS        read-only
	STATUS        mandatory
	DESCRIPTION
	     " This attribute specifies the FW item number of the currently
	       plugged PIU. Default value is \0 . "
	--DEFAULT next-function-async     fsnEqhEntryNext
	--DEFAULT get-function-async      fsnEqhEntryGet
	::= { xldv11HwEquipHolderEntry 8 }

     xldv11EqhRiFwIssue OBJECT-TYPE
	-- info-LEAF:    xldv11EqhRiFwIssue
	-- info-TREE:    xldv11Hwm
	-- info-ACC:     ro
	-- info-SYNTAX:  DisplayString (SIZE (0..10))
	-- info-VALUE:   Default: "\0"
	-- info-COMMENT: Specifies the FW item issue of the currently plugged PIU.
	-- info-ROU:     GET hm
	-- info-IMPL:    V1.0->
	-- info-VERCTRL: -
	SYNTAX        DisplayString (SIZE (0..10))
	ACCESS        read-only
	STATUS        mandatory
	DESCRIPTION
	     " This attribute specifies the FW item issue of the currently
	       plugged PIU. Default value is \0 . "
	--DEFAULT next-function-async     fsnEqhEntryNext
	--DEFAULT get-function-async      fsnEqhEntryGet
	::= { xldv11HwEquipHolderEntry 9 }

     xldv11EqhRiHwItemNumber OBJECT-TYPE
	-- info-LEAF:    xldv11EqhRiHwItemNumber
	-- info-TREE:    xldv11Hwm
	-- info-ACC:     ro
	-- info-SYNTAX:  DisplayString (SIZE (0..20))
	-- info-VALUE:   Default: "\0"
	-- info-COMMENT: Specifies the HW item number of the currently plugged PIU.
	-- info-ROU:     GET hm 
	-- info-IMPL:    V1.0->
	-- info-VERCTRL: -
	SYNTAX        DisplayString (SIZE (0..20))
	ACCESS        read-only
	STATUS        mandatory
	DESCRIPTION
	     " This attribute specifies the HW item number of the currently
	       plugged PIU. Default value is \0 . "
	--DEFAULT next-function-async     fsnEqhEntryNext
	--DEFAULT get-function-async      fsnEqhEntryGet
	::= { xldv11HwEquipHolderEntry 10 }

     xldv11EqhRiHwIssue OBJECT-TYPE
	-- info-LEAF:    xldv11EqhRiHwIssue
	-- info-TREE:    xldv11Hwm
	-- info-ACC:     ro
	-- info-SYNTAX:  DisplayString (SIZE (0..10))
	-- info-VALUE:   Default: "\0"
	-- info-COMMENT: Specifies the HW item issue of the currently plugged PIU. 
	-- info-ROU:     GET hm 
	-- info-IMPL:    V1.0->
	-- info-VERCTRL: -
	SYNTAX        DisplayString (SIZE (0..10))
	ACCESS        read-only
	STATUS        mandatory
	DESCRIPTION
	     " This attribute specifies the HW item issue of the currently
	       plugged PIU. Default value is \0 . "
	--DEFAULT next-function-async     fsnEqhEntryNext
	--DEFAULT get-function-async      fsnEqhEntryGet
	::= { xldv11HwEquipHolderEntry 11 }

     xldv11EqhRiSerialNumber OBJECT-TYPE
	-- info-LEAF:    xldv11EqhRiSerialNumber
	-- info-TREE:    xldv11Hwm
	-- info-ACC:     ro
	-- info-SYNTAX:  DisplayString (SIZE (0..10))
	-- info-VALUE:   Default: "\0"
	-- info-COMMENT: Specifies the Serial Number of the currently plugged PIU. 
	-- info-ROU:     GET hm 
	-- info-IMPL:    V1.0->
	-- info-VERCTRL: -
	SYNTAX        DisplayString (SIZE (0..10))
	ACCESS        read-only
	STATUS        mandatory
	DESCRIPTION
	     " This attribute specifies the Serial Number of the currently
	       plugged PIU. Default value is \0 . "
	--DEFAULT next-function-async     fsnEqhEntryNext
	--DEFAULT get-function-async      fsnEqhEntryGet
	::= { xldv11HwEquipHolderEntry 12 }

     -- --------------------------------------------------------------
     --            Hardware Plug-In Unit Table (XLDV1.1U)
     -- --------------------------------------------------------------

     xldv11HwPlugInUnitTable OBJECT-TYPE
	-- info-NODE:    xldv11HwPlugInUnitTable
	-- info-TREE:    xldv11Hwm
	-- info-ACC:     nac
	-- info-SYNTAX:  SEQUENCE OF Xldv11HwPlugInUnitEntry
	-- info-COMMENT: Table of plug in units.
	-- info-IMPL:    V1.0->
	SYNTAX        SEQUENCE OF Xldv11HwPlugInUnitEntry
	ACCESS        not-accessible
	STATUS        mandatory
	DESCRIPTION
	     " Table containing the plug-in unit entries . "
	::= { xldv11Hwm 6 }

     xldv11HwPlugInUnitEntry OBJECT-TYPE
	-- info-NODE:    xldv11HwPlugInUnitEntry
	-- info-TREE:    xldv11Hwm
	-- info-INDEX:   xldv11HwUnitIndex
	-- info-ACC:     nac
	-- info-SYNTAX:  Xldv11HwPlugInUnitEntry
	-- info-COMMENT: Entry of plug in unit table.
	-- info-IMPL:    V1.0->
	SYNTAX        Xldv11HwPlugInUnitEntry
	ACCESS        not-accessible
	STATUS        mandatory
	DESCRIPTION
	     " Each entry is used to represent equipment that is inserted
	       (plugged into) and removed from slots of the ATM NE .
	       Notifications : 
		 xldv11TrStateChangeOper, 
		 xldv11TrStateChangeAdmin,
		 xldv11TrTrObjCreate, xldv11TrObjDelete,
		 alarm traps when a fault has been detected or cleared. "
	INDEX { xldv11HwUnitIndex }
	::= { xldv11HwPlugInUnitTable 1 }

     Xldv11HwPlugInUnitEntry ::=
	SEQUENCE { xldv11PiuAdminState          Xldv11AdminState,
		   xldv11PiuAvailStatus         Xldv11AvailStatus,
		   xldv11PiuOperState           Xldv11OperState,
		   xldv11PiuType                DisplayString,
		   xldv11PiuAlarmSeverityIndex  Xldv11AlmSevProfileIndex,
		   xldv11PiuAlarmFilteringIndex Xldv11AlmFiltProfileIndex,
                   xldv11PiuUpgradeResult       Xldv11ControlReq
		   }

     xldv11PiuAdminState OBJECT-TYPE
	-- info-LEAF:    xldv11PiuAdminState
	-- info-TREE:    xldv11Hwm
	-- info-ACC:     rw
	-- info-SYNTAX:  Xldv11AdminState
	-- info-VALUE:   unlocked(1), locked(2)
	-- info-COMMENT: This attribute is used to activate (unlock) and
	-- info-COMMENT: deactivate (lock) the plug-in unit.
	-- info-ROU:     GET db  SET hm 
	-- info-IMPL:    V1.0->
	-- info-VERCTRL: -
	SYNTAX        Xldv11AdminState
	ACCESS        read-write
	STATUS        mandatory
	DESCRIPTION
	     " This attribute is used to activate (unlock) and deactivate
	       (lock) the functions performed by the plug-in unit.
	       Default is locked except for LU155:OM, LU155:OL, LUPON:O,
	       LUDSX3:C. For LU155:OM, LU155:OL, LUPON:O, LUDSX3:C locking
	       is only allowed from LCT.
	       In the transition from lock to unlock the Plug-In Unit is
	       diagnosed.
	       The range of values is: unlocked, locked . "
	--DEFAULT test-function-async     fsnPiuEntryTest
	--DEFAULT next-function-async     fsnPiuEntryNext
	--DEFAULT set-function-async      fsnPiuEntrySet
	--DEFAULT get-function-async      fsnPiuEntryGet
	::= { xldv11HwPlugInUnitEntry 1 }

     xldv11PiuAvailStatus OBJECT-TYPE
	-- info-LEAF:    xldv11PiuAvailStatus
	-- info-TREE:    xldv11Hwm
	-- info-ACC:     ro
	-- info-SYNTAX:  Xldv11AvailStatus
	-- info-VALUE:   available(1), failed(2), degraded(3), offline(4)
	-- info-VALUE:   notInstalled(5)
	-- info-COMMENT: Availability status of the PIU.
	-- info-ROU:     GET db
	-- info-IMPL:    V1.0->
	-- info-VERCTRL: -
	SYNTAX        Xldv11AvailStatus
	ACCESS        read-only
	STATUS        mandatory
	DESCRIPTION
	     " The availability status of a plug-in unit is described with
	       this attribute.
	       Range of values is:
		  available,
		  failed,
		  degraded,
		  offline,
		  notInstalled,
		  dependency . "
	--DEFAULT next-function-async     fsnPiuEntryNext
	--DEFAULT get-function-async      fsnPiuEntryGet
	::= { xldv11HwPlugInUnitEntry 2 }

     xldv11PiuOperState OBJECT-TYPE
	-- info-LEAF:    xldv11PiuOperState
	-- info-TREE:    xldv11Hwm
	-- info-ACC:     ro
	-- info-SYNTAX:  Xldv11OperState
	-- info-VALUE:   enabled(1), disabled(2)
	-- info-COMMENT: Indicates whether or not the PIU is
	-- info-COMMENT: capable of performing its normal functions.
	-- info-ROU:     GET db
	-- info-IMPL:    V1.0->
	-- info-VERCTRL: -
	SYNTAX        Xldv11OperState
	ACCESS        read-only
	STATUS        mandatory
	DESCRIPTION
	     " This attribute indicates whether or not the plug-in unit is
	       capable of performing its normal functions.
	       The range of values is: enabled(1), disabled(2). "
	--DEFAULT next-function-async     fsnPiuEntryNext
	--DEFAULT get-function-async      fsnPiuEntryGet
	::= { xldv11HwPlugInUnitEntry 3 }

     xldv11PiuType OBJECT-TYPE
	-- info-LEAF:    xldv11PiuType
	-- info-TREE:    xldv11Hwm
	-- info-ACC:     ro
	-- info-SYNTAX:  DisplayString (SIZE (0..20))
	-- info-VALUE:   'LU155:OM', 'UPL:A', 'POSUA:2P', 'POSUA:2I',
	-- info-VALUE:   'CMU:A', 'SUAD:16',
	-- info-VALUE:   'LTAD:1P', 'LTAD:2P', 'LTAD:2I',
	-- info-VALUE:   'NTAD:1P', 'NTAD:1I', 'LI25:1', 
	-- info-VALUE:   XLDV1.1U->: 'LUPON:O', 'LI25:2', 'LIETH25:11', 'PSAM:A'
	-- info-VALUE:   XLDV1.2->: 'LU155:OL', 'CMU:B', 'SUAD:16T',
	-- info-VALUE:   XLDV1.3->: 'CMU:C', 'LU155:C', 'LUDSX3:C' , 'CPE'
	-- info-VALUE:   XLDV1.x->: 'POSUV:4', 'SUVD:4', 'NTVD:1'
	-- info-COMMENT: Identifies the type of a PIU.
	-- info-ROU:     GET db
	-- info-IMPL:    V1.0:rw V1.1U->
	-- info-VERCTRL: -
	SYNTAX        DisplayString (SIZE (0..20))
	ACCESS        read-only 
	STATUS        mandatory
	DESCRIPTION
	     " Identifier for the type of a plug-in unit. It is writeable
	       only in state locked. This attribute may be any printable
	       string(e.g. CLEI code).
	       See description of xldv11EqhPiuTypes for possible string values."
	--DEFAULT next-function-async     fsnPiuEntryNext
	--DEFAULT get-function-async      fsnPiuEntryGet
	::= { xldv11HwPlugInUnitEntry 4 }

     xldv11PiuAlarmSeverityIndex OBJECT-TYPE
	-- info-LEAF:    xldv11PiuAlarmSeverityIndex
	-- info-TREE:    xldv11Hwm
	-- info-ACC:     rw
	-- info-SYNTAX:  Xldv11AlmSevProfileIndex
	-- info-VALUE:   1..40
	-- info-COMMENT: Pointer to the instance of the alarm severity
	-- info-COMMENT: profile that contains the severity assignments
	-- info-COMMENT: for the alarms reported by this PIU.
	-- info-ROU:     GET db  SET db
	-- info-IMPL:    V1.0:ro->V1.3H V1.3A->
	-- info-VERCTRL: GET db SET blocked
	SYNTAX        Xldv11AlmSevProfileIndex
	ACCESS        read-write
	STATUS        mandatory
	DESCRIPTION
	     " It is a pointer to the instance of the alarm severity
	       assignment profile managed entity that contains the severity
	       assignments for the alarms reported by this managed entity.
	       Default is 1. "
	--DEFAULT test-function-async     fsnPiuEntryTest
	--DEFAULT next-function-async     fsnPiuEntryNext
	--DEFAULT set-function-async      fsnPiuEntrySet
	--DEFAULT get-function-async      fsnPiuEntryGet
	::= { xldv11HwPlugInUnitEntry 5 }

     xldv11PiuAlarmFilteringIndex OBJECT-TYPE
	-- info-LEAF:    xldv11PiuAlarmFilteringIndex
	-- info-TREE:    xldv11Hwm
	-- info-ACC:     ro
	-- info-SYNTAX:  Xldv11AlmFiltProfileIndex
	-- info-VALUE:   1..40
	-- info-COMMENT: Pointer to the instance of the alarm filtering profile
	-- info-COMMENT: that contains the filtering assignments for the alarms
	-- info-COMMENT: reported by this PIU.
	-- info-ROU:     GET db
	-- info-IMPL:    V1.3A->
	-- info-VERCTRL: -
	SYNTAX        Xldv11AlmFiltProfileIndex
	ACCESS        read-only
	STATUS        mandatory
	DESCRIPTION
	     " It is a pointer to the instance of the alarm filtering
	       assignment profile managed entity that contains the filtering
	       assignments for the alarms reported by this managed entity.
	       (Not implemented) . "
	--DEFAULT next-function-async     fsnPiuEntryNext
	--DEFAULT get-function-async      fsnPiuEntryGet
	::= { xldv11HwPlugInUnitEntry 6 }

    xldv11PiuUpgradeResult OBJECT-TYPE
       -- info-LEAF:    xldv11PiuUpgradeResult
       -- info-TREE:    xldv11Swm
       -- info-ACC:     ro
       -- info-SYNTAX:  Xldv11ControlReq
       -- info-VALUE:   SW upgrade task states :
       -- info-VALUE:   sutInitialized,sutToDo
       -- info-VALUE:   sutStarted,sutCrashed 
       -- info-VALUE:   sutFtpDone,sutDone
       -- info-VALUE:   sutReadyForReset,sutObsolete
       -- info-VALUE:   Result values at end of task :
       -- info-VALUE:   sucUpgrStartRequest,
       -- info-VALUE:   sucActivateLoad, sucReadSAPSContentFile,
       -- info-VALUE:   sucGetSwVersions, sucUpgrMissParameter,
       -- info-VALUE:   sucGetSwVersionsFailed
       -- info-VALUE:   sucOk ,sucNotOk
       -- info-VALUE:   sucDbAccessFailed ,sucPiuUnlocked
       -- info-VALUE:   sucTransmissionError ,sucWrongSwVersion
       -- info-VALUE:   sucUnitTypeMismatch
       -- info-VALUE:   sucFtpTransError ,sucFtpCrcError
       -- info-VALUE:   sucSwHwMismatch ,sucUpgrWrongAvState
       -- info-VALUE:   sucFepromCopyFault ,sucUpdateDescFileFailed
       -- info-VALUE:   sucFtpServerNoteAvailable ,sucFtpSendError
       -- info-VALUE:   sucDbBackupFault ,sucUpgradeComplete
       -- info-VALUE:   sucUpgradeNotComplete
       -- info-VALUE:   sucUpgrTaskCreationFault
       -- info-VALUE:   sucUpgrDbAccessFault
       -- info-COMMENT: specifies the SW upgrade task state and
       -- info-COMMENT: the result at the end of loading 
       -- info-COMMENT: the plugged unit
       -- info-ROU:     GET db
       -- info-IMPL:    V1.3N->
       -- info-VERCTRL: -
       SYNTAX        Xldv11ControlReq
       ACCESS        read-only
       STATUS        mandatory
       DESCRIPTION
          " This read-only attribute informs about the state of SW upgarde 
            task and the result at the end of loading 
            the current plug-in unit."
	--DEFAULT next-function-async     fsnPiuEntryNext
	--DEFAULT get-function-async      fsnPiuEntryGet
	::= { xldv11HwPlugInUnitEntry 7 }

     -- --------------------------------------------------------------
     --                    HW Unit control subgroup
     -- --------------------------------------------------------------

     xldv11HwuControl OBJECT IDENTIFIER ::= { xldv11Hwm 7 }
	-- info-NODE:    xldv11HwuControl
	-- info-TREE:    xldv11Hwm
	-- info-ACC:     nac
	-- info-COMMENT: This managed entity manages the creation and
	-- info-COMMENT: deletion of Hw Units.
	-- info-IMPL:    V1.1U->

     -- This managed entity manages the creation and deletion of Hw Units.
     -- This feature replaces the XLDV1.0 feature of directly overwriting 
     -- the XldPiuType.
     -- The table xldv11HwPlugInUnitTable replaces the table
     -- xldHwPlugInUnitTable.
     -- The only difference is that the attribute xldv11PiuType is now read-only.
     -- In XLDV1.1U only creation of a HW unit is allowed. The tables
     -- xldv11HwUnitTable, and xldv11IfTable are static and are automatically
     -- updated.
     -- In XLDV1.1 entries of these tables are created or deleted when HW units
     -- are created or deleted.


     xldv11HwuControlReq OBJECT-TYPE
	-- info-LEAF:    xldv11HwuControlReq
	-- info-TREE:    xldv11Hwm
	-- info-ACC:     rw
	-- info-SYNTAX:  Xldv11ControlReq
	-- info-VALUE:   createHwUnit(160)(command), deleteHwUnit(161)(command)
	-- info-VALUE:   noRequest(1), commExecStarted(5), paramFaulty(11)
	-- info-VALUE:   requestBusy(V1.3N->),setDataFailed(V1.3N->),
	-- info-VALUE:   aswTimeout(V1.3N->),
	-- info-COMMENT: Identifies the control command for creating or
	-- info-COMMENT: deleting a HW unit.
	-- info-ROU:     GET db  SET hm
	-- info-IMPL:    V1.1U->
	-- info-VERCTRL: -
	SYNTAX        Xldv11ControlReq
	ACCESS        read-write
	STATUS        mandatory
	DESCRIPTION
	     " This attribute identifies the control command for creating or
	       deleting a HW unit. In XldV1.1U only createHwUnit allowed.
	       Range of values is:
		  noRequest,
		  createHwUnit,
		  deleteHwUnit,
		  commExecStarted,
		  paramFaulty .
	       Notifications : xldv11TrHwuControl when command is finished. "
	--DEFAULT test-function-async     fsnHwuTest
	--DEFAULT next-function-async     fsnHwuNext
	--DEFAULT set-function-async      fsnHwuSet
	--DEFAULT get-function-async      fsnHwuGet
	::= { xldv11HwuControl 1 }

     xldv11HwuControlStatus OBJECT-TYPE
	-- info-LEAF:    xldv11HwuControlStatus
	-- info-TREE:    xldv11Hwm
	-- info-ACC:     ro
	-- info-SYNTAX:  Xldv11ControlStatus
	-- info-VALUE:   requestIdle(1), requestBusy(2), requestPassed(3)
	-- info-VALUE:   requestFailed(4)
	-- info-COMMENT: Indicates the status of a control request.
	-- info-ROU:     GET db
	-- info-IMPL:    V1.1U->
	-- info-VERCTRL: -
	SYNTAX        Xldv11ControlStatus
	ACCESS        read-only
	STATUS        mandatory
	DESCRIPTION
	     " This attribute indicates the status of a control request.
	       Range of values is:
		  requestIdle,
		  requestBusy,
		  requestPassed,
		  requestFailed . "
	--DEFAULT next-function-async     fsnHwuNext
	--DEFAULT get-function-async      fsnHwuGet
	::= { xldv11HwuControl 2 }

     xldv11HwuUnitType OBJECT-TYPE
	-- info-LEAF:    xldv11HwuUnitType
	-- info-TREE:    xldv11Hwm
	-- info-ACC:     rw
	-- info-SYNTAX:  Xldv11HwUnitType
	-- info-VALUE:   equipment(V1.x->), equipmentHolder(V1.x->), plugInUnit(V1.1U->)
	-- info-COMMENT: Identifies the type of hardware unit which should be created.
	-- info-COMMENT: The following entities can not be created: atmNe,
	-- info-COMMENT: equipment (ONU), equipmentHolder (basic shelf)
	-- info-COMMENT: equipmentHolder (slot1..slot32 of basic shelf)
	-- info-ROU:     GET db SET db
	-- info-IMPL:    V1.1U->
	-- info-VERCTRL: -
	SYNTAX        Xldv11HwUnitType
	ACCESS        read-write
	STATUS        mandatory
	DESCRIPTION
	     " Identifies the type of hardware unit which should be created.
	       The values are equipment, equipmentHolder and plugInUnit . "
	--DEFAULT test-function-async     fsnHwuTest
	--DEFAULT next-function-async     fsnHwuNext
	--DEFAULT set-function-async      fsnHwuSet
	--DEFAULT get-function-async      fsnHwuGet
	::= { xldv11HwuControl 3 }

     xldv11HwuEquType OBJECT-TYPE
    -- info-LEAF:    xldv11HwuEquType
    -- info-TREE:    xldv11Hwm
    -- info-ACC:     ro
    -- info-SYNTAX:  OCTET STRING ( SIZE (0..21) )
    -- info-VALUE:   ntAdsl, ntVdsl, ntCpe
    -- info-COMMENT: Indicates the equipment which should be created.
    -- info-ROU:     GET db  SET db
    -- info-IMPL:    V1.x->
    -- info-VERCTRL: -
    SYNTAX        OCTET STRING ( SIZE (0..21) )
    ACCESS        read-only
    STATUS        mandatory
    DESCRIPTION
	 " Indicates the equipment which should be created
	   (ntAdsl or ntVdsl or ntCpe). Default is \0."
    --DEFAULT next-function-async     fsnHwuNext
    --DEFAULT get-function-async      fsnHwuGet
    ::= { xldv11HwuControl 4 }

 xldv11HwuEqhType OBJECT-TYPE
    -- info-LEAF:    xldv11HwuEqhType
    -- info-TREE:    xldv11Hwm
    -- info-ACC:     ro
    -- info-SYNTAX:  Xldv11EqhType
    -- info-VALUE:   extendedShelf(4), ntAdslShelf(5), ntVdslShelf(6)
    -- info-VALUE:   cpeShelf(7)
    -- info-COMMENT: Indicates the equipmentHolder which should be created.
    -- info-ROU:     GET db  SET db
    -- info-IMPL:    V1.x->
    -- info-VERCTRL: -
    SYNTAX        Xldv11EqhType
    ACCESS        read-only
    STATUS        mandatory
    DESCRIPTION
	 " Indicates the equipmentHolder which should be created (extendedShelf or
	   ntAdslShelf or ntVdslShelf) ."
    --DEFAULT get-function-async      fsnHwuGet
    --DEFAULT next-function-async     fsnHwuNext
    ::= { xldv11HwuControl 5 }

 xldv11HwuPiuType OBJECT-TYPE
    -- info-LEAF:    xldv11HwuPiuType
    -- info-TREE:    xldv11Hwm
    -- info-ACC:     rw
    -- info-SYNTAX:  OCTET STRING ( SIZE (0..200) )
    -- info-VALUE:   any PIU, but not CMU* and LU*
    -- info-COMMENT: Identifies the type of a plug-in unit which should be created.
    -- info-ROU:     GET db  SET db
    -- info-IMPL:    V1.1U->
    -- info-VERCTRL: -
    SYNTAX        OCTET STRING ( SIZE (0..200) ) 
    ACCESS        read-write
    STATUS        mandatory
    DESCRIPTION
	 " Identifies the type of a plug-in unit which should be created.
	   The following entities cannot be created or deleted : LU*, and CMU .
	   Default is \0."
    --DEFAULT test-function-async     fsnHwuTest
    --DEFAULT next-function-async     fsnHwuNext
    --DEFAULT set-function-async      fsnHwuSet
    --DEFAULT get-function-async      fsnHwuGet
    ::= { xldv11HwuControl 6 }

 xldv11HwuContainingUnitIndex OBJECT-TYPE
    -- info-LEAF:    xldv11HwuContainingUnitIndex
    -- info-TREE:    xldv11Hwm
    -- info-ACC:     rw
    -- info-SYNTAX:  Unsigned16
    -- info-VALUE:   0..65535
    -- info-COMMENT: Identifies the managed entity which contains the created unit.
    -- info-ROU:     GET db  SET db
    -- info-IMPL:    V1.1U->
    -- info-VERCTRL: -
    SYNTAX        Unsigned16
    ACCESS        read-write
    STATUS        mandatory
    DESCRIPTION
	 " Identifies the managed entity which contains the created unit . "
    --DEFAULT test-function-async     fsnHwuTest
    --DEFAULT next-function-async     fsnHwuNext
    --DEFAULT set-function-async      fsnHwuSet
    --DEFAULT get-function-async      fsnHwuGet
    ::= { xldv11HwuControl 7 }

 xldv11HwuContainedUnitAddr OBJECT-TYPE
    -- info-LEAF:    xldv11HwuContainedUnitAddr
    -- info-TREE:    xldv11Hwm
    -- info-ACC:     rw
    -- info-SYNTAX:  INTEGER
    -- info-VALUE:   1..512
    -- info-COMMENT: Identifies the index of the contained unit, which should
    -- info-COMMENT: be created, within the containing unit .
    -- info-ROU:     GET db  SET db
    -- info-IMPL:    V1.1U->
    -- info-VERCTRL: -
    SYNTAX        INTEGER (1..512)
    ACCESS        read-write
    STATUS        mandatory
    DESCRIPTION
	 " Identifies the index of the contained unit within the containing unit . "
    --DEFAULT test-function-async     fsnHwuTest
    --DEFAULT next-function-async     fsnHwuNext
    --DEFAULT set-function-async      fsnHwuSet
    --DEFAULT get-function-async      fsnHwuGet
    ::= { xldv11HwuControl 8 }

 xldv11HwuUnitIndex OBJECT-TYPE
    -- info-LEAF:    xldv11HwuUnitIndex
    -- info-TREE:    xldv11Hwm
    -- info-ACC:     rw
    -- info-SYNTAX:  Unsigned16
    -- info-VALUE:   0..65535
    -- info-COMMENT: Identifies the HW Unit which should be deleted.
    -- info-ROU:     GET db  SET db
    -- info-IMPL:    V1.x->
    -- info-VERCTRL: -
    SYNTAX        Unsigned16
    ACCESS        read-write
    STATUS        mandatory
    DESCRIPTION
	 " Identifies the HW Unit which should be deleted . "
    --DEFAULT test-function-async     fsnHwuTest
    --DEFAULT next-function-async     fsnHwuNext
    --DEFAULT set-function-async      fsnHwuSet
    --DEFAULT get-function-async      fsnHwuGet
    ::= { xldv11HwuControl 9 }

 xldv11HwuControlTimer OBJECT-TYPE
    -- info-LEAF:    xldv11HwuControlTimer
    -- info-TREE:    xldv11Hwm
    -- info-ACC:     ro
    -- info-SYNTAX:  Integer32
    -- info-VALUE:   -2147483648..2147483647
    -- info-COMMENT: Maximum wait time for TMN-OS when a create or delete
    -- info-COMMENT: HW unit request cannot be executed immediately.
    -- info-ROU:     GET db
    -- info-IMPL:    V1.1U->
    -- info-VERCTRL: -
    SYNTAX        Integer32
    ACCESS        read-only
    STATUS        mandatory
    DESCRIPTION
	  " The maximum wait time for the manager when a create
	    or delete HW unit request cannot be executed
	    immediately ( value commExecStarted in GetResponse
	    for xldv11HwuControlReq ).
	    The manager reads this value from the ONU. "
    --DEFAULT next-function-async     fsnHwuNext
    --DEFAULT get-function-async      fsnHwuGet
    ::= { xldv11HwuControl 10 }

     xldv11HwuControlReqResult OBJECT-TYPE
	-- info-LEAF:    xldv11HwuControlReqResult
	-- info-TREE:    xldv11Hwm
	-- info-ACC:     ro
	-- info-SYNTAX:  Xldv11ControlReq
	-- info-VALUE:   see xldv11HwuControlReq
	-- info-COMMENT: specifies the result of user command
	-- info-ROU:     GET db
	-- info-IMPL:    V1.3N->
	-- info-VERCTRL: -
	SYNTAX        Xldv11ControlReq
	ACCESS        read-only
	STATUS        mandatory
	DESCRIPTION
	     " This read-only attribute informs about the result of 
	     the last user command."
	--DEFAULT next-function-async     fsnHwuNext
	--DEFAULT get-function-async      fsnHwuGet
    ::= { xldv11HwuControl 11 }

     xldv11HwuControlTimeStamp OBJECT-TYPE
        -- info-LEAF:    xldv11HwuControlTimeStamp
        -- info-TREE:    xldv11Hwu
        -- info-ACC:     ro
        -- info-SYNTAX:  TimeTicks
        -- info-VALUE:   0..2Giga
        -- info-COMMENT: specifies the time stamp in seconds
        -- info-COMMENT: of the last command
        -- info-COMMENT: (end of command)
        -- info-ROU:     GET db
	-- info-IMPL:    V1.3N->
        -- info-VERCTRL: -
        SYNTAX        TimeTicks
        ACCESS        read-only
        STATUS        mandatory
        DESCRIPTION
           " This read-only attribute informs about the time stamp
             of the last command (end of command)."
        --DEFAULT next-function-async     fsnHwuNext
        --DEFAULT get-function-async      fsnHwuGet
        ::= { xldv11HwuControl 12 }

 -- --------------------------------------------------------------
 --                 HWM NT control subgroup (XLDV1.1)
 -- --------------------------------------------------------------

 xldv11HwnControl OBJECT IDENTIFIER ::= { xldv11Hwm 8 }
    -- info-NODE:    xldv11HwnControl
    -- info-TREE:    xldv11Hwm
    -- info-ACC:     nac
    -- info-COMMENT: This managed entity manages the connection or
    -- info-COMMENT: disconnection of a NT to or from a port of
    -- info-COMMENT: a LTAD* or SUVD*
    -- info-IMPL:    V1.x

 --
 -- This managed entity manages the commands to connect    
 -- or disconnect a NT to or from a certain port of LTAD* or a SUVD:4.
 -- Valid for XLDV1.x
 --

 xldv11HwnControlReq OBJECT-TYPE
    -- info-LEAF:    xldv11HwnControlReq
    -- info-TREE:    xldv11Hwm
    -- info-ACC:     rw
    -- info-SYNTAX:  Xldv11ControlReq
    -- info-VALUE:   connectNt(170)(command), disconnectNt(171)(command)  
    -- info-VALUE:   noRequest(1),
    -- info-VALUE:   ntPiuIndexNotAvail(172),ntPiuIndexNotValid(173)
    -- info-VALUE:   ntPiuPortNotAvail(174),ntPiuPortAlreadyConnected(175)
    -- info-VALUE:   onuPiuIndexNotAvail(176),onuPiuIndexNotValid(177)
    -- info-VALUE:   onuPiuPortNotAvail(178),onuPiuPortAlreadyConnected(179)
    -- info-VALUE:   requestBusy(V1.3N->),setDataFailed(V1.3N->),
    -- info-VALUE:   aswTimeout(V1.3N->),
    -- info-COMMENT: Identifies the control command for connecting 
    -- info-COMMENT: or disconnecting an NT.
    -- info-ROU:     GET db  SET hm
    -- info-IMPL:    V1.x
    -- info-VERCTRL: V1.1U->
    SYNTAX        Xldv11ControlReq
    ACCESS        read-write
    STATUS        mandatory
    DESCRIPTION
	 " This attribute identifies the control command to connect     
	   or disconnect a NT to or from a port of LTAD* or a SDVB:4.
	   Range of values is:
	      noRequest,
	      connectNt (command),
	      disconnectNt (command),
	      ntPiuIndexNotAvail,
	      ntPiuIndexNotValid,
	      ntPiuPortNotAvail,
	      ntPiuPortAlreadyConnected,
	      onuPiuIndexNotAvail,
	      onuPiuIndexNotValid,
	      onuPiuPortAlreadyConnected,
	      onuPiuPortNotAvail .  
	   Notifications : none ."
    --DEFAULT test-function-async     fsnHwnTest
    --DEFAULT next-function-async     fsnHwnNext
    --DEFAULT set-function-async      fsnHwnSet
    --DEFAULT get-function-async      fsnHwnGet
    ::= { xldv11HwnControl 1 }

 xldv11HwnControlStatus OBJECT-TYPE
    -- info-LEAF:    xldv11HwnControlStatus
    -- info-TREE:    xldv11Hwm
    -- info-ACC:     ro
    -- info-SYNTAX:  Xldv11ControlStatus
    -- info-VALUE:   requestIdle(1), requestBusy(2), requestPassed(3)
    -- info-VALUE:   requestFailed(4)
    -- info-COMMENT: Indicates the status of a control request.
    -- info-ROU:     GET db
    -- info-IMPL:    V1.x
    -- info-VERCTRL: V1.1U->
    SYNTAX        Xldv11ControlStatus
    ACCESS        read-only
    STATUS        mandatory
    DESCRIPTION
	 " This attribute indicates the status of a control request.
	   Range of values is:
	   requestIdle,
	   requestBusy,
	   requestPassed,
	   requestFailed . "
    --DEFAULT next-function-async     fsnHwnNext
    --DEFAULT get-function-async      fsnHwnGet
    ::= { xldv11HwnControl 2 }

 xldv11HwnNtPiuIndex OBJECT-TYPE
    -- info-LEAF:    xldv11HwnNtPiuIndex
    -- info-TREE:    xldv11Hwm
    -- info-ACC:     rw
    -- info-SYNTAX:  Unsigned16
    -- info-VALUE:   -
    -- info-COMMENT: HwUnitIndex of the Piu within the NT.
    -- info-ROU:     GET db SET db
    -- info-IMPL:    V1.x
    -- info-VERCTRL: V1.1U->
    SYNTAX        Unsigned16
    ACCESS        read-write
    STATUS        mandatory
    DESCRIPTION
	 " This attribute identifies the plugin unit which terminates
	   the ADSL or VDSL line within the NT ."
    --DEFAULT test-function-async     fsnHwnTest
    --DEFAULT next-function-async     fsnHwnNext
    --DEFAULT set-function-async      fsnHwnSet
    --DEFAULT get-function-async      fsnHwnGet
    ::= { xldv11HwnControl 3 }

 xldv11HwnNtPiuPort OBJECT-TYPE
    -- info-LEAF:    xldv11HwnNtPiuPort
    -- info-TREE:    xldv11Hwm
    -- info-ACC:     rw
    -- info-SYNTAX:  INTEGER
    -- info-VALUE:   1..4
    -- info-COMMENT: HwUnitIndex of the Piu within the NT.
    -- info-ROU:     GET db SET db
    -- info-IMPL:    V1.x
    -- info-VERCTRL: V1.1U->
    SYNTAX        INTEGER (1..4)
    ACCESS        read-write
    STATUS        mandatory
    DESCRIPTION
	 " This attribute identifies the port of the plugin unit 
	   which terminates the ADSL or VDSL line within the NT ."
    --DEFAULT test-function-async     fsnHwnTest
    --DEFAULT next-function-async     fsnHwnNext
    --DEFAULT set-function-async      fsnHwnSet
    --DEFAULT get-function-async      fsnHwnGet
    ::= { xldv11HwnControl 4 }

 xldv11HwnOnuPiuIndex OBJECT-TYPE
    -- info-LEAF:    xldv11HwnOnuPiuIndex
    -- info-TREE:    xldv11Hwm
    -- info-ACC:     rw
    -- info-SYNTAX:  Unsigned16
    -- info-VALUE:   -
    -- info-COMMENT: HwUnitIndex of the Piu within the ONU.
    -- info-ROU:     GET db SET db
    -- info-IMPL:    V1.x
    -- info-VERCTRL: V1.1U->
    SYNTAX        Unsigned16
    ACCESS        read-write
    STATUS        mandatory
    DESCRIPTION
	 " This attribute identifies the plugin unit which terminates
	   the ADSL or VDSL line within the ONU ."
    --DEFAULT test-function-async     fsnHwnTest
    --DEFAULT next-function-async     fsnHwnNext
    --DEFAULT set-function-async      fsnHwnSet
    --DEFAULT get-function-async      fsnHwnGet
    ::= { xldv11HwnControl 5 }

 xldv11HwnOnuPiuPort OBJECT-TYPE
    -- info-LEAF:    xldv11HwnOnuPiuPort
    -- info-TREE:    xldv11Hwm
    -- info-ACC:     rw
    -- info-SYNTAX:  INTEGER
    -- info-VALUE:   1..4
    -- info-COMMENT: port of Piu within the ONU.
    -- info-ROU:     GET db SET db
    -- info-IMPL:    V1.x
    -- info-VERCTRL: V1.1U->
    SYNTAX        INTEGER (1..4)
    ACCESS        read-write
    STATUS        mandatory
    DESCRIPTION
	 " This attribute identifies the port of the plugin unit which
	   terminates the ADSL or VDSL line within the ONU ."
    --DEFAULT test-function-async     fsnHwnTest
    --DEFAULT next-function-async     fsnHwnNext
    --DEFAULT set-function-async      fsnHwnSet
    --DEFAULT get-function-async      fsnHwnGet
    ::= { xldv11HwnControl 6 }

     xldv11HwnControlReqResult OBJECT-TYPE
	-- info-LEAF:    xldv11HwnControlReqResult
	-- info-TREE:    xldv11Hwm
	-- info-ACC:     ro
	-- info-SYNTAX:  Xldv11ControlReq
	-- info-VALUE:   see xldv11HwnControlReq
	-- info-COMMENT: specifies the result of user command
	-- info-ROU:     GET db
	-- info-IMPL:    V1.x
	-- info-VERCTRL: -
	SYNTAX        Xldv11ControlReq
	ACCESS        read-only
	STATUS        mandatory
	DESCRIPTION
	     " This read-only attribute informs about the result of 
	     the last user command."
	--DEFAULT next-function-async     fsnHwnNext
	--DEFAULT get-function-async      fsnHwnGet
    ::= { xldv11HwnControl 7 }

 -- --------------------------------------------------------------
 --              Remote Inventory subgroup (XLDV1.1)
 -- --------------------------------------------------------------

 xldv11RemoteInventory OBJECT IDENTIFIER ::= { xldv11Hwm 9 }
    -- info-NODE:    xldv11RemoteInventory
    -- info-TREE:    xldv11Hwm
    -- info-ACC:     nac
    -- info-COMMENT: This managed entity manages the remote 
    -- info-COMMENT: inventory data either of a single board
    -- info-COMMENT: or all currently plugged boards
    -- info-IMPL:    V1.x

 xldv11RiControlReq OBJECT-TYPE
    -- info-LEAF:    xldv11RiControlReq
    -- info-TREE:    xldv11Hwm
    -- info-ACC:     rw
    -- info-SYNTAX:  Xldv11ControlReq
    -- info-VALUE:   riSingleBoard(205)(command),riAllData(206)(command)
    -- info-VALUE:   noRequest(1),
    -- info-VALUE:   commExecStarted(5),paramFaulty(11)
    -- info-VALUE:   requestBusy(V1.3N->),setDataFailed(V1.3N->),
    -- info-VALUE:   aswTimeout(V1.3N->),
    -- info-COMMENT: Identifies the control command for retrieve 
    -- info-COMMENT: of remote inventory data
    -- info-ROU:     GET db  SET hm
    -- info-IMPL:    V1.x
    -- info-VERCTRL: V1.1U..V1.3B: GET db SET blocked
    SYNTAX        Xldv11ControlReq
    ACCESS        read-write
    STATUS        mandatory
    DESCRIPTION
	 " This attribute identifies the control commands to get
	   information about the boards currently plugged into the
	   XLD system. On a request from TMN-OS or LCT, the  
	   Product Identification Data (PID) and location data 
	   (rack, row, slot) of either a single board or of 
	   all boards plugged are collected. These data are sent to 
	   to a file at the FTP server.
	   Range of values is:
	      noRequest,
	      riSingleBoard(command),
	      riAllData(command),
	      commExecStarted,
	      paramFaulty .
	   Notifications : xldv11TrRemInvReady when the remote inventory data
	   have been collected and the resulting file has been sent to the
	   FTP server. "
    --DEFAULT test-function-async     fsnRiTest
    --DEFAULT next-function-async     fsnRiNext
    --DEFAULT set-function-async      fsnRiSet
    --DEFAULT get-function-async      fsnRiGet
    ::= { xldv11RemoteInventory 1 }

 xldv11RiControlStatus OBJECT-TYPE
    -- info-LEAF:    xldv11RiControlStatus
    -- info-TREE:    xldv11Hwm
    -- info-ACC:     ro
    -- info-SYNTAX:  Xldv11ControlStatus
    -- info-VALUE:   requestIdle(1), requestBusy(2), requestPassed(3)
    -- info-VALUE:   requestFailed(4)
    -- info-COMMENT: Indicates the status of a control request.
    -- info-ROU:     GET db
    -- info-IMPL:    V1.x
    -- info-VERCTRL: V1.1U->
    SYNTAX        Xldv11ControlStatus
    ACCESS        read-only
    STATUS        mandatory
    DESCRIPTION
	 " This attribute indicates the status of a control request.
	   Range of values is:
	      requestIdle,
	      requestBusy,
	      requestPassed,
	      requestFailed . "
    --DEFAULT next-function-async     fsnRiNext
    --DEFAULT get-function-async      fsnRiGet
    ::= { xldv11RemoteInventory 2 }

 xldv11RiControlTimer OBJECT-TYPE
    -- info-LEAF:    xldv11RiControlTimer
    -- info-TREE:    xldv11Hwm
    -- info-ACC:     ro
    -- info-SYNTAX:  Integer32
    -- info-VALUE:   -2147483648..2147483647
    -- info-COMMENT: Maximum wait time for TMN-OS when a remote
    -- info-COMMENT: inventory retrieve cannot be executed immediately.
    -- info-ROU:     GET db
    -- info-IMPL:    V1.x
    -- info-VERCTRL: V1.1U->
    SYNTAX        Integer32
    ACCESS        read-only
    STATUS        mandatory
    DESCRIPTION
	  " The maximum wait time for the manager when remote
	    inventory data retrieve request cannot be executed
	    immediately (value commExecStarted in the GetResponse 
	    for xldv11RiControlReq). 
	    The manager reads this value from the ONU.
	    The end of request indicates the trap xldv11TrRemInvReady ."
    --DEFAULT next-function-async     fsnRiNext
    --DEFAULT get-function-async      fsnRiGet
    ::= { xldv11RemoteInventory 3 }

 xldv11RiResultFilePath OBJECT-TYPE
    -- info-LEAF:    xldv11RiResultFilePath
    -- info-TREE:    xldv11Hwm
    -- info-ACC:     rw
    -- info-SYNTAX:  OCTET STRING ( SIZE (0..200) )
    -- info-VALUE:   -
    -- info-COMMENT: destination path at FTP server where file with 
    -- info-COMMENT: remote inventory data should be stored
    -- info-ROU:     GET db  SET db
    -- info-IMPL:    V1.x
    -- info-VERCTRL: V1.1U->
    SYNTAX        OCTET STRING ( SIZE (0..200) )
    ACCESS        read-write
    STATUS        mandatory
    DESCRIPTION
	 " This attribute contains the path where the file containing
	   the remote inventory data should be stored on the 
	   FTP server. If this attribute does not contain a valid path
	   name no remote inventory data will be transmitted ."
    --DEFAULT test-function-async     fsnRiTest
    --DEFAULT next-function-async     fsnRiNext
    --DEFAULT set-function-async      fsnRiSet
    --DEFAULT get-function-async      fsnRiGet
    ::= { xldv11RemoteInventory 4 }

 xldv11RiHwUnitIndex OBJECT-TYPE
    -- info-LEAF:    xldv11RiHwUnitIndex 
    -- info-TREE:    xldv11Hwm
    -- info-ACC:     rw
    -- info-SYNTAX:  Unsigned16
    -- info-VALUE:   -
    -- info-COMMENT: HwUnitIndex of the Piu.in case of a retrieve.
    -- info-COMMENT: remote inventory data.of a single board.
    -- info-ROU:     GET db SET db
    -- info-IMPL:    V1.x
    -- info-VERCTRL: V1.1U->
    SYNTAX        Unsigned16
    ACCESS        read-write
    STATUS        mandatory
    DESCRIPTION
	  " This attribute specifies the HwUnitIndex of the requested board
	   if remote inventory data for a single board are requested."
    --DEFAULT test-function-async     fsnRiTest
    --DEFAULT next-function-async     fsnRiNext
    --DEFAULT set-function-async      fsnRiSet
    --DEFAULT get-function-async      fsnRiGet
    ::= { xldv11RemoteInventory 5 }

 xldv11RiControlReqResult OBJECT-TYPE
    -- info-LEAF:    xldv11RiControlReqResult
    -- info-TREE:    xldv11Hwm
    -- info-ACC:     ro
    -- info-SYNTAX:  Xldv11ControlReq
    -- info-VALUE:   see xldv11RiControlReq
    -- info-COMMENT: specifies the result of user command
    -- info-ROU:     GET db
    -- info-IMPL:    V1.x
    -- info-VERCTRL: -
    SYNTAX        Xldv11ControlReq
    ACCESS        read-only
    STATUS        mandatory
    DESCRIPTION
	  " This read-only attribute informs about the result of 
	     the last user command."
   --DEFAULT next-function-async     fsnRiNext
   --DEFAULT get-function-async      fsnRiGet
    ::= { xldv11RemoteInventory 6 }

  xldv11RiControlTimeStamp OBJECT-TYPE
     -- info-LEAF:    xldv11RiControlTimeStamp
     -- info-TREE:    xldv11Hwu
     -- info-ACC:     ro
     -- info-SYNTAX:  TimeTicks
     -- info-VALUE:   0..2Giga
     -- info-COMMENT: specifies the time stamp in seconds
     -- info-COMMENT: of the last command
     -- info-COMMENT: (end of command)
     -- info-ROU:     GET db
     -- info-IMPL:    V1.3N->
     -- info-VERCTRL: -
     SYNTAX        TimeTicks
     ACCESS        read-only
     STATUS        mandatory
     DESCRIPTION
        " This read-only attribute informs about the time stamp
        of the last command (end of command)."
   --DEFAULT next-function-async     fsnRiNext
   --DEFAULT get-function-async      fsnRiGet
    ::= { xldv11RemoteInventory 7 }

 -- --------------------------------------------------------------
 --            Hardware POSU Table (XLDV1.2B)
 -- --------------------------------------------------------------

 -- This table is needed for XLDV1.3H which is based on XLDV1.2B SW
 -- and new hardware. With XLDV1.3H a new type of configurable POSU
 -- exists which can be configured operating either in mode POTS or ISDN.
 --
 xldv11HwPosuTable OBJECT-TYPE
    -- info-NODE:    xldv11HwPosuTable
    -- info-TREE:    xldv11Hwm
    -- info-ACC:     nac
    -- info-SYNTAX:  SEQUENCE OF Xldv11HwPosuEntry
    -- info-COMMENT: Table for plugin units of type POSU*
    -- info-IMPL:    V1.3H->
    SYNTAX        SEQUENCE OF Xldv11HwPosuEntry
    ACCESS        not-accessible
    STATUS        mandatory
    DESCRIPTION
	 " This table augments the entries of xldv11HwPluginUnitTable
	 with attributes for POSUs.  "
    ::= { xldv11Hwm 10 }

 xldv11HwPosuEntry OBJECT-TYPE
    -- info-NODE:    xldv11HwPosuEntry
    -- info-TREE:    xldv11Hwm
    -- info-INDEX:   xldv11HwUnitIndex
    -- info-ACC:     nac
    -- info-SYNTAX:  Xldv11HwPosuEntry
    -- info-COMMENT: entry of Xldv11HwPosuTable
    -- info-IMPL:    V1.3H->
    SYNTAX        Xldv11HwPosuEntry
    ACCESS        not-accessible
    STATUS        mandatory
    DESCRIPTION
	 " Each entry is used to specify additional attributes for POSUs. 
	  Notifications : none. "
    INDEX { xldv11HwUnitIndex }
    ::= { xldv11HwPosuTable 1 }

 Xldv11HwPosuEntry ::=
    SEQUENCE { xldv11PosModePort1      INTEGER,
	       xldv11PosModePort2      INTEGER
	       }

 xldv11PosModePort1 OBJECT-TYPE
    -- info-LEAF:    xldv11PosModePort1
    -- info-TREE:    xldv11Hwm
    -- info-ACC:     rw
    -- info-SYNTAX:  INTEGER
    -- info-VALUE:   1 (pots), 2 (isdn = default ) 
    -- info-COMMENT: operating mode of POSU port1
    -- info-ROU:     GET db  SET hm 
    -- info-IMPL:    V1.3H->
    -- info-VERCTRL: V1.1U..V1.2B:GET db SET blocked
    SYNTAX        INTEGER { pots (1),
			    isdn (2) }
    ACCESS        read-write
    STATUS        mandatory
    DESCRIPTION
	 " This attribute is used to select the operating mode.
	   Default mode is isdn."
    --DEFAULT test-function-async     fsnPosEntryTest
    --DEFAULT next-function-async     fsnPosEntryNext
    --DEFAULT set-function-async      fsnPosEntrySet
    --DEFAULT get-function-async      fsnPosEntryGet
    ::= { xldv11HwPosuEntry 1 }

 xldv11PosModePort2 OBJECT-TYPE
    -- info-LEAF:    xldv11PosModePort2
    -- info-TREE:    xldv11Hwm
    -- info-ACC:     rw
    -- info-SYNTAX:  INTEGER
    -- info-VALUE:   1 (pots), 2 (isdn = default )
    -- info-COMMENT: operating mode of POSU port2
    -- info-ROU:     GET db  SET hm 
    -- info-IMPL:    V1.3H->
    -- info-VERCTRL: V1.1U..V1.2B:GET db SET blocked
    SYNTAX        INTEGER { pots (1),
			    isdn (2) }
    ACCESS        read-write
    STATUS        mandatory
    DESCRIPTION
	 " This attribute is used to select the operating mode.
	   Default mode is isdn."
    --DEFAULT test-function-async     fsnPosEntryTest
    --DEFAULT next-function-async     fsnPosEntryNext
    --DEFAULT set-function-async      fsnPosEntrySet
    --DEFAULT get-function-async      fsnPosEntryGet
    ::= { xldv11HwPosuEntry 2 }
 -- ==============================================================
 --    T r u n k / L i n e   M a i n t e n a n c e   G r o u p
 -- ==============================================================

 -- --------------------------------------------------------------
 --                   TLM Interface Table
 -- --------------------------------------------------------------

 xldv11IfTable OBJECT-TYPE
    -- info-NODE:    xldv11IfTable
    -- info-TREE:    xldv11Tlm
    -- info-ACC:     nac
    -- info-SYNTAX:  SEQUENCE OF Xldv11IfEntry
    -- info-COMMENT: Table of Tlm interface objects.
    -- info-COMMENT: PPTP's or tca.
    -- info-IMPL:    V1.0->
    SYNTAX        SEQUENCE OF Xldv11IfEntry
    ACCESS        not-accessible
    STATUS        mandatory
    DESCRIPTION
	 " The TLM interface table. "
    ::= { xldv11Tlm 1 }

 xldv11IfEntry OBJECT-TYPE
    -- info-NODE:    xldv11IfEntry
    -- info-TREE:    xldv11Tlm
    -- info-INDEX:   xldv11IfIndex
    -- info-ACC:     nac
    -- info-SYNTAX:  Xldv11IfEntry
    -- info-COMMENT: Entry of Tlm interface table.
    -- info-IMPL:    V1.0->
    SYNTAX        Xldv11IfEntry
    ACCESS        not-accessible
    STATUS        mandatory
    DESCRIPTION
	 " An entry in the TLM interface table. Each entry represents
	   either a physical path termination point (PPTP) or a
	   TC adaptor (tcAdaptor).
	   Notifications :
	   alarm traps when a fault has been detected or cleared.
	   xldv11TrStateChangeOper,
	   xldv11TrStateChangeAdmin."
    INDEX         { xldv11IfIndex }
    ::= { xldv11IfTable 1 }

 Xldv11IfEntry ::=
      SEQUENCE { xldv11IfIndex                Unsigned16,
		 xldv11IfType                 Xldv11IfType,
		 xldv11IfLineIndex            Unsigned16,
		 xldv11IfHwUnitIndex          Unsigned16,
		 xldv11IfHwPortId             INTEGER,
		 xldv11IfConnectivityIndex    Unsigned16,
		 xldv11IfOperState            Xldv11OperState,
		 xldv11IfAdminState           Xldv11AdminState,
		 xldv11IfAlarmState           Xldv11AlarmState,
		 xldv11IfAlarmSeverityIndex   Xldv11AlmSevProfileIndex,
		 xldv11IfAlarmFilteringIndex  Xldv11AlmFiltProfileIndex }

 xldv11IfIndex OBJECT-TYPE
    -- info-LEAF:    xldv11IfIndex 
    -- info-TREE:    xldv11Tlm
    -- info-ACC:     ro
    -- info-SYNTAX:  Unsigned16
    -- info-VALUE:   -
    -- info-COMMENT: Index to identify a TLM interface.
    -- info-ROU:     GET db
    -- info-IMPL:    V1.0->
    -- info-VERCTRL: -
    SYNTAX        Unsigned16
    ACCESS        read-only
    STATUS        mandatory
    DESCRIPTION
	 " A unique number to identify a TLM interface in the ATM NE. "
    --DEFAULT next-function-async     fsnIfEntryNext
    --DEFAULT get-function-async      fsnIfEntryGet
    ::= { xldv11IfEntry 1 }

 xldv11IfType OBJECT-TYPE
    -- info-LEAF:    xldv11IfType 
    -- info-TREE:    xldv11Tlm
    -- info-ACC:     ro
    -- info-SYNTAX:  Xldv11IfType
    -- info-VALUE:   s1n(1),s1f(2),adc(3),adr(4)
    -- info-VALUE:   ibm(5),tca(6),pon(7)(V1.1U)
    -- info-VALUE:   vdc(8)(V1.x),vdr(9)(V1.x->)
    -- info-VALUE:   eth(10)(V1.U->)
    -- info-VALUE:   d3n(11)(V1.3A->),d3f(12)(V1.3A->)
    -- info-VALUE:   e3n(13)(V1.3A->), e3f(14)(V1.3A->)
    -- info-VALUE:   s3n(15)(V1.2A->), s3f(16)(V1.2A->)
    -- info-COMMENT: type of TLM interface.
    -- info-ROU:     GET db
    -- info-IMPL:    V1.0->
    -- info-VERCTRL: -
    SYNTAX        Xldv11IfType
    ACCESS        read-only
    STATUS        mandatory
    DESCRIPTION
	 " The type of a TLM interface as it is extended for the XLD Version.
	   Possible values for PPTP: 
	   XLDV1.0  : s1n, s1f, adc, adr, ibm
	   XLDV1.1U : pon
	   XLDV1.1L : eth
	   XLDV1.2A : s3n, s3f
	   XLDV1.3A : d3n, d3f, e3n, e3f, vdc, vdr
	   XLDV1.x  : vdc, vdr
	   Possible values for tcAdaptor:
	   All versions :  tca. "
    --DEFAULT next-function-async     fsnIfEntryNext
    --DEFAULT get-function-async      fsnIfEntryGet
    ::= { xldv11IfEntry 2 }

 xldv11IfLineIndex OBJECT-TYPE
    -- info-LEAF:    xldv11IfLineIndex
    -- info-TREE:    xldv11Tlm
    -- info-ACC:     ro
    -- info-SYNTAX:  Unsigned16
    -- info-VALUE:   -
    -- info-COMMENT: line index
    -- info-ROU:     GET db
    -- info-IMPL:    V1.0->
    -- info-VERCTRL: -
    SYNTAX        Unsigned16
    ACCESS        read-only
    STATUS        mandatory
    DESCRIPTION
	 " A unique value to identify interfaces belonging to the
	   same line. "
    --DEFAULT next-function-async     fsnIfEntryNext
    --DEFAULT get-function-async      fsnIfEntryGet
    ::= { xldv11IfEntry 3 }

 xldv11IfHwUnitIndex OBJECT-TYPE
    -- info-LEAF:    xldv11IfHwUnitIndex 
    -- info-TREE:    xldv11Tlm
    -- info-ACC:     ro
    -- info-SYNTAX:  Unsigned16
    -- info-VALUE:   -
    -- info-COMMENT: HwUnitIndex of the dependent Piu.
    -- info-ROU:     GET db
    -- info-IMPL:    V1.0->
    -- info-VERCTRL: -
    SYNTAX        Unsigned16
    ACCESS        read-only
    STATUS        mandatory
    DESCRIPTION
	 " The index to identify the hardware unit the physical
	   path/TC layer terminates on."
    --DEFAULT next-function-async     fsnIfEntryNext
    --DEFAULT get-function-async      fsnIfEntryGet
    ::= { xldv11IfEntry 4 }

 xldv11IfHwPortId OBJECT-TYPE
    -- info-LEAF:    xldv11IfHwPortId 
    -- info-TREE:    xldv11Tlm
    -- info-ACC:     ro
    -- info-SYNTAX:  INTEGER
    -- info-VALUE:   0..255
    -- info-COMMENT: Port number .
    -- info-ROU:     GET db
    -- info-IMPL:    V1.0->
    -- info-VERCTRL: -
    SYNTAX        INTEGER (0..255)
    ACCESS        read-only
    STATUS        mandatory
    DESCRIPTION
	 " This attribute identifies the port number on the HW unit
	   the physical path/TC layer terminates on. "
    --DEFAULT next-function-async     fsnIfEntryNext
    --DEFAULT get-function-async      fsnIfEntryGet
    ::= { xldv11IfEntry 5 }

 xldv11IfConnectivityIndex OBJECT-TYPE
    -- info-LEAF:    xldv11ConnectivityIndex
    -- info-TREE:    xldv11Tlm
    -- info-ACC:     ro
    -- info-SYNTAX:  Unsigned16
    -- info-VALUE:   -
    -- info-COMMENT: for pptp the associated HwPortId.
    -- info-COMMENT: for tca the associated PPTP.
    -- info-ROU:     GET db
    -- info-IMPL:    V1.0->
    -- info-VERCTRL: -
    SYNTAX        Unsigned16 
    ACCESS        read-only
    STATUS        mandatory
    DESCRIPTION
	 " For PPTP it is the associated HW port ID. For TC adaptor
	   it is the IfIndex of the PPTP the TC adaptor is connected to. "
    --DEFAULT next-function-async     fsnIfEntryNext
    --DEFAULT get-function-async      fsnIfEntryGet
    ::= { xldv11IfEntry 6 }

 xldv11IfOperState OBJECT-TYPE
    -- info-LEAF:    xldv11IfOperState
    -- info-TREE:    xldv11Tlm
    -- info-ACC:     ro
    -- info-SYNTAX:  Xldv11OperState
    -- info-VALUE:   enabled(1), disabled(2)
    -- info-COMMENT: Indicates whether or not the Tlm interface is
    -- info-COMMENT: capable of performing its normal functions.
    -- info-ROU:     GET db
    -- info-IMPL:    V1.0->
    -- info-VERCTRL: -
    SYNTAX        Xldv11OperState
    ACCESS        read-only
    STATUS        mandatory
    DESCRIPTION
	 " The operational state of this unit.
	   The range of values is: enabled, disabled. "
    --DEFAULT next-function-async     fsnIfEntryNext
    --DEFAULT get-function-async      fsnIfEntryGet
    ::= { xldv11IfEntry 7 }

 xldv11IfAdminState OBJECT-TYPE
    -- info-LEAF:    xldv11IfAdminState
    -- info-TREE:    xldv11Tlm
    -- info-ACC:     rw
    -- info-SYNTAX:  Xldv11AdminState
    -- info-VALUE:   unlocked(1), locked(2)
    -- info-COMMENT: This attribute is used to activate (unlock) and
    -- info-COMMENT: deactivate (lock) the Tlm interface.
    -- info-ROU:     GET db  SET tm
    -- info-IMPL:    V1.0->
    -- info-VERCTRL: -
    SYNTAX        Xldv11AdminState
    ACCESS        read-write
    STATUS        mandatory
    DESCRIPTION
	 " Activates(unlock) or deactivates(lock) the functionality
	   of this managed entity. It must be locked before physical
	   looptest has been started. The attribute is not
	   configurable during looptest.
	   For PPTP of type s1n, s3n, e3n, d3n, pon and tcAdaptors connected
	   to s1n, s3n, e3n, d3n or pon the value is only lockable from a
	   connected LCT. A request to lock these attributes will be
	   rejected.
	   The range of values is: unlocked, locked. "
    --DEFAULT test-function-async     fsnIfEntryTest
    --DEFAULT next-function-async     fsnIfEntryNext
    --DEFAULT set-function-async      fsnIfEntrySet
    --DEFAULT get-function-async      fsnIfEntryGet
    ::= { xldv11IfEntry 8 }

 xldv11IfAlarmState OBJECT-TYPE
    -- info-LEAF:    xldv11IfAlarmState
    -- info-TREE:    xldv11Tlm
    -- info-ACC:     ro
    -- info-SYNTAX:  Xldv11AlarmState
    -- info-VALUE:   noAlarm(0), hpEBER(1), hpUNEQ(2), lcd(3)
    -- info-VALUE:   lof(4), lop(5), los(6)
    -- info-VALUE:   msAIS(7), msEBER(8), msRDI(9), msSD(10)
    -- info-VALUE:   pAIS(11), pRDI(12), rsEBER(13), slm(14)
    -- info-VALUE:   tim(15), actFault(16), hiBER(43), lomf(102)
    -- info-VALUE:   fail(103), lps(104), xmissionErr(105), ais(114)
    -- info-VALUE:   rdi(115), plcpLof(116), plcpRDI(117), internalFault(123)
    -- info-VALUE:   immMNR(132), lpr(133), lol(134)
    -- info-COMMENT: alarm state. default noAlarm.
    -- info-ROU:     GET db
    -- info-IMPL:    V1.0->
    -- info-VERCTRL: -
    SYNTAX        Xldv11AlarmState
    ACCESS        read-only
    STATUS        mandatory
    DESCRIPTION
	 " The nature of an alarm. Values see type definition of Xldv11AlarmState. "
    --DEFAULT next-function-async     fsnIfEntryNext
    --DEFAULT get-function-async      fsnIfEntryGet
    ::= { xldv11IfEntry 9 }

 xldv11IfAlarmSeverityIndex OBJECT-TYPE
    -- info-LEAF:    xldv11IfAlarmSeverityIndex
    -- info-TREE:    xldv11Tlm
    -- info-ACC:     rw
    -- info-SYNTAX:  Xldv11AlmSevProfileIndex
    -- info-VALUE:   1..40
    -- info-COMMENT: Pointer to the instance of the alarm severity
    -- info-COMMENT: profile that contains the severity assignments
    -- info-COMMENT: for the alarms reported by this Tlm interface.
    -- info-ROU:     GET db  SET db
    -- info-IMPL:    V1.0:ro->V1.3H V1.3A->
    -- info-VERCTRL: GET db SET blocked
    SYNTAX        Xldv11AlmSevProfileIndex
    ACCESS        read-write
    STATUS        mandatory
    DESCRIPTION
	 " The index of the associated entry in the alarm severity
	   profile table. These entries contain the severity
	   assigments for the alarms reported by this managed
	   entity.
	   The range of values is:
	   1,.., 10: for possible pre-configured alarm severity
		     profiles XLD V1.0 .
	   Default is 1."
    --DEFAULT test-function-async     fsnIfEntryTest
    --DEFAULT next-function-async     fsnIfEntryNext
    --DEFAULT set-function-async      fsnIfEntrySet
    --DEFAULT get-function-async      fsnIfEntryGet
    ::= { xldv11IfEntry 10 }

 xldv11IfAlarmFilteringIndex OBJECT-TYPE
    -- info-LEAF:    xldv11IfAlarmFilteringIndex
    -- info-TREE:    xldv11Tlm
    -- info-ACC:     ro
    -- info-SYNTAX:  Xldv11AlmFiltProfileIndex
    -- info-VALUE:   1..40
    -- info-COMMENT: Pointer to the instance of the alarm filtering profile
    -- info-COMMENT: that contains the filtering assignments for the alarms
    -- info-COMMENT: reported by this Tlm interface.
    -- info-ROU:     GET db
    -- info-IMPL:    V1.3A->
    -- info-VERCTRL: -
    SYNTAX        Xldv11AlmFiltProfileIndex
    ACCESS        read-only
    STATUS        mandatory
    DESCRIPTION
	 " It is a pointer to the instance of the alarm filtering
	   assignment profile managed entity that contains the filtering
	   assignments for the alarms reported by this managed entity.
	   (Not implemented in XLD V1.0 and XLD V1.1U). "
    --DEFAULT next-function-async     fsnIfEntryNext
    --DEFAULT get-function-async      fsnIfEntryGet
    ::= { xldv11IfEntry 11 }


 -- --------------------------------------------------------------
 --              TLM ADSL central control subgroup
 -- --------------------------------------------------------------
 --
 -- This managed entity manages the control commands 
 -- for the ADSL central link.
 -- Valid for XLDV1.1U
 --

 xldv11AdcControl OBJECT IDENTIFIER ::= { xldv11Tlm 2 }
    -- info-NODE:    xldv11AdcControl
    -- info-TREE:    xldv11Tlm
    -- info-ACC:     nac
    -- info-COMMENT: ADSL control object
    -- info-IMPL:    V1.1U->

 xldv11AdcCtrlControlReq OBJECT-TYPE
    -- info-LEAF:    xldv11AdcCtrlControlReq
    -- info-TREE:    xldv11Tlm
    -- info-ACC:     rw
    -- info-SYNTAX:  Xldv11AdcCtrlControlReq
    -- info-COMMENT: ADSL control request object
    -- info-VALUE:   activateData(190)(command)
    -- info-VALUE:   noRequest(1), paramFaulty(11)
    -- info-VALUE:   wrongAdminState(240)
    -- info-VALUE:   resourceProblemUpstream(193), resourceProblemDownstream(194)
    -- info-VALUE:   vpProblemUpstream(195), vpProblemDownstream(196)
    -- info-VALUE:   bandwidthUpstreamWarning(197), bandwidthDownstreamWarning(198)
    -- info-VALUE:   mbsUpstreamWarning(199), mbsDownstreamWarning(200).
    -- info-VALUE:   requestBusy(V1.3N->),setDataFailed(V1.3N->),
    -- info-VALUE:   aswTimeout(V1.3N->),
    -- info-ROU:     GET db SET tm  
    -- info-IMPL:    V1.1U->
    -- info-VERCTRL: -
    SYNTAX        Xldv11ControlReq
    ACCESS        read-write
    STATUS        mandatory
    DESCRIPTION
	 " This attribute marks the command to activate a configured set of
	   data (command: activateData), which includes minimum and maximum
	   bandwidth in upstream and downstream direction, latency and
	   margin.
	   Negative return values result from faulty parameters from the
	   agent (response: paramFaulty), no more bandwidth available in the
	   ONU (response: resourceProblem) or bandwidth used by a certain VP
	   (response: vpProblem).
	   Range of values is:
	      noRequest ,
	      activeData,
	      paramFaulty,
	      wrongAdminState,
	      resourceProblemUpstream,
	      resourceProblemDownstream,
	      vpProblemUpstream,
	      vpProblemDownstream,
	      bandwidthUpstreamWarning,
	      bandwidthDownstreamWarning,
	      mbsUpstreamWarning,
	      mbsDownstreamWarning.
	   Notifications : none "
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 1 }

 xldv11AdcCtrlControlStatus OBJECT-TYPE
    -- info-LEAF:    xldv11AdcCtrlControlStatus
    -- info-TREE:    xldv11Tlm
    -- info-ACC:     ro
    -- info-SYNTAX:  Xldv11ControlStatus
    -- info-VALUE:   requestIdle(1), requestBusy(2), requestPassed(3)
    -- info-VALUE:   requestFailed(4)
    -- info-COMMENT: Indicates the status of a control request.
    -- info-ROU:     GET db
    -- info-IMPL:    V1.1U->
    -- info-VERCTRL: -
    SYNTAX        Xldv11ControlStatus
    ACCESS        read-only
    STATUS        mandatory
    DESCRIPTION
	 " This attribute indicates the status of a control request.
	   Range of values is:
	      requestIdle,
	      requestBusy,
	      requestPassed,
	      requestFailed . "
    --DEFAULT next-function-async     fsnAdcCtrlNext
    --DEFAULT get-function-async      fsnAdcCtrlGet
    ::= { xldv11AdcControl 2 }

 xldv11AdcCtrlIfIndex OBJECT-TYPE
    -- info-LEAF:    xldv11AdcCtrlIfIndex 
    -- info-TREE:    xldv11Tlm
    -- info-ACC:     rw
    -- info-SYNTAX:  Unsigned16
    -- info-VALUE:   -
    -- info-COMMENT: Index to identify a adc PPTP.
    -- info-ROU:     GET db SET db
    -- info-IMPL:    V1.1U->
    -- info-VERCTRL: -
    SYNTAX        Unsigned16
    ACCESS        read-write
    STATUS        mandatory
    DESCRIPTION
	 " It is the relevant interface index of the ADSL central PPTP."
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 3 }

 xldv11AdcCtrlMinRateDn OBJECT-TYPE
    -- info-LEAF:    xldv11AdcCtrlMinRateDn
    -- info-TREE:    xldv11Tlm
    -- info-ACC:     rw
    -- info-SYNTAX:  Xldv11AdslDataRateDown
    -- info-VALUE:   1..255 (default 1)
        -- info-VALUE:   kbps32Cps75  (   1 ),
        -- info-VALUE:   kbps64Cps150 (   2 ),
        -- info-VALUE:   kbps96Cps226 (   3 ),
        -- info-VALUE:   kbps128Cps301(   4 ),
        -- info-VALUE:   kbps160Cps377(   5 ),
        -- info-VALUE:   kbps192Cps452(   6 ),
        -- info-VALUE:   kbps224Cps528(   7 ),
        -- info-VALUE:   kbps256Cps603(   8 ),
        -- info-VALUE:   kbps288Cps679(   9 ),
        -- info-VALUE:   kbps320Cps754(  10 ),
        -- info-VALUE:   kbps352Cps830(  11 ),
        -- info-VALUE:   kbps384Cps905(  12 ),
        -- info-VALUE:   kbps416Cps981(  13 ),
        -- info-VALUE:   kbps448Cps1056(  14 ),
        -- info-VALUE:   kbps480Cps1132(  15 ),
        -- info-VALUE:   kbps512Cps1207(  16 ),
        -- info-VALUE:   kbps544Cps1283(  17 ),
        -- info-VALUE:   kbps576Cps1358(  18 ),
        -- info-VALUE:   kbps608Cps1433(  19 ),
        -- info-VALUE:   kbps640Cps1509(  20 ),
        -- info-VALUE:   kbps672Cps1584(  21 ),
        -- info-VALUE:   kbps704Cps1660(  22 ),
        -- info-VALUE:   kbps736Cps1735(  23 ),
        -- info-VALUE:   kbps768Cps1811(  24 ),
        -- info-VALUE:   kbps800Cps1886(  25 ),
        -- info-VALUE:   kbps832Cps1962(  26 ),
        -- info-VALUE:   kbps864Cps2037(  27 ),
        -- info-VALUE:   kbps896Cps2113(  28 ),
        -- info-VALUE:   kbps928Cps2188(  29 ),
        -- info-VALUE:   kbps960Cps2264(  30 ),
        -- info-VALUE:   kbps992Cps2339(  31 ),
        -- info-VALUE:   kbps1024Cps2415(  32 ),
        -- info-VALUE:   kbps1056Cps2490(  33 ),
        -- info-VALUE:   kbps1088Cps2566(  34 ),
        -- info-VALUE:   kbps1120Cps2641(  35 ),
        -- info-VALUE:   kbps1152Cps2716(  36 ),
        -- info-VALUE:   kbps1184Cps2792(  37 ),
        -- info-VALUE:   kbps1216Cps2867(  38 ),
        -- info-VALUE:   kbps1248Cps2943(  39 ),
        -- info-VALUE:   kbps1280Cps3018(  40 ),
        -- info-VALUE:   kbps1312Cps3094(  41 ),
        -- info-VALUE:   kbps1344Cps3169(  42 ),
        -- info-VALUE:   kbps1376Cps3245(  43 ),
        -- info-VALUE:   kbps1408Cps3320(  44 ),
        -- info-VALUE:   kbps1440Cps3396(  45 ),
        -- info-VALUE:   kbps1472Cps3471(  46 ),
        -- info-VALUE:   kbps1504Cps3547(  47 ),
        -- info-VALUE:   kbps1536Cps3622(  48 ),
        -- info-VALUE:   kbps1568Cps3698(  49 ),
        -- info-VALUE:   kbps1600Cps3773(  50 ),
        -- info-VALUE:   kbps1632Cps3849(  51 ),
        -- info-VALUE:   kbps1664Cps3924(  52 ),
        -- info-VALUE:   kbps1696Cps4000(  53 ),
        -- info-VALUE:   kbps1728Cps4075(  54 ),
        -- info-VALUE:   kbps1760Cps4150(  55 ),
        -- info-VALUE:   kbps1792Cps4226(  56 ),
        -- info-VALUE:   kbps1824Cps4301(  57 ),
        -- info-VALUE:   kbps1856Cps4377(  58 ),
        -- info-VALUE:   kbps1888Cps4452(  59 ),
        -- info-VALUE:   kbps1920Cps4528(  60 ),
        -- info-VALUE:   kbps1952Cps4603(  61 ),
        -- info-VALUE:   kbps1984Cps4679(  62 ),
        -- info-VALUE:   kbps2016Cps4754(  63 ),
        -- info-VALUE:   kbps2048Cps4830(  64 ),
        -- info-VALUE:   kbps2080Cps4905(  65 ),
        -- info-VALUE:   kbps2112Cps4981(  66 ),
        -- info-VALUE:   kbps2144Cps5056(  67 ),
        -- info-VALUE:   kbps2176Cps5132(  68 ),
        -- info-VALUE:   kbps2208Cps5207(  69 ),
        -- info-VALUE:   kbps2240Cps5283(  70 ),
        -- info-VALUE:   kbps2272Cps5358(  71 ),
        -- info-VALUE:   kbps2304Cps5433(  72 ),
        -- info-VALUE:   kbps2336Cps5509(  73 ),
        -- info-VALUE:   kbps2368Cps5584(  74 ),
        -- info-VALUE:   kbps2400Cps5660(  75 ),
        -- info-VALUE:   kbps2432Cps5735(  76 ),
        -- info-VALUE:   kbps2464Cps5811(  77 ),
        -- info-VALUE:   kbps2496Cps5886(  78 ),
        -- info-VALUE:   kbps2528Cps5962(  79 ),
        -- info-VALUE:   kbps2560Cps6037(  80 ),
        -- info-VALUE:   kbps2592Cps6113(  81 ),
        -- info-VALUE:   kbps2624Cps6188(  82 ),
        -- info-VALUE:   kbps2656Cps6264(  83 ),
        -- info-VALUE:   kbps2688Cps6339(  84 ),
        -- info-VALUE:   kbps2720Cps6415(  85 ),
        -- info-VALUE:   kbps2752Cps6490(  86 ),
        -- info-VALUE:   kbps2784Cps6566(  87 ),
        -- info-VALUE:   kbps2816Cps6641(  88 ),
        -- info-VALUE:   kbps2848Cps6716(  89 ),
        -- info-VALUE:   kbps2880Cps6792(  90 ),
        -- info-VALUE:   kbps2912Cps6867(  91 ),
        -- info-VALUE:   kbps2944Cps6943(  92 ),
        -- info-VALUE:   kbps2976Cps7018(  93 ),
        -- info-VALUE:   kbps3008Cps7094(  94 ),
        -- info-VALUE:   kbps3040Cps7169(  95 ),
        -- info-VALUE:   kbps3072Cps7245(  96 ),
        -- info-VALUE:   kbps3104Cps7320(  97 ),
        -- info-VALUE:   kbps3136Cps7396(  98 ),
        -- info-VALUE:   kbps3168Cps7471(  99 ),
        -- info-VALUE:   kbps3200Cps7547( 100 ),
        -- info-VALUE:   kbps3232Cps7622( 101 ),
        -- info-VALUE:   kbps3264Cps7698( 102 ),
        -- info-VALUE:   kbps3296Cps7773( 103 ),
        -- info-VALUE:   kbps3328Cps7849( 104 ),
        -- info-VALUE:   kbps3360Cps7924( 105 ),
        -- info-VALUE:   kbps3392Cps8000( 106 ),
        -- info-VALUE:   kbps3424Cps8075( 107 ),
        -- info-VALUE:   kbps3456Cps8150( 108 ),
        -- info-VALUE:   kbps3488Cps8226( 109 ),
        -- info-VALUE:   kbps3520Cps8301( 110 ),
        -- info-VALUE:   kbps3552Cps8377( 111 ),
        -- info-VALUE:   kbps3584Cps8452( 112 ),
        -- info-VALUE:   kbps3616Cps8528( 113 ),
        -- info-VALUE:   kbps3648Cps8603( 114 ),
        -- info-VALUE:   kbps3680Cps8679( 115 ),
        -- info-VALUE:   kbps3712Cps8754( 116 ),
        -- info-VALUE:   kbps3744Cps8830( 117 ),
        -- info-VALUE:   kbps3776Cps8905( 118 ),
        -- info-VALUE:   kbps3808Cps8981( 119 ),
        -- info-VALUE:   kbps3840Cps9056( 120 ),
        -- info-VALUE:   kbps3872Cps9132( 121 ),
        -- info-VALUE:   kbps3904Cps9207( 122 ),
        -- info-VALUE:   kbps3936Cps9283( 123 ),
        -- info-VALUE:   kbps3968Cps9358( 124 ),
        -- info-VALUE:   kbps4000Cps9433( 125 ),
        -- info-VALUE:   kbps4032Cps9509( 126 ),
        -- info-VALUE:   kbps4064Cps9584( 127 ),
        -- info-VALUE:   kbps4096Cps9660( 128 ),
        -- info-VALUE:   kbps4128Cps9735( 129 ),
        -- info-VALUE:   kbps4160Cps9811( 130 ),
        -- info-VALUE:   kbps4192Cps9886( 131 ),
        -- info-VALUE:   kbps4224Cps9962( 132 ),
        -- info-VALUE:   kbps4256Cps10037( 133 ),
        -- info-VALUE:   kbps4288Cps10113( 134 ),
        -- info-VALUE:   kbps4320Cps10188( 135 ),
        -- info-VALUE:   kbps4352Cps10264( 136 ),
        -- info-VALUE:   kbps4384Cps10339( 137 ),
        -- info-VALUE:   kbps4416Cps10415( 138 ),
        -- info-VALUE:   kbps4448Cps10490( 139 ),
        -- info-VALUE:   kbps4480Cps10566( 140 ),
        -- info-VALUE:   kbps4512Cps10641( 141 ),
        -- info-VALUE:   kbps4544Cps10716( 142 ),
        -- info-VALUE:   kbps4576Cps10792( 143 ),
        -- info-VALUE:   kbps4608Cps10867( 144 ),
        -- info-VALUE:   kbps4640Cps10943( 145 ),
        -- info-VALUE:   kbps4672Cps11018( 146 ),
        -- info-VALUE:   kbps4704Cps11094( 147 ),
        -- info-VALUE:   kbps4736Cps11169( 148 ),
        -- info-VALUE:   kbps4768Cps11245( 149 ),
        -- info-VALUE:   kbps4800Cps11320( 150 ),
        -- info-VALUE:   kbps4832Cps11396( 151 ),
        -- info-VALUE:   kbps4864Cps11471( 152 ),
        -- info-VALUE:   kbps4896Cps11547( 153 ),
        -- info-VALUE:   kbps4928Cps11622( 154 ),
        -- info-VALUE:   kbps4960Cps11698( 155 ),
        -- info-VALUE:   kbps4992Cps11773( 156 ),
        -- info-VALUE:   kbps5024Cps11849( 157 ),
        -- info-VALUE:   kbps5056Cps11924( 158 ),
        -- info-VALUE:   kbps5088Cps12000( 159 ),
        -- info-VALUE:   kbps5120Cps12075( 160 ),
        -- info-VALUE:   kbps5152Cps12150( 161 ),
        -- info-VALUE:   kbps5184Cps12226( 162 ),
        -- info-VALUE:   kbps5216Cps12301( 163 ),
        -- info-VALUE:   kbps5248Cps12377( 164 ),
        -- info-VALUE:   kbps5280Cps12452( 165 ),
        -- info-VALUE:   kbps5312Cps12528( 166 ),
        -- info-VALUE:   kbps5344Cps12603( 167 ),
        -- info-VALUE:   kbps5376Cps12679( 168 ),
        -- info-VALUE:   kbps5408Cps12754( 169 ),
        -- info-VALUE:   kbps5440Cps12830( 170 ),
        -- info-VALUE:   kbps5472Cps12905( 171 ),
        -- info-VALUE:   kbps5504Cps12981( 172 ),
        -- info-VALUE:   kbps5536Cps13056( 173 ),
        -- info-VALUE:   kbps5568Cps13132( 174 ),
        -- info-VALUE:   kbps5600Cps13207( 175 ),
        -- info-VALUE:   kbps5632Cps13283( 176 ),
        -- info-VALUE:   kbps5664Cps13358( 177 ),
        -- info-VALUE:   kbps5696Cps13433( 178 ),
        -- info-VALUE:   kbps5728Cps13509( 179 ),
        -- info-VALUE:   kbps5760Cps13584( 180 ),
        -- info-VALUE:   kbps5792Cps13660( 181 ),
        -- info-VALUE:   kbps5824Cps13735( 182 ),
        -- info-VALUE:   kbps5856Cps13811( 183 ),
        -- info-VALUE:   kbps5888Cps13886( 184 ),
        -- info-VALUE:   kbps5920Cps13962( 185 ),
        -- info-VALUE:   kbps5952Cps14037( 186 ),
        -- info-VALUE:   kbps5984Cps14113( 187 ),
        -- info-VALUE:   kbps6016Cps14188( 188 ),
        -- info-VALUE:   kbps6048Cps14264( 189 )
        -- info-VALUE:   kbps6080Cps14339( 190 )
        -- info-VALUE:   kbps6112Cps14415( 191 )
        -- info-VALUE:   kbps6144Cps14490( 192 )
        -- info-VALUE:   kbps6176Cps14566( 193 )
        -- info-VALUE:   kbps6208Cps14641( 194 )
        -- info-VALUE:   kbps6240Cps14716( 195 )
        -- info-VALUE:   kbps6272Cps14792( 196 )
        -- info-VALUE:   kbps6304Cps14867( 197 )
        -- info-VALUE:   kbps6336Cps14943( 198 )
        -- info-VALUE:   kbps6368Cps15018( 199 ),
        -- info-VALUE:   kbps6336Cps14943( 198 )
        -- info-VALUE:   kbps6368Cps15018( 199 ),
        -- info-VALUE:   kbps6400Cps15094( 200 ),
        -- info-VALUE:   kbps6432Cps15169( 201 ),
        -- info-VALUE:   kbps6464Cps15245( 202 ),
        -- info-VALUE:   kbps6496Cps15320( 203 ),
        -- info-VALUE:   kbps6528Cps15396( 204 ),
        -- info-VALUE:   kbps6560Cps15471( 205 ),
        -- info-VALUE:   kbps6592Cps15547( 206 ),
        -- info-VALUE:   kbps6624Cps15622( 207 ),
        -- info-VALUE:   kbps6656Cps15698( 208 ),
        -- info-VALUE:   kbps6688Cps15773( 209 ),
        -- info-VALUE:   kbps6720Cps15849( 210 ),
        -- info-VALUE:   kbps6752Cps15924( 211 ),
        -- info-VALUE:   kbps6784Cps16000( 212 ),
        -- info-VALUE:   kbps6816Cps16075( 213 ),
        -- info-VALUE:   kbps6848Cps16150( 214 ),
        -- info-VALUE:   kbps6880Cps16226( 215 ),
        -- info-VALUE:   kbps6912Cps16301( 216 ),
        -- info-VALUE:   kbps6944Cps16377( 217 ),
        -- info-VALUE:   kbps6976Cps16452( 218 ),
        -- info-VALUE:   kbps7008Cps16528( 219 ),
        -- info-VALUE:   kbps7040Cps16603( 220 ),
        -- info-VALUE:   kbps7072Cps16679( 221 ),
        -- info-VALUE:   kbps7104Cps16754( 222 ),
        -- info-VALUE:   kbps7136Cps16830( 223 ),
        -- info-VALUE:   kbps7168Cps16905( 224 ),
        -- info-VALUE:   kbps7200Cps16981( 225 ),
        -- info-VALUE:   kbps7232Cps17056( 226 ),
        -- info-VALUE:   kbps7264Cps17132( 227 ),
        -- info-VALUE:   kbps7296Cps17207( 228 ),
        -- info-VALUE:   kbps7328Cps17283( 229 ),
        -- info-VALUE:   kbps7360Cps17358( 230 ),
        -- info-VALUE:   kbps7392Cps17433( 231 ),
        -- info-VALUE:   kbps7424Cps17509( 232 ),
        -- info-VALUE:   kbps7456Cps17584( 233 ),
        -- info-VALUE:   kbps7488Cps17660( 234 ),
        -- info-VALUE:   kbps7520Cps17735( 235 ),
        -- info-VALUE:   kbps7552Cps17811( 236 ),
        -- info-VALUE:   kbps7584Cps17886( 237 ),
        -- info-VALUE:   kbps7616Cps17962( 238 ),
        -- info-VALUE:   kbps7648Cps18037( 239 ),
        -- info-VALUE:   kbps7680Cps18113( 240 ),
        -- info-VALUE:   kbps7712Cps18188( 241 ),
        -- info-VALUE:   kbps7744Cps18264( 242 ),
        -- info-VALUE:   kbps7776Cps18339( 243 ),
        -- info-VALUE:   kbps7808Cps18415( 244 ),
        -- info-VALUE:   kbps7840Cps18490( 245 ),
        -- info-VALUE:   kbps7872Cps18566( 246 ),
        -- info-VALUE:   kbps7904Cps18641( 247 ),
        -- info-VALUE:   kbps7936Cps18716( 248 ),
        -- info-VALUE:   kbps7968Cps18792( 249 ),
        -- info-VALUE:   kbps8000Cps18867( 250 ),
        -- info-VALUE:   kbps8032Cps18943( 251 ),
        -- info-VALUE:   kbps8064Cps19018( 252 ),
        -- info-VALUE:   kbps8096Cps19094( 253 ),
        -- info-VALUE:   kbps8128Cps19169( 254 ),
        -- info-VALUE:   kbps8160Cps19245( 255 )
    -- info-COMMENT: desired lower limit of downstream data rate.
    -- info-COMMENT: range 32..8160 Kbit/sec (75..19245 cells/sec). units 32 Kbit/sec.
    -- info-COMMENT: in units 32 Kbit/sec.
    -- info-ROU:     GET db SET db
    -- info-IMPL:    V1.1U->
    -- info-VERCTRL: -
    SYNTAX        Xldv11AdslDataRateDown
    ACCESS        read-write
    STATUS        mandatory
    DESCRIPTION
	 " Desired lower limit of downstream data rate. The data rate can be
	   32..8160 Kbit/sec (75..19245 cells/sec) and is splitted into units of 32 Kbit/sec.
	   Default value is 1."
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 4 }

 xldv11AdcCtrlMinRateUp OBJECT-TYPE
    -- info-LEAF:    xldv11AdcCtrlMinRateUp
    -- info-TREE:    xldv11Tlm
    -- info-ACC:     rw
    -- info-SYNTAX:  Xldv11AdslDataRateUp
    -- info-VALUE:   1..25 (default 1)
    -- info-COMMENT: desired lower limit of upstream data rate.
    -- info-COMMENT: range 32..800 Kbit/sec (75..1868 cells/sec)
    -- info-COMMENT: units 32 Kbit/sec.
    -- info-ROU:     GET db SET db
    -- info-IMPL:    V1.1U->
    -- info-VERCTRL: -
    SYNTAX        Xldv11AdslDataRateUp
    ACCESS        read-write
    STATUS        mandatory
    DESCRIPTION
	 " Desired lower limit of upstream data rate. The data rate can be
	   32..800 Kbit/sec and is splitted into units of 32 Kbit/sec.
	   Default value is 1."
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 5 }

 xldv11AdcCtrlMaxRateDn OBJECT-TYPE
    -- info-LEAF:    xldv11AdcCtrlMaxRateDn
    -- info-TREE:    xldv11Tlm
    -- info-ACC:     rw
    -- info-SYNTAX:  Xldv11AdslDataRateADown
    -- info-VALUE:   1..255 (default 255)
    -- info-COMMENT: desired upper limit of downstream data rate.
    -- info-COMMENT: range 32..8160 Kbit/sec. units 32 Kbit/sec.
    -- info-ROU:     GET db SET db
    -- info-IMPL:    V1.1U->
    -- info-VERCTRL: -
    SYNTAX        Xldv11AdslDataRateDown
    ACCESS        read-write
    STATUS        mandatory
    DESCRIPTION
	 " Desired upper limit of downstream data rate. The data rate can be
	   32..8160 Kbit/sec and is splitted into units of 32 Kbit/sec.
	   Default is 255."
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 6 }

 xldv11AdcCtrlMaxRateUp OBJECT-TYPE
    -- info-LEAF:    xldv11AdcCtrlMaxRateUp
    -- info-TREE:    xldv11Tlm
    -- info-ACC:     rw
    -- info-SYNTAX:  Xldv11AdslDataRateUp
    -- info-VALUE:   1..25 (default 25)
    -- info-COMMENT: desired upper limit of upstream data rate.
    -- info-COMMENT: range 32..800 Kbit/sec. units 32 Kbit/sec.
    -- info-ROU:     GET db SET db
    -- info-IMPL:    V1.1U->
    -- info-VERCTRL: -
    SYNTAX        Xldv11AdslDataRateUp
    ACCESS        read-write
    STATUS        mandatory
    DESCRIPTION
	 " Desired upper limit of upstream data rate. The data rate can be
	   32..800 Kbit/sec and is splitted into units of 32 Kbit/sec.
	   Default is 25."
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 7 }

 xldv11AdcCtrlMarginDn OBJECT-TYPE
    -- info-LEAF:    xldv11AdcCtrlMarginDn
    -- info-TREE:    xldv11Tlm
    -- info-ACC:     rw
    -- info-SYNTAX:  INTEGER
    -- info-VALUE:   0..12 (default 6)
    -- info-COMMENT: desired downstream margin. units dB.
    -- info-ROU:     GET db SET db
    -- info-IMPL:    V1.1U->
    -- info-VERCTRL: -
    SYNTAX        INTEGER (0..12)
    ACCESS        read-write
    STATUS        mandatory
    DESCRIPTION
	 " Desired downstream margin in units of dB .i
	   Default is 6."
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 8 }

 xldv11AdcCtrlMarginUp OBJECT-TYPE
    -- info-LEAF:    xldv11AdcCtrlMarginUp
    -- info-TREE:    xldv11Tlm
    -- info-ACC:     rw
    -- info-SYNTAX:  INTEGER
    -- info-VALUE:   0..12 (default 6)
    -- info-COMMENT: desired upstream margin. units dB.
    -- info-ROU:     GET db SET db
    -- info-IMPL:    V1.1U->
    -- info-VERCTRL: -
    SYNTAX        INTEGER (0..12)
    ACCESS        read-write
    STATUS        mandatory
    DESCRIPTION
	 " Desired upstream margin in units of dB .
	   Default value is 6. "
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 9 }

 xldv11AdcCtrlLatencyDn OBJECT-TYPE
    -- info-LEAF:    xldv11AdcCtrlLatencyDn
    -- info-TREE:    xldv11Tlm
    -- info-ACC:     rw
    -- info-SYNTAX:  Xldv11Latency
    -- info-VALUE:   high, low (default low)
    -- info-COMMENT: desired interleave depth downstream.
    -- info-COMMENT: 0 = low. 1 = high.
    -- info-ROU:     GET db SET db
    -- info-IMPL:    V1.1U->
    -- info-VERCTRL: -
    SYNTAX        Xldv11Latency
    ACCESS        read-write
    STATUS        mandatory
    DESCRIPTION
	 " Desired interleave depth downstream.
	   Range of values is: 0 = latency low (default)
			       1 = latency high . "
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 10 }

 xldv11AdcCtrlLatencyUp OBJECT-TYPE
    -- info-LEAF:    xldv11AdcCtrlLatencyUp
    -- info-TREE:    xldv11Tlm
    -- info-ACC:     rw
    -- info-SYNTAX:  Xldv11Latency
    -- info-VALUE:   high, low (default low)
    -- info-COMMENT: desired interleave depth upstream.
    -- info-COMMENT: 0 = low. 1 = high.
    -- info-ROU:     GET db SET db
    -- info-IMPL:    V1.1U->
    -- info-VERCTRL: -
    SYNTAX        Xldv11Latency
    ACCESS        read-write
    STATUS        mandatory
    DESCRIPTION
	 " Desired interleave depth upstream
	   Range of values is: 0 = latency low (default)
			       1 = latency high . "
    --DEFAULT test-function-async     fsnAdcCtrlTest        
    --DEFAULT next-function-async     fsnAdcCtrlNext
    --DEFAULT set-function-async      fsnAdcCtrlSet
    --DEFAULT get-function-async      fsnAdcCtrlGet
    ::= { xldv11AdcControl 11 }

 xldv11AdcCtrlMinMarginDn OBJECT-TYPE
    -- info-LEAF:    xldv11AdcCtrlMinMarginDn
    -- info-TREE:    xldv11Tlm
    -- info-ACC:     rw
    -- info-SYNTAX:  INTEGER
    -- info-VALUE:   -12..12 (default 0)
    -- info-COMMENT: Threshold for downstream margin
    -- info-COMMENT: units in dB.
    -- info-ROU:     GET db SET db
    -- info-IMPL:    V1.1U->
    -- info-VERCTRL: -
    SYNTAX        INTEGER (-12..12)
    ACCESS        read-write
    STATUS        mandatory
    DESCRIPTION
	 " Threshold for downstream margin when an alarm
	   should be sent in units of dB. Default is 0."
    --DEFAULT test-function-async     fsnAdcCtrlTest
    --DEFAULT next-function-async     fsnAdcCtrlNext
    --DEFAULT set-function-async      fsnAdcCtrlSet
    --DEFAULT get-function-async      fsnAdcCtrlGet
    ::= { xldv11AdcControl 12 }

 xldv11AdcCtrlMinMarginUp OBJECT-TYPE
    -- info-LEAF:    xldv11AdcCtrlMinMarginUp
    -- info-TREE:    xldv11Tlm
    -- info-ACC:     rw
    -- info-SYNTAX:  INTEGER
    -- info-VALUE:   -12..12 (default 0)
    -- info-COMMENT: Threshold for upstream margin
    -- info-COMMENT: units in dB.
    -- info-ROU:     GET db SET db
    -- info-IMPL:    V1.1U->
    -- info-VERCTRL: -
    SYNTAX        INTEGER (-12..12)
    ACCESS        read-write
    STATUS        mandatory
    DESCRIPTION
	 " Threshold for upstream margin when an alarm
	   should be sent in units of dB. Default is 0."
    --DEFAULT test-function-async     fsnAdcCtrlTest
    --DEFAULT next-function-async     fsnAdcCtrlNext
    --DEFAULT set-function-async      fsnAdcCtrlSet
    --DEFAULT get-function-async      fsnAdcCtrlGet
    ::= { xldv11AdcControl 13 }

 xldv11AdcCtrlControlReqResult OBJECT-TYPE
    -- info-LEAF:    xldv11AdcCtrlControlReqResult
    -- info-TREE:    xldv11Tlm
    -- info-ACC:     ro
    -- info-SYNTAX:  Xldv11ControlReq
    -- info-VALUE:   see xldv11AdcCtrlControlReq
    -- info-COMMENT: specifies the result of user command
    -- info-ROU:     GET db
    -- info-IMPL:    V1.3N->
    -- info-VERCTRL: -
    SYNTAX        Xldv11ControlReq
    ACCESS        read-only
    STATUS        mandatory
    DESCRIPTION
	  " This read-only attribute informs about the result of 
	     the last user command."
    --DEFAULT next-function-async     fsnAdcCtrlNext
    --DEFAULT get-function-async      fsnAdcCtrlGet
    ::= { xldv11AdcControl 14 }

  xldv11AdcCtrlControlTimeStamp OBJECT-TYPE
     -- info-LEAF:    xldv11AdcCtrlControlTimeStamp
     -- info-TREE:    xldv11Tlm
     -- info-ACC:     ro
     -- info-SYNTAX:  TimeTicks
     -- info-VALUE:   0..2Giga
     -- info-COMMENT: specifies the time stamp in seconds
     -- info-COMMENT: of the last command
     -- info-COMMENT: (end of command)
     -- info-ROU:     GET db
     -- info-IMPL:    V1.3N->
     -- info-VERCTRL: -
     SYNTAX        TimeTicks
     ACCESS        read-only
     STATUS        mandatory
     DESCRIPTION
        " This read-only attribute informs about the time stamp
        of the last command (end of command)."
    --DEFAULT next-function-async     fsnAdcCtrlNext
    --DEFAULT get-function-async      fsnAdcCtrlGet
    ::= { xldv11AdcControl 15 }


 -- --------------------------------------------------------------
 --                TLM VDSL central control subgroup
 -- --------------------------------------------------------------
 --
 -- This managed entity represents the extension of the VDSL-C interface.
 -- It includes addtional attributes to configure the VDSL link.
 -- Valid for XLDV1.1
 --

 xldv11VdcControl OBJECT IDENTIFIER ::= { xldv11Tlm 3 }
    -- info-NODE:    xldv11VdcControl
    -- info-TREE:    xldv11Tlm
    -- info-ACC:     nac
    -- info-COMMENT: VDSL control object
    -- info-IMPL:    V1.x

 xldv11VdcCtrlControlReq OBJECT-TYPE
    -- info-LEAF:    xldv11VdcCtrlControlReq
    -- info-TREE:    xldv11Tlm
    -- info-ACC:     rw
    -- info-SYNTAX:  Xldv11VdcCtrlControlReq
    -- info-COMMENT: VDSL control request object
    -- info-VALUE:   activateData(190)(command)
    -- info-VALUE:   noRequest(1), paramFaulty(11)
    -- info-VALUE:   resourceProblem(191),vpProblem(192),wrongAdminState(240)
    -- info-VALUE:   requestBusy(V1.3N->),setDataFailed(V1.3N->),
    -- info-VALUE:   aswTimeout(V1.3N->),
    -- info-ROU:     GET db SET tm  
    -- info-IMPL:    V1.x
    -- info-VERCTRL: V1.1U..V1.x: GET db SET blocked
    SYNTAX        Xldv11ControlReq
    ACCESS        read-write
    STATUS        mandatory
    DESCRIPTION
	 " This attribute marks the command to activate a configured set of
	   data (command: activateData), which includes minimum and maximum
	   bandwidth in upstream and downstream direction, latency and some
	   additional modem parameters (power boost, warmstart, VDSL mode,
	   Sleep mode, PSD mask, power adaptation).
	   Negative return values result from faulty parameters from the
	   agent (response: paramFaulty), no more bandwidth available in the
	   ONU (response: resourceProblem) or bandwidth used by a certain VP
	   (response: vpProblem).
	   Range of values is:
	      noRequest,
	      activeData(command),
	      paramFaulty,
	      resourceProblem,
	      vpProblem ,
	      wrongAdminState.
	   Notifications : none ."
    --DEFAULT test-function-async     fsnVdcCtrlTest
    --DEFAULT next-function-async     fsnVdcCtrlNext
    --DEFAULT set-function-async      fsnVdcCtrlSet
    --DEFAULT get-function-async      fsnVdcCtrlGet
    ::= { xldv11VdcControl 1 }

 xldv11VdcCtrlControlStatus OBJECT-TYPE
    -- info-LEAF:    xldv11VdcCtrlControlStatus
    -- info-TREE:    xldv11Tlm
    -- info-ACC:     ro
    -- info-SYNTAX:  Xldv11ControlStatus
    -- info-VALUE:   requestIdle(1), requestBusy(2), requestPassed(3)
    -- info-VALUE:   requestFailed(4)
    -- info-COMMENT: Indicates the status of a control request.
    -- info-ROU:     GET db
    -- info-IMPL:    V1.x
    -- info-VERCTRL: V1.1U->:GET db
    SYNTAX        Xldv11ControlStatus
    ACCESS        read-only
    STATUS        mandatory
    DESCRIPTION
	 " This attribute indicates the status of a control request.
	   Range of values is:
	      requestIdle,
	      requestBusy,
	      requestPassed,
	      requestFailed . "
    --DEFAULT next-function-async     fsnVdcCtrlNext
    --DEFAULT get-function-async      fsnVdcCtrlGet
    ::= { xldv11VdcControl 2 }

 xldv11VdcCtrlIfIndex OBJECT-TYPE
    -- info-LEAF:    xldv11VdcCtrlIfIndex 
    -- info-TREE:    xldv11Tlm
    -- info-ACC:     rw
    -- info-SYNTAX:  Unsigned16
    -- info-VALUE:   -
    -- info-COMMENT: Index to identify a vdc PPTP.
    -- info-ROU:     GET db SET db
    -- info-IMPL:    V1.x
    -- info-VERCTRL: V1.1U->:GET db
    SYNTAX        Unsigned16
    ACCESS        read-write
    STATUS        mandatory
    DESCRIPTION
	 " It is the relevant interface index of the VDSL-C PPTP."
    --DEFAULT test-function-async     fsnVdcCtrlTest
    --DEFAULT next-function-async     fsnVdcCtrlNext
    --DEFAULT set-function-async      fsnVdcCtrlSet
    --DEFAULT get-function-async      fsnVdcCtrlGet
    ::= { xldv11VdcControl 3 }

 xldv11VdcCtrlMinRateDn OBJECT-TYPE
    -- info-LEAF:    xldv11VdcCtrlMinRateDn
    -- info-TREE:    xldv11Tlm
    -- info-ACC:     rw
    -- info-SYNTAX:  Xldv11VdcRateDn
    -- info-VALUE:   (multiples of 810 Kbps)
    -- info-VALUE:   2,4,6,8,12,16
    -- info-VALUE:   24,32,48,64
    -- info-COMMENT: desired lower limit of downstream data rate.
    -- info-ROU:     GET db SET db
    -- info-IMPL:    V1.x
    -- info-VERCTRL: V1.1U->:GET db SET db
    SYNTAX        Xldv11VdcRateDn
    ACCESS        read-write
    STATUS        mandatory
    DESCRIPTION
	 " The lower limit of the downstream data rate. Possible values (in
	   multiples of 810 Kbps): 2, 4, 6, 8, 12, 16, 24, 32, 48, 64 . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 4 }

 xldv11VdcCtrlMinRateUp OBJECT-TYPE
    -- info-LEAF:    xldv11VdcCtrlMinRateUp
    -- info-TREE:    xldv11Tlm
    -- info-ACC:     rw
    -- info-SYNTAX:  Xldv11VdcRateUp
    -- info-VALUE:   (multiples of 810 Kbps)
    -- info-VALUE:   1,2,4,8,12,16
    -- info-COMMENT: desired lower limit of upstream data rate.
    -- info-ROU:     GET db SET db
    -- info-IMPL:    V1.x
    -- info-VERCTRL: V1.1U->:GET db SET db
    SYNTAX        Xldv11VdcRateUp
    ACCESS        read-write
    STATUS        mandatory
    DESCRIPTION
	 " The lower limit of the upstream data rate. Possible values (in
	   multiples of 810 Kbps): 1, 2, 4, 8, 12, 16 . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 5 }

 xldv11VdcCtrlMaxRateDn OBJECT-TYPE
    -- info-LEAF:    xldv11VdcCtrlMaxRateDn
    -- info-TREE:    xldv11Tlm
    -- info-ACC:     rw
    -- info-SYNTAX:  Xldv11VdcRateDn
    -- info-VALUE:   (multiples of 810 Kbps)
    -- info-VALUE:   2,4,6,8,12,16
    -- info-VALUE:   24,32,48,64
    -- info-COMMENT: desired upper limit of downstream data rate.
    -- info-ROU:     GET db SET db
    -- info-IMPL:    V1.x
    -- info-VERCTRL: V1.1U->:GET db SET db
    SYNTAX        Xldv11VdcRateDn
    ACCESS        read-write
    STATUS        mandatory
    DESCRIPTION
	 " The upper limit of the downstream data rate. Possible values (in
	   multiples of 810 Kbps): 2, 4, 6, 8, 12, 16, 24, 32, 48, 64 . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 6 }

 xldv11VdcCtrlMaxRateUp OBJECT-TYPE
    -- info-LEAF:    xldv11VdcCtrlMaxRateUp
    -- info-TREE:    xldv11Tlm
    -- info-ACC:     rw
    -- info-SYNTAX:  Xldv11VdcRateUp
    -- info-VALUE:   (multiples of 810 Kbps)
    -- info-VALUE:   1,2,4,8,12,16
    -- info-COMMENT: desired upper limit of upstream data rate.
    -- info-ROU:     GET db SET db
    -- info-IMPL:    V1.x
    -- info-VERCTRL: V1.1U->:GET db SET db
    SYNTAX        Xldv11VdcRateUp
    ACCESS        read-write
    STATUS        mandatory
    DESCRIPTION
	 " The upper limit of the upstream data rate.Possible values (in
	   multiples of 810 Kbps): 1, 2, 4, 8, 12, 16 . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 7 }

 xldv11VdcCtrlLatencyDn OBJECT-TYPE
    -- info-LEAF:    xldv11VdcCtrlLatencyDn
    -- info-TREE:    xldv11Tlm
    -- info-ACC:     rw
    -- info-SYNTAX:  Xldv11VdcLatencyDn 
    -- info-VALUE:   (delay in msec)
    -- info-VALUE:   0,2,4,8,12,16,20,32
    -- info-COMMENT: interleave depth
    -- info-COMMENT: downstream
    -- info-ROU:     GET db SET db
    -- info-IMPL:    V1.x
    -- info-VERCTRL: V1.1U->:GET db SET db
    SYNTAX        Xldv11VdcLatencyDn
    ACCESS        read-write
    STATUS        mandatory
    DESCRIPTION
	  " Selects interleave depth (i.e. latency time) used for
	    error correction in downstream direction. Possible values (delay
	    in msec): 0, 2, 4, 8, 12, 16, 20, 32 . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 8 }

 xldv11VdcCtrlLatencyUp OBJECT-TYPE
    -- info-LEAF:    xldv11VdcCtrlLatencyUp
    -- info-TREE:    xldv11Tlm
    -- info-ACC:     rw
    -- info-SYNTAX:  Xldv11VdcLatencyUp 
    -- info-VALUE:   (delay in msec)
    -- info-VALUE:   0,2,4,8,10,20
    -- info-COMMENT: interleave depth
    -- info-COMMENT: upstream
    -- info-ROU:     GET db SET db
    -- info-IMPL:    V1.x
    -- info-VERCTRL: V1.1U->:GET db SET db
    SYNTAX        Xldv11VdcLatencyUp
    ACCESS        read-write
    STATUS        mandatory
    DESCRIPTION
	  " Selects interleave depth (i.e. latency time) used for
	    error correction in upstream direction. Possible values (delay
	    in msec): 0, 2, 4, 8, 10, 20 . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 9 }

 xldv11VdcCtrlPowerBoost OBJECT-TYPE
    -- info-LEAF:    xldv11VdcCtrlPowerBoost
    -- info-TREE:    xldv11Tlm
    -- info-ACC:     rw
    -- info-SYNTAX:  Xldv11VdcPowerBoostAdaptationType
    -- info-VALUE:   suEnabled,ntEnabled,bothEnabled,bothDisabled
    -- info-COMMENT: Configured power boost mode
    -- info-ROU:     GET db SET db
    -- info-IMPL:    V1.x
    -- info-VERCTRL: V1.1U->:GET db SET db
    SYNTAX        Xldv11VdcPowerBoostAdaptationType
    ACCESS        read-write
    STATUS        mandatory
    DESCRIPTION
	  " Configured power boost mode.
	    Range of values is:
	       suEnabled,
	       ntEnabled,
	       bothEnabled,
	       bothDisabled . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 10 }

 xldv11VdcCtrlWarmStart OBJECT-TYPE
    -- info-LEAF:    xldv11VdcCtrlWarmStart
    -- info-TREE:    xldv11Tlm
    -- info-ACC:     rw
    -- info-SYNTAX:  Xldv11OperState
    -- info-VALUE:   enabled, disabled
    -- info-COMMENT: Configured warmstart option.
    -- info-ROU:     GET db SET db
    -- info-IMPL:    V1.x
    -- info-VERCTRL: V1.1U->:GET db SET db
    SYNTAX        Xldv11OperState
    ACCESS        read-write
    STATUS        mandatory
    DESCRIPTION
	  " Configured warmstart option.
	    Possible values: enabled, disabled . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 11 }

 xldv11VdcCtrlVdslMode OBJECT-TYPE
    -- info-LEAF:    xldv11VdcCtrlVdslMode
    -- info-TREE:    xldv11Tlm
    -- info-ACC:     rw
    -- info-SYNTAX:  Xldv11VdcVdslMode 
    -- info-VALUE:   adslFriendly, vdslEfficient
    -- info-COMMENT: Configured VDSL mode option
    -- info-ROU:     GET db SET db
    -- info-IMPL:    V1.x
    -- info-VERCTRL: V1.1U->:GET db SET db
    SYNTAX        Xldv11VdcVdslMode
    ACCESS        read-write
    STATUS        mandatory
    DESCRIPTION
	  " Configured VDSL mode option.  Possible values:
	    adslFriendly,
	    vdslEfficient . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 12 }

 xldv11VdcCtrlSleepMode OBJECT-TYPE
    -- info-LEAF:    xldv11VdcCtrlSleepMode
    -- info-TREE:    xldv11Tlm
    -- info-ACC:     rw
    -- info-SYNTAX:  Xldv11OperState
    -- info-VALUE:   enabled, disabled
    -- info-COMMENT: Configured sleep mode option
    -- info-ROU:     GET db SET db
    -- info-IMPL:    V1.x
    -- info-VERCTRL: V1.1U->:GET db SET db
    SYNTAX        Xldv11OperState
    ACCESS        read-write
    STATUS        mandatory
    DESCRIPTION
	  " Configured sleep mode option.
	    Possible values: enabled, disabled . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 13 }

 xldv11VdcCtrlPsdMask OBJECT-TYPE
    -- info-LEAF:    xldv11VdcCtrlPsdMask
    -- info-TREE:    xldv11Tlm
    -- info-ACC:     rw
    -- info-SYNTAX:  Xldv11VdcPsdMask 
    -- info-VALUE:   m1 (strong effect), m2 (weak effect)
    -- info-COMMENT: Configured PSD mask option
    -- info-COMMENT: electro-magnetic interference effects
    -- info-ROU:     GET db SET db
    -- info-IMPL:    V1.x
    -- info-VERCTRL: V1.1U->:GET db SET db
    SYNTAX        Xldv11VdcPsdMask
    ACCESS        read-write
    STATUS        mandatory
    DESCRIPTION
	  " Configured PSD mask option (electro-magnetic interference
	    effects, M1 for strong and M2 for weak effects).
	    Possible values: m1, m2 . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 14 }

 xldv11VdcCtrlPowerAdaptation OBJECT-TYPE
    -- info-LEAF:    xldv11VdcCtrlPowerAdaptation
    -- info-TREE:    xldv11Tlm
    -- info-ACC:     rw
    -- info-SYNTAX:  Xldv11VdcPowerBoostAdaptationType
    -- info-VALUE:   suEnabled,ntEnabled,bothEnabled,bothDisabled
    -- info-COMMENT: Configured power adaptation mode
    -- info-ROU:     GET db SET db
    -- info-IMPL:    V1.x
    -- info-VERCTRL: V1.1U->:GET db SET db
    SYNTAX        Xldv11VdcPowerBoostAdaptationType
    ACCESS        read-write
    STATUS        mandatory
    DESCRIPTION
	  " Configured power adaptation option.
	    Range of values is:
	       suEnabled,
	       ntEnabled,
	       bothEnabled,
	       bothDisabled . "
    --DEFAULT test-function-async     fsnVdcCtrlTest
    --DEFAULT next-function-async     fsnVdcCtrlNext
    --DEFAULT set-function-async      fsnVdcCtrlSet
    --DEFAULT get-function-async      fsnVdcCtrlGet
    ::= { xldv11VdcControl 15 }

 xldv11VdcCtrlControlReqResult OBJECT-TYPE
    -- info-LEAF:    xldv11VdcCtrlControlReqResult
    -- info-TREE:    xldv11Tlm
    -- info-ACC:     ro
    -- info-SYNTAX:  Xldv11ControlReq
    -- info-VALUE:   see xldv11VdcCtrlControlReq
    -- info-COMMENT: specifies the result of user command
    -- info-ROU:     GET db
    -- info-IMPL:    V1.x
    -- info-VERCTRL: -
    SYNTAX        Xldv11ControlReq
    ACCESS        read-only
    STATUS        mandatory
    DESCRIPTION
	  " This read-only attribute informs about the result of 
	     the last user command."
    --DEFAULT next-function-async     fsnVdcCtrlNext
    --DEFAULT get-function-async      fsnVdcCtrlGet
    ::= { xldv11VdcControl 16 }

  xldv11VdcCtrlControlTimeStamp OBJECT-TYPE
     -- info-LEAF:    xldv11VdcCtrlControlTimeStamp
     -- info-TREE:    xldv11Tlm
     -- info-ACC:     ro
     -- info-SYNTAX:  TimeTicks
     -- info-VALUE:   0..2Giga
     -- info-COMMENT: specifies the time stamp in seconds
     -- info-COMMENT: of the last command
     -- info-COMMENT: (end of command)
     -- info-ROU:     GET db
     -- info-IMPL:    V1.x->
     -- info-VERCTRL: -
     SYNTAX        TimeTicks
     ACCESS        read-only
     STATUS        mandatory
     DESCRIPTION
        " This read-only attribute informs about the time stamp
        of the last command (end of command)."
    --DEFAULT next-function-async     fsnVdcCtrlNext
    --DEFAULT get-function-async      fsnVdcCtrlGet
    ::= { xldv11VdcControl 17 }


 -- --------------------------------------------------------------
 --                 TLM ADSL central PPTP Table
 -- --------------------------------------------------------------

 -- This managed entity represents the extension for the PPTP at
 -- the ADSL central interface. It includes additional attributes to
 -- configure the ADSL link.
 --

 xldv11AdcPPTPTable OBJECT-TYPE
    -- info-NODE:    xldv11AdcPPTPTable
    -- info-TREE:    xldv11Tlm
    -- info-ACC:     nac
    -- info-SYNTAX:  SEQUENCE OF Xldv11AdcPPTPEntry
    -- info-COMMENT: Table of adc PPTP objects.
    -- info-IMPL:    V1.0->
    SYNTAX        SEQUENCE OF Xldv11AdcPPTPEntry
    ACCESS        not-accessible
    STATUS        mandatory
    DESCRIPTION
	 " The physical path termination point table for ADSL C. "
    ::= { xldv11Tlm 4 }

 xldv11AdcPPTPEntry OBJECT-TYPE
    -- info-NODE:    xldv11AdcPPTPEntry
    -- info-TREE:    xldv11Tlm
    -- info-INDEX:   xldv11IfIndex
    -- info-ACC:     nac
    -- info-SYNTAX:  Xldv11AdcPPTPEntry
    -- info-COMMENT: Entry of AdcPPTPTable
    -- info-IMPL:    V1.0->
    SYNTAX        Xldv11AdcPPTPEntry
    ACCESS        not-accessible
    STATUS        mandatory
    DESCRIPTION
	 " An entry describing a termination point in the PPTP table.
	   Notifications : see xldv11IfEntry."
    INDEX         { xldv11IfIndex }
    ::= { xldv11AdcPPTPTable 1 }

 Xldv11AdcPPTPEntry ::=
    SEQUENCE { xldv11AdcMinRateDnCfg       Xldv11AdslDataRateDown,
	       xldv11AdcMinRateUpCfg       Xldv11AdslDataRateUp,
	       xldv11AdcMaxRateDnCfg       Xldv11AdslDataRateDown,
	       xldv11AdcMaxRateUpCfg       Xldv11AdslDataRateUp,
	       xldv11AdcMarginDnCfg        INTEGER,
	       xldv11AdcMarginUpCfg        INTEGER,
	       xldv11AdcMinMarginDnCfg     INTEGER,
	       xldv11AdcMinMarginUpCfg     INTEGER,
	       xldv11AdcLatencyDnCfg       Xldv11Latency,
	       xldv11AdcLatencyUpCfg       Xldv11Latency,
	       xldv11AdcRateDn             Xldv11AdslDataRateDown,
	       xldv11AdcRateUp             Xldv11AdslDataRateUp,
	       xldv11AdcMarginDn           INTEGER,
	       xldv11AdcMarginUp           INTEGER,
	       xldv11AdcAttenuationDn      INTEGER,
	       xldv11AdcAttenuationUp      INTEGER,
	       xldv11AdcLinkState          Xldv11LinkState,
	       xldv11AdcAISOnLOS           Xldv11OperState,
	       xldv11AdcAISOnACT           Xldv11OperState ,
	       xldv11AdcGuaranteedBandwidthUsage INTEGER }

 xldv11AdcMinRateDnCfg OBJECT-TYPE
    -- info-LEAF:    xldv11AdcMinRateDnCfg
    -- info-TREE:    xldv11Tlm
    -- info-ACC:     ro
    -- info-SYNTAX:  Xldv11AdslDataRateDown
    -- info-VALUE:   1..255 (default 1)
    -- info-COMMENT: desired lower limit of downstream data rate.
    -- info-COMMENT: range 32..8160 Kbit/sec. units 32 Kbit/sec.
    -- info-ROU:     GET db SET db
    -- info-IMPL:    V1.0:rw V1.1U:ro->
    -- info-VERCTRL: -
    SYNTAX        Xldv11AdslDataRateDown
    ACCESS        read-only
    STATUS        mandatory
    DESCRIPTION
	 " The lower value of the downstream data rate. The data
	   rate can be 32..8160 Kbit/sec and is splitted into units
	   of 32 Kbit/sec. Default value is 1. "
    --DEFAULT next-function-async     fsnAdcEntryNext
    --DEFAULT get-function-async      fsnAdcEntryGet
    ::= { xldv11AdcPPTPEntry 1 }

 xldv11AdcMinRateUpCfg OBJECT-TYPE
    -- info-LEAF:    xldv11AdcMinRateUpCfg
    -- info-TREE:    xldv11Tlm
    -- info-ACC:     ro
    -- info-SYNTAX:  Xldv11AdslDataRateUp
    -- info-VALUE:   1..25 (default 1)
    -- info-COMMENT: desired lower limit of upstream data rate.
    -- info-COMMENT: range 32..800 Kbit/sec. units 32 Kbit/sec.
    -- info-ROU:     GET db SET db
    -- info-IMPL:    V1.0:rw V1.1U:ro->
    -- info-VERCTRL: -
    SYNTAX        Xldv11AdslDataRateUp
    ACCESS        read-only
    STATUS        mandatory
    DESCRIPTION
	 " The lower value of the upstream data rate. The data
	   rate can be 32..800 Kbit/sec and is splitted into units
	   of 32 Kbit/sec. Default value is 1. "
    --DEFAULT next-function-async     fsnAdcEntryNext
    --DEFAULT get-function-async      fsnAdcEntryGet
    ::= { xldv11AdcPPTPEntry 2 }

 xldv11AdcMaxRateDnCfg OBJECT-TYPE
    -- info-LEAF:    xldv11AdcMaxRateDnCfg
    -- info-TREE:    xldv11Tlm
    -- info-ACC:     ro
    -- info-SYNTAX:  Xldv11AdslDataRateDown
    -- info-VALUE:   1..255 (default 255)
    -- info-COMMENT: desired upper limit of downstream data rate.
    -- info-COMMENT: range 32..8160 Kbit/sec. units 32 Kbit/sec.
    -- info-ROU:     GET db SET db
    -- info-IMPL:    V1.0:rw V1.1U:ro->
    -- info-VERCTRL: -
    SYNTAX        Xldv11AdslDataRateDown
    ACCESS        read-only
    STATUS        mandatory
    DESCRIPTION
	 " The upper value of the downstream data rate. The data
	   rate can be 32..8160 Kbit/sec and is splitted into units
	   of 32 Kbit/sec. Default is 255."
    --DEFAULT next-function-async     fsnAdcEntryNext
    --DEFAULT get-function-async      fsnAdcEntryGet
    ::= { xldv11AdcPPTPEntry 3 }

 xldv11AdcMaxRateUpCfg OBJECT-TYPE
    -- info-LEAF:    xldv11AdcMaxRateUpCfg
    -- info-TREE:    xldv11Tlm
    -- info-ACC:     ro
    -- info-SYNTAX:  Xldv11AdslDataRateUp
    -- info-VALUE:   1..25 (default 25)
    -- info-COMMENT: desired upper limit of upstream data rate.
    -- info-COMMENT: range 32..800 Kbit/sec. units 32 Kbit/sec.
    -- info-ROU:     GET db SET db
    -- info-IMPL:    V1.0:rw V1.1U:ro->
    -- info-VERCTRL: -
    SYNTAX        Xldv11AdslDataRateUp
    ACCESS        read-only
    STATUS        mandatory
    DESCRIPTION
	 " The upper value of the upstream data rate. The data
	   rate can be 32..800 Kbit/sec and is splitted into units
	   of 32 Kbit/sec. Default is 25. "
    --DEFAULT next-function-async     fsnAdcEntryNext
    --DEFAULT get-function-async      fsnAdcEntryGet
    ::= { xldv11AdcPPTPEntry 4 }

 xldv11AdcMarginDnCfg OBJECT-TYPE
    -- info-LEAF:    xldv11AdcMarginDnCfg
    -- info-TREE:    xldv11Tlm
    -- info-ACC:     ro
    -- info-SYNTAX:  INTEGER
    -- info-VALUE:   0..12 (default 6)
    -- info-COMMENT: desired downstream margin
    -- info-COMMENT: units in dB.
    -- info-ROU:     GET db
    -- info-IMPL:    V1.0:rw V1.1U:ro->
    -- info-VERCTRL: -
    SYNTAX        INTEGER (0..12)
    ACCESS        read-only
    STATUS        mandatory
    DESCRIPTION
	 " Desired downstream margin. The unit of measurement
	   is dB. Default value is 6. "
    --DEFAULT next-function-async     fsnAdcEntryNext
    --DEFAULT get-function-async      fsnAdcEntryGet
    ::= { xldv11AdcPPTPEntry 5 }

 xldv11AdcMarginUpCfg OBJECT-TYPE
    -- info-LEAF:    xldv11AdcMarginUpCfg
    -- info-TREE:    xldv11Tlm
    -- info-ACC:     ro
    -- info-SYNTAX:  INTEGER
    -- info-VALUE:   0..12 (default 6)
    -- info-COMMENT: desired upstream margin
    -- info-COMMENT: units in dB.
    -- info-ROU:     GET db
    -- info-IMPL:    V1.0:rw V1.1U:ro->
    -- info-VERCTRL: -
    SYNTAX        INTEGER (0..12)
    ACCESS        read-only
    STATUS        mandatory
    DESCRIPTION
	 " Desired upstream margin. The unit of measurement
	   is dB. Default is 6."
    --DEFAULT next-function-async     fsnAdcEntryNext
    --DEFAULT get-function-async      fsnAdcEntryGet
    ::= { xldv11AdcPPTPEntry 6 }

 xldv11AdcMinMarginDnCfg OBJECT-TYPE
    -- info-LEAF:    xldv11AdcMinMarginDnCfg
    -- info-TREE:    xldv11Tlm
    -- info-ACC:     ro
    -- info-SYNTAX:  INTEGER
    -- info-VALUE:   -12..12 (default 0)
    -- info-COMMENT: desired downstream margin
    -- info-COMMENT: units in dB.
    -- info-ROU:     GET db
    -- info-IMPL:    V1.0:rw V1.1U:ro->
    -- info-VERCTRL: -
    SYNTAX        INTEGER (-12..12)
    ACCESS        read-only
    STATUS        mandatory
    DESCRIPTION
	 " Desired minimal downstream margin. Default value is 0.
	   The unit of measurement is dB. "
    --DEFAULT next-function-async     fsnAdcEntryNext
    --DEFAULT get-function-async      fsnAdcEntryGet
    ::= { xldv11AdcPPTPEntry 7 }

 xldv11AdcMinMarginUpCfg OBJECT-TYPE
    -- info-LEAF:    xldv11AdcMinMarginUpCfg
    -- info-TREE:    xldv11Tlm
    -- info-ACC:     ro
    -- info-SYNTAX:  INTEGER
    -- info-VALUE:   -12..12 (default 0)
    -- info-COMMENT: desired minimal upstream margin
    -- info-COMMENT: units in dB.
    -- info-ROU:     GET db
    -- info-IMPL:    V1.0:rw V1.1U:ro->
    -- info-VERCTRL: -
    SYNTAX        INTEGER (-12..12)
    ACCESS        read-only
    STATUS        mandatory
    DESCRIPTION
	 " Desired minimal upstream margin. Default value is 0.
	   The unit of measurement is dB. "
    --DEFAULT next-function-async     fsnAdcEntryNext
    --DEFAULT get-function-async      fsnAdcEntryGet
    ::= { xldv11AdcPPTPEntry 8 }

 xldv11AdcLatencyDnCfg OBJECT-TYPE
    -- info-LEAF:    xldv11AdcLatencyDnCfg
    -- info-TREE:    xldv11Tlm
    -- info-ACC:     ro
    -- info-SYNTAX:  Xldv11Latency
    -- info-VALUE:   high, low (default low)
    -- info-COMMENT: desired interleave depth downstream.
    -- info-COMMENT: 0 = low. 1 = high.
    -- info-ROU:     GET db
    -- info-IMPL:    V1.0:rw V1.1U:ro->
    -- info-VERCTRL: -
    SYNTAX        Xldv11Latency
    ACCESS        read-only
    STATUS        mandatory
    DESCRIPTION
	  " Desired interleave depth (i.e. latency time) used for
	    error correction in downstream direction.
	    0: Latency low (default)
	    1: Latency high. "
    --DEFAULT next-function-async     fsnAdcEntryNext
    --DEFAULT get-function-async      fsnAdcEntryGet
    ::= { xldv11AdcPPTPEntry 10 }

 xldv11AdcLatencyUpCfg OBJECT-TYPE
    -- info-LEAF:    xldv11AdcLatencyUpCfg
    -- info-TREE:    xldv11Tlm
    -- info-ACC:     ro
    -- info-SYNTAX:  Xldv11Latency
    -- info-VALUE:   high, low (default low)
    -- info-COMMENT: desired interleave depth upstream.
    -- info-COMMENT: 0 = low (default). 1 = high.
    -- info-ROU:     GET db
    -- info-IMPL:    V1.0:rw V1.1U:ro->
    -- info-VERCTRL: -
    SYNTAX        Xldv11Latency
    ACCESS        read-only
    STATUS        mandatory
    DESCRIPTION
	  " Desired interleave depth (i.e. latency time) used for
	    error correction in upstream direction.
	    0: Latency low (default low)
	    1: Latency high. "
    --DEFAULT next-function-async     fsnAdcEntryNext
    --DEFAULT get-function-async      fsnAdcEntryGet
    ::= { xldv11AdcPPTPEntry 11 }

 xldv11AdcRateDn OBJECT-TYPE
    -- info-LEAF:    xldv11AdcRateDn
    -- info-TREE:    xldv11Tlm
    -- info-ACC:     ro
    -- info-SYNTAX:  Xldv11AdslDataRateDown
    -- info-VALUE:   1..255
    -- info-COMMENT: current upper limit of downstream data rate.
    -- info-COMMENT: range 32..8160 Kbit/sec. units 32 Kbit/sec.
    -- info-COMMENT: default : Xldv11AdcCurDefault
    -- info-ROU:     GET tm
    -- info-IMPL:    V1.0:rw V1.1U:ro->
    -- info-VERCTRL: -
    SYNTAX        Xldv11AdslDataRateDown
    ACCESS        read-only
    STATUS        mandatory
    DESCRIPTION
	 " The current downstream data rate. The data rate
	   can be 32..8160 Kbit/sec and is splitted into units
	   of 32 Kbit/sec. Default is Xldv11AdcCurDefault."
    --DEFAULT next-function-async     fsnAdcEntryNext
    --DEFAULT get-function-async      fsnAdcEntryGet
    ::= { xldv11AdcPPTPEntry 12 }

 xldv11AdcRateUp OBJECT-TYPE
    -- info-LEAF:    xldv11AdcRateUp
    -- info-TREE:    xldv11Tlm
    -- info-ACC:     ro
    -- info-SYNTAX:  Xldv11AdslDataRateUp
    -- info-VALUE:   1..25
    -- info-COMMENT: current upper limit of upstream data rate.
    -- info-COMMENT: range 32..800 Kbit/sec. units 32 Kbit/sec.
    -- info-COMMENT: default : Xldv11AdcCurDefault
    -- info-ROU:     GET tm
    -- info-IMPL:    V1.0:rw V1.1U:ro->
    -- info-VERCTRL: -
    SYNTAX        Xldv11AdslDataRateUp
    ACCESS        read-only
    STATUS        mandatory
    DESCRIPTION
	 " The current upstream data rate. The data rate
	   can be 32..800 Kbit/sec and is splitted into units
	   of 32 Kbit/sec. Default is Xldv11AdcCurDefault."
    --DEFAULT next-function-async     fsnAdcEntryNext
    --DEFAULT get-function-async      fsnAdcEntryGet
    ::= { xldv11AdcPPTPEntry 13 }

 xldv11AdcMarginDn OBJECT-TYPE
    -- info-LEAF:    xldv11AdcMarginDn
    -- info-TREE:    xldv11Tlm
    -- info-ACC:     ro
    -- info-SYNTAX:  INTEGER
    -- info-VALUE:   -127..128
    -- info-COMMENT: current downstream margin
    -- info-COMMENT: units in dB.
    -- info-COMMENT: default : Xldv11AdcCurDefault
    -- info-ROU:     GET tm
    -- info-IMPL:    V1.0:rw V1.1U:ro->
    -- info-VERCTRL: -
    SYNTAX        INTEGER (-127..128)
    ACCESS        read-only
    STATUS        mandatory
    DESCRIPTION
	 " The current downstream margin in units of dB.
	   Default is Xldv11AdcCurDefault. "
    --DEFAULT next-function-async     fsnAdcEntryNext
    --DEFAULT get-function-async      fsnAdcEntryGet
    ::= { xldv11AdcPPTPEntry 14 }

 xldv11AdcMarginUp OBJECT-TYPE
    -- info-LEAF:    xldv11AdcMarginUp
    -- info-TREE:    xldv11Tlm
    -- info-ACC:     ro
    -- info-SYNTAX:  INTEGER
    -- info-VALUE:   -127..128
    -- info-COMMENT: current upstream margin. units dB.
    -- info-ROU:     GET tm
    -- info-IMPL:    V1.0:rw V1.1U:ro->
    -- info-VERCTRL: -
    SYNTAX        INTEGER (-127..128)
    ACCESS        read-only
    STATUS        mandatory
    DESCRIPTION
	 " The current upstream margin in units of dB.
	   Default is Xldv11AdcCurDefault. "
    --DEFAULT next-function-async     fsnAdcEntryNext
    --DEFAULT get-function-async      fsnAdcEntryGet
    ::= { xldv11AdcPPTPEntry 15 }

 xldv11AdcAttenuationDn OBJECT-TYPE
    -- info-LEAF:    xldv11AdcAttenuationDn
    -- info-TREE:    xldv11Tlm
    -- info-ACC:     ro
    -- info-SYNTAX:  INTEGER
    -- info-VALUE:   0..255
    -- info-COMMENT: current downstream attenuation
    -- info-COMMENT: in steps of 0,5 dB.
    -- info-ROU:     GET tm
    -- info-IMPL:    V1.0:rw V1.1U:ro->
    -- info-VERCTRL: -
    SYNTAX        INTEGER (0..255)
    ACCESS        read-only
    STATUS        mandatory
    DESCRIPTION
	 " The current downstream attenuation in steps of 0,5 dB.
	   Default is Xldv11AdcCurDefault. "
    --DEFAULT next-function-async     fsnAdcEntryNext
    --DEFAULT get-function-async      fsnAdcEntryGet
    ::= { xldv11AdcPPTPEntry 16 }

 xldv11AdcAttenuationUp OBJECT-TYPE
    -- info-LEAF:    xldv11AdcAttenuationUp
    -- info-TREE:    xldv11Tlm
    -- info-ACC:     ro
    -- info-SYNTAX:  INTEGER
    -- info-VALUE:   0..255
    -- info-COMMENT: current upstream attenuation
    -- info-COMMENT: in steps of 0,5 dB.
    -- info-COMMENT: default : Xldv11AdcCurDefault
    -- info-ROU:     GET tm
    -- info-IMPL:    V1.0:rw V1.1U:ro->
    -- info-VERCTRL: -
    SYNTAX        INTEGER (0..255)
    ACCESS        read-only
    STATUS        mandatory
    DESCRIPTION
	 " The current upstream attenuation in steps of 0,5 dB.
	   Default is Xldv11AdcCurDefault. "
    --DEFAULT next-function-async     fsnAdcEntryNext
    --DEFAULT get-function-async      fsnAdcEntryGet
    ::= { xldv11AdcPPTPEntry 17 }

 xldv11AdcLinkState OBJECT-TYPE
    -- info-LEAF:    xldv11AdcLinkState
    -- info-TREE:    xldv11Tlm
    -- info-ACC:     ro
    -- info-SYNTAX:  Xldv11LinkState
    -- info-VALUE:   unknown,idle,quiet,train,active,
    -- info-VALUE:   download,remoteDownload
    -- info-COMMENT: link state of ADSL central office modem
    -- info-ROU:     GET tm
    -- info-IMPL:    V1.0:rw V1.1U:ro->
    -- info-VERCTRL: -
    SYNTAX        Xldv11LinkState
    ACCESS        read-only
    STATUS        mandatory
    DESCRIPTION
	 " The attribute reflects upon the internal states of the
	   Central Office Modem.
	   Range of values is:
	      unknown,
	      idle,
	      quiet,
	      train,
	      active,
	      download,
	      remoteDownload. "
    --DEFAULT next-function-async     fsnAdcEntryNext
    --DEFAULT get-function-async      fsnAdcEntryGet
    ::= { xldv11AdcPPTPEntry 18 }

 xldv11AdcAISOnLOS  OBJECT-TYPE
    -- info-LEAF:    xldv11AdcAISOnLOS
    -- info-TREE:    xldv11Tlm
    -- info-ACC:     rw
    -- info-SYNTAX:  Xldv11OperState
    -- info-VALUE:   disabled : No VP-AIS generation (default)
    -- info-VALUE:   enabled  :    VP-AIS generation 
    -- info-COMMENT: enables or disables the VP-AIS generation.
    -- info-ROU:     GET db SET tm
    -- info-IMPL:    V1.1U->
    -- info-VERCTRL: -
    SYNTAX        Xldv11OperState
    ACCESS        read-write
    STATUS        mandatory
    DESCRIPTION
	 " The attribute enables or disables the VP-AIS generation
	   after defect LOS.
	   disabled : No VP-AIS generation
	   enabled  :    VP-AIS generation 
	   Default:  disabled. "
    --DEFAULT test-function-async     fsnAdcEntryTest
    --DEFAULT next-function-async     fsnAdcEntryNext
    --DEFAULT get-function-async      fsnAdcEntryGet
    --DEFAULT set-function-async      fsnAdcEntrySet
    ::= { xldv11AdcPPTPEntry 19 }

 xldv11AdcAISOnACT  OBJECT-TYPE
    -- info-LEAF:    xldv11AdcAISOnACT
    -- info-TREE:    xldv11Tlm
    -- info-ACC:     rw
    -- info-SYNTAX:  Xldv11OperState
    -- info-VALUE:   disabled : No VP-AIS generation (default)
    -- info-VALUE:   enabled  :    VP-AIS generation 
    -- info-COMMENT: enables or disables the VP-AIS generation.
    -- info-COMMENT: after link activation fault
    -- info-ROU:     GET db SET tm
    -- info-IMPL:    V1.1U->
    -- info-VERCTRL: -
    SYNTAX        Xldv11OperState
    ACCESS        read-write
    STATUS        mandatory
    DESCRIPTION
	 " The attribute enables or disables the VP-AIS generation
	   after link activation fault.
	   disabled : No VP-AIS generation
	   enabled  :    VP-AIS generation 
	   Default:  disabled. "
    --DEFAULT test-function-async     fsnAdcEntryTest
    --DEFAULT next-function-async     fsnAdcEntryNext
    --DEFAULT get-function-async      fsnAdcEntryGet
    --DEFAULT set-function-async      fsnAdcEntrySet
    ::= { xldv11AdcPPTPEntry 20 }

 xldv11AdcGuaranteedBandwidthUsage OBJECT-TYPE
    -- info-LEAF:    xldv11AdcGuaranteedBandwidthUsage
    -- info-TREE:    xldv11Tlm
    -- info-ACC:     ro
    -- info-SYNTAX:  INTEGER
    -- info-VALUE:   0..100
    -- info-COMMENT: used bandwidth in percent
    -- info-ROU:     GET db
    -- info-IMPL:    V1.x
    -- info-VERCTRL: V1.1U->:GET db
    SYNTAX        INTEGER (0..100)
    ACCESS        read-only
    STATUS        mandatory
    DESCRIPTION
	 " used bandwidth in percent. "
    --DEFAULT next-function-async     fsnAdcEntryNext
    --DEFAULT get-function-async      fsnAdcEntryGet
    ::= { xldv11AdcPPTPEntry 21 }

 -- --------------------------------------------------------------
 --                   TLM IBM PPTP Table (XLDV1.1U)
 -- --------------------------------------------------------------
 --
 -- This managed entity represents the extension for the PPTP at
 -- the IBM interface.

 -- --------------------------------------------------------------

 -- --------------------------------------------------------------
 --                   TLM VDSL central PPTP Table
 -- --------------------------------------------------------------
 --
 -- This managed entity represents the extension for the PPTP at
 -- the VDSL-C interface. It includes additional attributes to
 -- configure the VDSL link.
 --
 xldv11VdcPPTPTable OBJECT-TYPE
    -- info-NODE:    xldv11VdcPPTPTable
    -- info-TREE:    xldv11Tlm
    -- info-ACC:     nac
    -- info-SYNTAX:  SEQUENCE OF Xldv11VdcPPTPEntry
    -- info-COMMENT: Table of vdc PPTPs.
    -- info-IMPL:    V1.x->
    SYNTAX        SEQUENCE OF Xldv11VdcPPTPEntry
    ACCESS        not-accessible
    STATUS        mandatory
    DESCRIPTION
	 " The physical path termination point table for VDSL C. "
    ::= { xldv11Tlm 5 }

 xldv11VdcPPTPEntry OBJECT-TYPE
    -- info-NODE:    xldv11VdcPPTPEntry
    -- info-TREE:    xldv11Tlm
    -- info-INDEX:   xldv11IfIndex
    -- info-ACC:     nac
    -- info-SYNTAX:  Xldv11VdcPPTPEntry
    -- info-COMMENT: Entry of vdc PPTP table.
    -- info-IMPL:    V1.x->
    SYNTAX        Xldv11VdcPPTPEntry
    ACCESS        not-accessible
    STATUS        mandatory
    DESCRIPTION
	 " An entry describing a termination point in the PPTP table.
	   Notifications : see xldv11IfEntry."
    INDEX         { xldv11IfIndex }
    ::= { xldv11VdcPPTPTable 1 }

 Xldv11VdcPPTPEntry ::=
    SEQUENCE { xldv11VdcMinRateDnCfg        Xldv11VdcRateDn,
	       xldv11VdcMinRateUpCfg        Xldv11VdcRateUp,
	       xldv11VdcMaxRateDnCfg        Xldv11VdcRateDn,
	       xldv11VdcMaxRateUpCfg        Xldv11VdcRateUp,
	       xldv11VdcLatencyDnCfg        Xldv11VdcLatencyDn,
	       xldv11VdcLatencyUpCfg        Xldv11VdcLatencyUp,
	       xldv11VdcPowerBoostCfg       Xldv11VdcPowerBoostAdaptationType,
	       xldv11VdcWarmStartCfg        Xldv11OperState,
	       xldv11VdcVdslModeCfg         Xldv11VdcVdslMode,
	       xldv11VdcSleepModeCfg        Xldv11OperState,
	       xldv11VdcPsdMaskCfg          Xldv11VdcPsdMask,
	       xldv11VdcPowerAdaptationCfg  Xldv11VdcPowerBoostAdaptationType,
	       xldv11VdcRateDn              Xldv11VdcRateDn,
	       xldv11VdcRateUp              Xldv11VdcRateUp,
	       xldv11VdcMarginDn            Integer32,
	       xldv11VdcMarginUp            Integer32,
	       xldv11VdcAttenuationDn       Integer32,
	       xldv11VdcAttenuationUp       Integer32,
	       xldv11VdcLinkState           Xldv11LinkState ,
	       xldv11VdcGuaranteedBandwidthUsage INTEGER }

 xldv11VdcMinRateDnCfg OBJECT-TYPE
    -- info-LEAF:    xldv11VdcMinRateDnCfg
    -- info-TREE:    xldv11Tlm
    -- info-ACC:     ro
    -- info-SYNTAX:  Xldv11VdcRateDn
    -- info-VALUE:   (multiples of 810 Kbps)
    -- info-VALUE:   2,4,6,8,12,16
    -- info-VALUE:   24,32,48,64
    -- info-COMMENT: desired lower limit of downstream data rate.
    -- info-ROU:     GET db
    -- info-IMPL:    V1.x
    -- info-VERCTRL: V1.1U->:GET db
    SYNTAX        Xldv11VdcRateDn
    ACCESS        read-only
    STATUS        mandatory
    DESCRIPTION
	 " The lower limit of the downstream data rate. Possible values (in
	   multiples of 810 Kbps): 2, 4, 6, 8, 12, 16, 24, 32, 48, 64 . "
    --DEFAULT next-function-async     fsnVdcEntryNext
    --DEFAULT get-function-async      fsnVdcEntryGet
    ::= { xldv11VdcPPTPEntry 1 }

 xldv11VdcMinRateUpCfg OBJECT-TYPE
    -- info-LEAF:    xldv11VdcMinRateUpCfg
    -- info-TREE:    xldv11Tlm
    -- info-ACC:     ro
    -- info-SYNTAX:  Xldv11VdcRateUp
    -- info-VALUE:   (multiples of 810 Kbps)
    -- info-VALUE:   1,2,4,8,12,16
    -- info-COMMENT: desired lower limit of upstream data rate.
    -- info-ROU:     GET db
    -- info-IMPL:    V1.x
    -- info-VERCTRL: V1.1U->:GET db
    SYNTAX        Xldv11VdcRateUp
    ACCESS        read-only
    STATUS        mandatory
    DESCRIPTION
	 " The lower limit of the upstream data rate. Possible values (in
	   multiples of 810 Kbps): 1, 2, 4, 8, 12, 16 . "
    --DEFAULT next-function-async     fsnVdcEntryNext
    --DEFAULT get-function-async      fsnVdcEntryGet
    ::= { xldv11VdcPPTPEntry 2 }

 xldv11VdcMaxRateDnCfg OBJECT-TYPE
    -- info-LEAF:    xldv11VdcMaxRateDnCfg
    -- info-TREE:    xldv11Tlm
    -- info-ACC:     ro
    -- info-SYNTAX:  Xldv11VdcRateDn
    -- info-VALUE:   (multiples of 810 Kbps)
    -- info-VALUE:   2,4,6,8,12,16
    -- info-VALUE:   24,32,48,64
    -- info-COMMENT: desired upper limit of downstream data rate.
    -- info-ROU:     GET db
    -- info-IMPL:    V1.x
    -- info-VERCTRL: V1.1U->:GET db
    SYNTAX        Xldv11VdcRateDn
    ACCESS        read-only
    STATUS        mandatory
    DESCRIPTION
	 " The upper limit of the downstream data rate. Possible values (in
	   multiples of 810 Kbps): 2, 4, 6, 8, 12, 16, 24, 32, 48, 64 . "
    --DEFAULT next-function-async     fsnVdcEntryNext
    --DEFAULT get-function-async      fsnVdcEntryGet
    ::= { xldv11VdcPPTPEntry 3 }

 xldv11VdcMaxRateUpCfg OBJECT-TYPE
    -- info-LEAF:    xldv11VdcMaxRateUpCfg
    -- info-TREE:    xldv11Tlm
    -- info-ACC:     ro
    -- info-SYNTAX:  Xldv11VdcRateUp
    -- info-VALUE:   (multiples of 810 Kbps)
    -- info-VALUE:   1,2,4,8,12,16
    -- info-COMMENT: desired upper limit of upstream data rate.
    -- info-ROU:     GET db
    -- info-IMPL:    V1.x
    -- info-VERCTRL: V1.1U->:GET db
    SYNTAX        Xldv11VdcRateUp
    ACCESS        read-only
    STATUS        mandatory
    DESCRIPTION
	 " The upper limit of the upstream data rate.Possible values (in
	   multiples of 810 Kbps): 1, 2, 4, 8, 12, 16 . "
    --DEFAULT next-function-async     fsnVdcEntryNext
    --DEFAULT get-function-async      fsnVdcEntryGet
    ::= { xldv11VdcPPTPEntry 4 }

 xldv11VdcLatencyDnCfg OBJECT-TYPE
    -- info-LEAF:    xldv11VdcLatencyDnCfg
    -- info-TREE:    xldv11Tlm
    -- info-ACC:     ro
    -- info-SYNTAX:  Xldv11VdcLatencyDn 
    -- info-VALUE:   (delay in msec)
    -- info-VALUE:   0,2,4,8,12,16,20,32
    -- info-COMMENT: desired interleave depth
    -- info-COMMENT: downstream
    -- info-ROU:     GET db
    -- info-IMPL:    V1.x
    -- info-VERCTRL: V1.1U->:GET db
    SYNTAX        Xldv11VdcLatencyDn
    ACCESS        read-only
    STATUS        mandatory
    DESCRIPTION
	  " Desired interleave depth (i.e. latency time) used for
	    error correction in downstream direction. Possible values (delay
	    in msec): 0, 2, 4, 8, 12, 16, 20, 32 . "
    --DEFAULT next-function-async     fsnVdcEntryNext
    --DEFAULT get-function-async      fsnVdcEntryGet
    ::= { xldv11VdcPPTPEntry 5 }

 xldv11VdcLatencyUpCfg OBJECT-TYPE
    -- info-LEAF:    xldv11VdcLatencyUpCfg
    -- info-TREE:    xldv11Tlm
    -- info-ACC:     ro
    -- info-SYNTAX:  Xldv11VdcLatencyUp 
    -- info-VALUE:   (delay in msec)
    -- info-VALUE:   0,2,4,8,10,20
    -- info-COMMENT: desired interleave depth
    -- info-COMMENT: upstream
    -- info-ROU:     GET db
    -- info-IMPL:    V1.x
    -- info-VERCTRL: V1.1U->:GET db
    SYNTAX        Xldv11VdcLatencyUp
    ACCESS        read-only
    STATUS        mandatory
    DESCRIPTION
	  " Desired interleave depth (i.e. latency time) used for
	    error correction in upstream direction. Possible values (delay
	    in msec): 0, 2, 4, 8, 10, 20 . "
    --DEFAULT next-function-async     fsnVdcEntryNext
    --DEFAULT get-function-async      fsnVdcEntryGet
    ::= { xldv11VdcPPTPEntry 6 }

 xldv11VdcPowerBoostCfg OBJECT-TYPE
    -- info-LEAF:    xldv11VdcPowerBoostCfg
    -- info-TREE:    xldv11Tlm
    -- info-ACC:     ro
    -- info-SYNTAX:  Xldv11VdcPowerBoostAdaptationType
    -- info-VALUE:   suEnabled,ntEnabled,bothEnabled,bothDisabled
    -- info-COMMENT: desired power boost mode
    -- info-ROU:     GET db
    -- info-IMPL:    V1.x
    -- info-VERCTRL: V1.1U->:GET db
    SYNTAX        Xldv11VdcPowerBoostAdaptationType
    ACCESS        read-only
    STATUS        mandatory
    DESCRIPTION
	  " Desired power boost mode.
	    Range of values is:
	       suEnabled,
	       ntEnabled,
	       bothEnabled,
	       bothDisabled . "
    --DEFAULT next-function-async     fsnVdcEntryNext
    --DEFAULT get-function-async      fsnVdcEntryGet
    ::= { xldv11VdcPPTPEntry 7 }

 xldv11VdcWarmStartCfg OBJECT-TYPE
    -- info-LEAF:    xldv11VdcWarmStartCfg
    -- info-TREE:    xldv11Tlm
    -- info-ACC:     ro
    -- info-SYNTAX:  Xldv11OperState
    -- info-VALUE:   enabled, disabled
    -- info-COMMENT: Desired warmstart option.
    -- info-IMPL:    V1.x
    -- info-ROU:     GET db
    -- info-IMPL:    V1.x
    -- info-VERCTRL: V1.1U->:GET db
    SYNTAX        Xldv11OperState
    ACCESS        read-only
    STATUS        mandatory
    DESCRIPTION
	  " Configured warmstart option.
	    Possible values: enabled, disabled . "
    --DEFAULT next-function-async     fsnVdcEntryNext
    --DEFAULT get-function-async      fsnVdcEntryGet
    ::= { xldv11VdcPPTPEntry 8 }

 xldv11VdcVdslModeCfg OBJECT-TYPE
    -- info-LEAF:    xldv11VdcVdslModeCfg
    -- info-TREE:    xldv11Tlm
    -- info-ACC:     ro
    -- info-SYNTAX:  Xldv11VdcVdslMode 
    -- info-VALUE:   adslFriendly, vdslEfficient
    -- info-COMMENT: Desired VDSL mode option
    -- info-ROU:     GET db
    -- info-IMPL:    V1.x
    -- info-VERCTRL: V1.1U->:GET db
    SYNTAX        Xldv11VdcVdslMode
    ACCESS        read-only
    STATUS        mandatory
    DESCRIPTION
	  " Configured VDSL mode option.
	    Possible values:
	    adslFriendly,
	    vdslEfficient . "
    --DEFAULT next-function-async     fsnVdcEntryNext
    --DEFAULT get-function-async      fsnVdcEntryGet
    ::= { xldv11VdcPPTPEntry 9 }

 xldv11VdcSleepModeCfg OBJECT-TYPE
    -- info-LEAF:    xldv11VdcSleepModeCfg
    -- info-TREE:    xldv11Tlm
    -- info-ACC:     ro
    -- info-SYNTAX:  Xldv11OperState
    -- info-VALUE:   enabled, disabled
    -- info-COMMENT: Desired sleep mode option
    -- info-ROU:     GET db
    -- info-IMPL:    V1.x
    -- info-VERCTRL: V1.1U->:GET db
    SYNTAX        Xldv11OperState
    ACCESS        read-only
    STATUS        mandatory
    DESCRIPTION
	  " Desired sleep mode option.
	    Possible values: enabled, disabled . "
    --DEFAULT next-function-async     fsnVdcEntryNext
    --DEFAULT get-function-async      fsnVdcEntryGet
    ::= { xldv11VdcPPTPEntry 10 }

 xldv11VdcPsdMaskCfg OBJECT-TYPE
    -- info-LEAF:    xldv11VdcPsdMaskCfg
    -- info-TREE:    xldv11Tlm
    -- info-ACC:     ro
    -- info-SYNTAX:  Xldv11VdcPsdMask 
    -- info-VALUE:   m1 (strong effect), m2 (weak effect)
    -- info-COMMENT: desired PSD mask option
    -- info-COMMENT: electro-magnetic interference effects
    -- info-ROU:     GET db
    -- info-IMPL:    V1.x
    -- info-VERCTRL: V1.1U->:GET db
    SYNTAX        Xldv11VdcPsdMask
    ACCESS        read-only
    STATUS        mandatory
    DESCRIPTION
	  " Desired PSD mask option (electro-magnetic interference
	    effects, M1 for strong and M2 for weak effects).
	    Possible values: m1, m2 . "
    --DEFAULT next-function-async     fsnVdcEntryNext
    --DEFAULT get-function-async      fsnVdcEntryGet
    ::= { xldv11VdcPPTPEntry 11 }

 xldv11VdcPowerAdaptationCfg OBJECT-TYPE
    -- info-LEAF:    xldv11VdcPowerAdaptationCfg
    -- info-TREE:    xldv11Tlm
    -- info-ACC:     ro
    -- info-SYNTAX:  Xldv11VdcPowerBoostAdaptationType
    -- info-VALUE:   suEnabled,ntEnabled,bothEnabled,bothDisabled
    -- info-COMMENT: Desired power adaptation mode
    -- info-ROU:     GET db
    -- info-IMPL:    V1.x
    -- info-VERCTRL: V1.1U*->:GET db
    SYNTAX        Xldv11VdcPowerBoostAdaptationType
    ACCESS        read-only
    STATUS        mandatory
    DESCRIPTION
	  " Desired power adaptation option.
	    Range of values is:
	       suEnabled,
	       ntEnabled,
	       bothEnabled,
	       bothDisabled . "
    --DEFAULT next-function-async     fsnVdcEntryNext
    --DEFAULT get-function-async      fsnVdcEntryGet
    ::= { xldv11VdcPPTPEntry 12 }

 xldv11VdcRateDn OBJECT-TYPE
    -- info-LEAF:    xldv11VdcRateDn
    -- info-TREE:    xldv11Tlm
    -- info-ACC:     ro
    -- info-SYNTAX:  Xldv11VdcRateDn
    -- info-VALUE:   (multiples of 810 Kbps)
    -- info-VALUE:   2,4,6,8,12,16
    -- info-VALUE:   24,32,48,64
    -- info-COMMENT: current downstream data rate
    -- info-ROU:     GET db
    -- info-IMPL:    V1.x
    -- info-VERCTRL: V1.1U->:GET db
    SYNTAX        Xldv11VdcRateDn
    ACCESS        read-only
    STATUS        mandatory
    DESCRIPTION
	 " The current downstream data rate. Possible values: (in multiples
	   of 810 Kbps): 2, 4, 6, 8, 12, 16, 24, 32, 48, 64 . "
    --DEFAULT next-function-async     fsnVdcEntryNext
    --DEFAULT get-function-async      fsnVdcEntryGet
    ::= { xldv11VdcPPTPEntry 13 }

 xldv11VdcRateUp OBJECT-TYPE
    -- info-LEAF:    xldv11VdcRateUp
    -- info-TREE:    xldv11Tlm
    -- info-ACC:     ro
    -- info-SYNTAX:  Xldv11VdcRateUp
    -- info-VALUE:   (multiples of 810 Kbps)
    -- info-VALUE:   1,2,4,8,12,16
    -- info-COMMENT: current upstream data rate
    -- info-ROU:     GET db
    -- info-IMPL:    V1.x
    -- info-VERCTRL: V1.1U->:GET db
    SYNTAX        Xldv11VdcRateUp
    ACCESS        read-only
    STATUS        mandatory
    DESCRIPTION
	 " The current upstream data rate. Possible values: (in multiples
	   of 810 Kbps): 1, 2, 4, 8, 12, 16 . "
    --DEFAULT next-function-async     fsnVdcEntryNext
    --DEFAULT get-function-async      fsnVdcEntryGet
    ::= { xldv11VdcPPTPEntry 14 }

 xldv11VdcMarginDn OBJECT-TYPE
    -- info-LEAF:    xldv11VdcMarginDn
    -- info-TREE:    xldv11Tlm
    -- info-ACC:     ro
    -- info-SYNTAX:  Integer32
    -- info-VALUE:   -2147483648..2147483647
    -- info-COMMENT: current downstream margin
    -- info-COMMENT: in units of dB
    -- info-ROU:     GET db
    -- info-IMPL:    V1.x
    -- info-VERCTRL: V1.1U->:GET db
    SYNTAX        Integer32
    ACCESS        read-only
    STATUS        mandatory
    DESCRIPTION
	 " The current downstream margin in units of dB. "
    --DEFAULT next-function-async     fsnVdcEntryNext
    --DEFAULT get-function-async      fsnVdcEntryGet
    ::= { xldv11VdcPPTPEntry 15 }

 xldv11VdcMarginUp OBJECT-TYPE
    -- info-LEAF:    xldv11VdcMarginUp
    -- info-TREE:    xldv11Tlm
    -- info-ACC:     ro
    -- info-SYNTAX:  Integer32
    -- info-VALUE:   -2147483648..2147483647
    -- info-COMMENT: current upstream margin
    -- info-COMMENT: in units of dB
    -- info-ROU:     GET db
    -- info-IMPL:    V1.x
    -- info-VERCTRL: V1.1U->:GET db
    SYNTAX        Integer32
    ACCESS        read-only
    STATUS        mandatory
    DESCRIPTION
	 " The current upstream margin in units of dB. "
    --DEFAULT next-function-async     fsnVdcEntryNext
    --DEFAULT get-function-async      fsnVdcEntryGet
    ::= { xldv11VdcPPTPEntry 16 }

 xldv11VdcAttenuationDn OBJECT-TYPE
    -- info-LEAF:    xldv11VdcAttenuationDn
    -- info-TREE:    xldv11Tlm
    -- info-ACC:     ro
    -- info-SYNTAX:  Integer32
    -- info-VALUE:   -2147483648..2147483647
    -- info-COMMENT: current downstream margin
    -- info-COMMENT: in units of dB
    -- info-ROU:     GET db
    -- info-IMPL:    V1.x
    -- info-VERCTRL: V1.1U->:GET db
    SYNTAX        Integer32
    ACCESS        read-only
    STATUS        mandatory
    DESCRIPTION
	 " The current downstream attenuation in units of dB. "
    --DEFAULT next-function-async     fsnVdcEntryNext
    --DEFAULT get-function-async      fsnVdcEntryGet
    ::= { xldv11VdcPPTPEntry 17 }

 xldv11VdcAttenuationUp OBJECT-TYPE
    -- info-LEAF:    xldv11VdcAttenuationUp
    -- info-TREE:    xldv11Tlm
    -- info-ACC:     ro
    -- info-SYNTAX:  Integer32
    -- info-VALUE:   -2147483648..2147483647
    -- info-COMMENT: current upstream margin
    -- info-ROU:     GET db
    -- info-IMPL:    V1.x
    -- info-VERCTRL: V1.1U->:GET db
    SYNTAX        Integer32
    ACCESS        read-only
    STATUS        mandatory
    DESCRIPTION
	 " The current upstream attenuation in units of dB. "
    --DEFAULT next-function-async     fsnVdcEntryNext
    --DEFAULT get-function-async      fsnVdcEntryGet
    ::= { xldv11VdcPPTPEntry 18 }

 xldv11VdcLinkState OBJECT-TYPE
    -- info-LEAF:    xldv11VdcLinkState
    -- info-TREE:    xldv11Tlm
    -- info-ACC:     ro
    -- info-SYNTAX:  Xldv11LinkState
    -- info-VALUE:   unknown,idle,quiet,train,active,
    -- info-VALUE:   sleepMode
    -- info-COMMENT: link state of VDSL central office modem
    -- info-ROU:     GET db
    -- info-IMPL:    V1.x
    -- info-VERCTRL: V1.1U->:GET db
    SYNTAX        Xldv11LinkState
    ACCESS        read-only
    STATUS        mandatory
    DESCRIPTION
	 " Current internal states of the Central Office VDSL Modem.
	   Range of values is:
	      unknown,
	      idle,
	      quiet,
	      train,
	      active,
	      sleepMode . "
    --DEFAULT next-function-async     fsnVdcEntryNext
    --DEFAULT get-function-async      fsnVdcEntryGet
    ::= { xldv11VdcPPTPEntry 19 }

 xldv11VdcGuaranteedBandwidthUsage OBJECT-TYPE
    -- info-LEAF:    xldv11VdcGuaranteedBandwidthUsage
    -- info-TREE:    xldv11Tlm
    -- info-ACC:     ro
    -- info-SYNTAX:  INTEGER
    -- info-VALUE:   0..100
    -- info-COMMENT: used bandwidth in percent
    -- info-ROU:     GET db
    -- info-IMPL:    V1.x
    -- info-VERCTRL: V1.1U->:GET db
    SYNTAX        INTEGER (0..100)
    ACCESS        read-only
    STATUS        mandatory
    DESCRIPTION
	 " used bandwidth in percent. "
    --DEFAULT next-function-async     fsnVdcEntryNext
    --DEFAULT get-function-async      fsnVdcEntryGet
    ::= { xldv11VdcPPTPEntry 20}

 -- --------------------------------------------------------------
 --                   TLM IBM PPTP Table (XLDV1.1U)
 -- --------------------------------------------------------------
 --
 -- This managed entity represents the extension for the PPTP at
 -- the IBM interface.
 --

 xldv11IbmPPTPTable OBJECT-TYPE
    -- info-NODE:    xldv11IbmPPTPTable
    -- info-TREE:    xldv11Tlm
    -- info-ACC:     nac
    -- info-SYNTAX:  SEQUENCE OF Xldv11IbmPPTPEntry
    -- info-COMMENT: Table of ibm PPTP objects.
    -- info-IMPL:    V1.1U->
    SYNTAX        SEQUENCE OF Xldv11IbmPPTPEntry
    ACCESS        not-accessible
    STATUS        mandatory
    DESCRIPTION
	 " The physical path termination point table for the IBM IF. "
    ::= { xldv11Tlm 6 }

 xldv11IbmPPTPEntry OBJECT-TYPE
    -- info-NODE:    xldv11IbmPPTPEntry
    -- info-TREE:    xldv11Tlm
    -- info-INDEX:   xldv11IfIndex
    -- info-ACC:     nac
    -- info-SYNTAX:  Xldv11IbmPPTPEntry
    -- info-COMMENT: Entry of Ibm PPTP table.
    -- info-IMPL:    V1.1U->
    SYNTAX        Xldv11IbmPPTPEntry
    ACCESS        not-accessible
    STATUS        mandatory
    DESCRIPTION
	 " An entry describing a termination point in the IbmPPTP table.
	   Notifications : see xldv11IfEntry."
    INDEX         { xldv11IfIndex }
    ::= { xldv11IbmPPTPTable 1 }

 Xldv11IbmPPTPEntry ::= SEQUENCE { xldv11IbmAISOnLOS   Xldv11OperState }

 xldv11IbmAISOnLOS  OBJECT-TYPE
    -- info-LEAF:    xldv11IbmAISOnLOS
    -- info-TREE:    xldv11Tlm
    -- info-ACC:     rw
    -- info-SYNTAX:  Xldv11OperState
    -- info-VALUE:   disabled : No VP-AIS generation (default)
    -- info-VALUE:   enabled  :    VP-AIS generation 
    -- info-COMMENT: enables or disables the VP-AIS generation.
    -- info-ROU:     GET db SET tm
    -- info-IMPL:    V1.1U->
    -- info-VERCTRL: -
    SYNTAX        Xldv11OperState
    ACCESS        read-write
    STATUS        mandatory
    DESCRIPTION
	 " To configure the VP-AIS generation on defect LOS.
	   Range of values is: enabled and disabled (default) . "
    --DEFAULT test-function-async     fsnIbmEntryTest
    --DEFAULT next-function-async     fsnIbmEntryNext
    --DEFAULT set-function-async      fsnIbmEntrySet
    --DEFAULT get-function-async      fsnIbmEntryGet
    ::= { xldv11IbmPPTPEntry 1 }


 -- --------------------------------------------------------------
 --                  TLM DS3 near-end PPTP Table (XLDV1.3A)
 -- --------------------------------------------------------------
 --
 -- This managed entity represents the extension for the PPTP at the
 -- DS3 near-end interface. It includes the additional attributes to
 -- configure the DS3 link.
 -- Valid for XLDV1.3A
 --

 xldv11Ds3NePPTPTable OBJECT-TYPE
    -- info-NODE:    xldv11Ds3NePPTPTable
    -- info-TREE:    xldv11Tlm
    -- info-ACC:     nac
    -- info-SYNTAX:  SEQUENCE OF Xldv11Ds3NePPTPEntry
    -- info-COMMENT: Table of d3n PPTP interface objects.
    -- info-IMPL:    V1.3A->
    SYNTAX        SEQUENCE OF Xldv11Ds3NePPTPEntry
    ACCESS        not-accessible
    STATUS        mandatory
    DESCRIPTION
	 " The physical path termination point table for the DS3 IF. "
    ::= { xldv11Tlm 7 }

 xldv11Ds3NePPTPEntry OBJECT-TYPE
    -- info-NODE:    xldv11xldv11Ds3NePPTPEntry
    -- info-TREE:    xldv11Tlm
    -- info-INDEX:   xldv11IfIndex
    -- info-ACC:     nac
    -- info-SYNTAX:  Xldv11Ds3NePPTPEntry
    -- info-COMMENT: Entry of Ds3NePPTP table.
    -- info-IMPL:    V1.3A->
    SYNTAX        Xldv11Ds3NePPTPEntry
    ACCESS        not-accessible
    STATUS        mandatory
    DESCRIPTION
	 " An entry describing a termination point in the PPTP table.
	   Notifications : see xldv11IfEntry."
    INDEX         { xldv11IfIndex }
    ::= { xldv11Ds3NePPTPTable 1 }

 Xldv11Ds3NePPTPEntry ::=
    SEQUENCE { xldv11D3nType                       Xldv11LineType,
	       xldv11D3nCodingType                 Xldv11CodingType,
	       xldv11D3nPayloadScramblingActivate  Xldv11OperState,
	       xldv11D3nEmptyCellType              Xldv11EmptyCellType ,
	       xldv11D3nBandwidthUsage             INTEGER }

 xldv11D3nType OBJECT-TYPE
    -- info-LEAF:    xldv11D3nType
    -- info-TREE:    xldv11Tlm
    -- info-ACC:     ro
    -- info-SYNTAX:  Xldv11LineType 
    -- info-VALUE:   ds3plcp
    -- info-COMMENT: line type
    -- info-ROU:     GET db
    -- info-IMPL:    V1.3A->
    -- info-VERCTRL: -
    SYNTAX        Xldv11LineType
    ACCESS        read-only
    STATUS        mandatory
    DESCRIPTION
	 " This attribute repesents the interface type of the line
	   used for transmission.
	   Range of value: ds3plcp . "
    --DEFAULT next-function-async     fsnD3nEntryNext
    --DEFAULT get-function-async      fsnD3nEntryGet
    ::= { xldv11Ds3NePPTPEntry 1 }

 xldv11D3nCodingType OBJECT-TYPE
    -- info-LEAF:    xldv11D3nCodingType
    -- info-TREE:    xldv11Tlm
    -- info-ACC:     ro
    -- info-SYNTAX:  Xldv11CodingType
    -- info-VALUE:   dsx3B3ZS
    -- info-COMMENT: coding type
    -- info-ROU:     GET db
    -- info-IMPL:    V1.3A->
    -- info-VERCTRL: -
    SYNTAX        Xldv11CodingType
    ACCESS        read-only
    STATUS        mandatory
    DESCRIPTION
	 " This attribute represents the coding type of the line 
	   used for transmission.
	   Range of value: dsx3B3ZS . "
    --DEFAULT next-function-async     fsnD3nEntryNext
    --DEFAULT get-function-async      fsnD3nEntryGet
    ::= { xldv11Ds3NePPTPEntry 2 }

 xldv11D3nPayloadScramblingActivate OBJECT-TYPE
    -- info-LEAF:    xldv11D3nPayloadScramblingActivate
    -- info-TREE:    xldv11Tlm
    -- info-ACC:     rw
    -- info-SYNTAX:  Xldv11OperState
    -- info-VALUE:   enabled (default), disabled
    -- info-COMMENT: -
    -- info-ROU:     GET db SET tm
    -- info-IMPL:    V1.3A->
    -- info-VERCTRL: V1.1U..V1.2B: GET db SET blocked
    SYNTAX        Xldv11OperState
    ACCESS        read-write
    STATUS        mandatory
    DESCRIPTION
	 " This attribute states wheather the payload scrambling is activated.
	   Range of value: enabled (default), disabled . "
    --DEFAULT test-function-async     fsnD3nEntryTest
    --DEFAULT next-function-async     fsnD3nEntryNext
    --DEFAULT set-function-async      fsnD3nEntrySet
    --DEFAULT get-function-async      fsnD3nEntryGet
    ::= { xldv11Ds3NePPTPEntry 3 }

 xldv11D3nEmptyCellType OBJECT-TYPE
    -- info-LEAF:    xldv11D3nEmptyCellType
    -- info-TREE:    xldv11Tlm
    -- info-ACC:     rw
    -- info-SYNTAX:  Xldv11EmptyCellType
    -- info-VALUE:   idle, unassigned (default)
    -- info-COMMENT: type of empty cells
    -- info-ROU:     GET db SET tm
    -- info-IMPL:    V1.3A->
    -- info-VERCTRL: V1.1U..V1.2B: GET db SET blocked
    SYNTAX        Xldv11EmptyCellType 
    ACCESS        read-write
    STATUS        mandatory
    DESCRIPTION
	 " This attribute contains the type of empty cells.
	   Range of value: idle, unassigned (default) . "
    --DEFAULT test-function-async     fsnD3nEntryTest
    --DEFAULT next-function-async     fsnD3nEntryNext
    --DEFAULT set-function-async      fsnD3nEntrySet
    --DEFAULT get-function-async      fsnD3nEntryGet
    ::= { xldv11Ds3NePPTPEntry 4 }

 xldv11D3nBandwidthUsage OBJECT-TYPE
    -- info-LEAF:    xldv11D3nBandwidthUsage
    -- info-TREE:    xldv11Tlm
    -- info-ACC:     ro
    -- info-SYNTAX:  INTEGER 
    -- info-VALUE:   (0..100) Default 0
    -- info-COMMENT: Used Bandwidth
    -- info-ROU:     GET db  
    -- info-IMPL:    V1.13A->
    -- info-VERCTRL: -
    SYNTAX        INTEGER (0..100)
    ACCESS        read-only
    STATUS        mandatory
    DESCRIPTION
	 " The used Bandwidth in percent
	   Range of value: 0 ..100 (default = 0 ). "
    --DEFAULT next-function-async     fsnD3nEntryNext
    --DEFAULT get-function-async      fsnD3nEntryGet
    ::= { xldv11Ds3NePPTPEntry 5 }



 -- --------------------------------------------------------------
 --                   TLM E3 near-end PPTP Table
 -- --------------------------------------------------------------
 --
 -- This managed entity represents the extension for the PPTP at
 -- the E3 near-end interface. It includes the additional
 -- attributes to configure the E3 link.
 --

 xldv11E3NePPTPTable OBJECT-TYPE
    -- info-NODE:    xldv11E3NePPTPTable
    -- info-TREE:    xldv11Tlm
    -- info-ACC:     nac
    -- info-SYNTAX:  SEQUENCE OF Xldv11E3NePPTPEntry
    -- info-COMMENT: Table of e3n PPTP objects.
    -- info-IMPL:    V1.3A->
    SYNTAX        SEQUENCE OF Xldv11E3NePPTPEntry
    ACCESS        not-accessible
    STATUS        mandatory
    DESCRIPTION
	 " The physical path termination point table for the E3 IF. "
    ::= { xldv11Tlm 8 }

 xldv11E3NePPTPEntry OBJECT-TYPE
    -- info-NODE:    xldv11E3NePPTPEntry
    -- info-TREE:    xldv11Tlm
    -- info-INDEX:   xldv11IfIndex
    -- info-ACC:     nac
    -- info-SYNTAX:  Xldv11E3NePPTPEntry
    -- info-COMMENT: entry of e3n PPTP table.
    -- info-IMPL:    V1.3A->
    SYNTAX        Xldv11E3NePPTPEntry
    ACCESS        not-accessible
    STATUS        mandatory
    DESCRIPTION
	 " An entry describing a termination point in the PPTP table.
	   Notifications : see xldv11IfEntry."
    INDEX         { xldv11IfIndex }
    ::= { xldv11E3NePPTPTable 1 }

 Xldv11E3NePPTPEntry ::=
    SEQUENCE { xldv11E3nType                       Xldv11LineType,
	       xldv11E3nCodingType                 Xldv11CodingType,
	       xldv11E3nTrailTraceSend             OCTET STRING,
	       xldv11E3nTrailTraceSendDefault      Xldv11OperState,
	       xldv11E3nTrailTraceExpect           OCTET STRING,
	       xldv11E3nTrailTraceTIMDetectionActivate  Xldv11OperState,
	       xldv11E3nTrailTraceReceive          OCTET STRING,
	       xldv11E3nEmptyCellType              Xldv11EmptyCellType,
	       xldv11E3nPayloadType                Xldv11E3nPayloadType ,
	       xldv11E3nBandwidthUsage             INTEGER }

 xldv11E3nType OBJECT-TYPE
    -- info-LEAF:    xldv11E3nType
    -- info-TREE:    xldv11Tlm
    -- info-ACC:     ro
    -- info-SYNTAX:  Xldv11LineType 
    -- info-VALUE:   e3direct
    -- info-COMMENT: line type
    -- info-ROU:     GET db
    -- info-IMPL:    V1.3A->
    -- info-VERCTRL: -
    SYNTAX        Xldv11LineType
    ACCESS        read-only
    STATUS        mandatory
    DESCRIPTION
	 " This attribute repesents the interface type of the line
	   used for transmission.
	   Range of value: e3direct. "
    --DEFAULT next-function-async     fsnE3nEntryNext
    --DEFAULT get-function-async      fsnE3nEntryGet
    ::= { xldv11E3NePPTPEntry 1 }

 xldv11E3nCodingType OBJECT-TYPE
    -- info-LEAF:    xldv11E3nCodingType
    -- info-TREE:    xldv11Tlm
    -- info-ACC:     ro
    -- info-SYNTAX:  Xldv11CodingType
    -- info-VALUE:   e3HDB3
    -- info-COMMENT: coding type
    -- info-ROU:     GET db
    -- info-IMPL:    V1.3A->
    -- info-VERCTRL: -
    SYNTAX        Xldv11CodingType
    ACCESS        read-only
    STATUS        mandatory
    DESCRIPTION
	 " This attribute represents the coding type of the line 
	   used for transmission.
	   Range of value: e3HDB3 . "
    --DEFAULT next-function-async     fsnE3nEntryNext
    --DEFAULT get-function-async      fsnE3nEntryGet
    ::= { xldv11E3NePPTPEntry 2 }

 xldv11E3nTrailTraceSend OBJECT-TYPE
    -- info-LEAF:    xldv11E3nTrailTraceSend
    -- info-TREE:    xldv11Tlm
    -- info-ACC:     rw
    -- info-SYNTAX:  OCTET STRING ( SIZE (0..16) )
    -- info-VALUE:   default : 15 * 0x00
    -- info-VALUE:   15 times [ 0x00 .. 0x7F ]
    -- info-COMMENT: pattern to be sent to LE
    -- info-ROU:     GET db SET tm
    -- info-IMPL:    V1.3A->
    -- info-VERCTRL: V1.1U..V1.2B: GET db SET blocked
    SYNTAX        OCTET STRING ( SIZE (0..16) )
    ACCESS        read-write
    STATUS        mandatory
    DESCRIPTION
	 " This attribute represents the input signal used for the trail
	   trace send functionality.
	   15 times less or equal 0x7F (+ CRC) (default: 16 * 0x01) . "
    --DEFAULT test-function-async     fsnE3nEntryTest
    --DEFAULT next-function-async     fsnE3nEntryNext
    --DEFAULT set-function-async      fsnE3nEntrySet
    --DEFAULT get-function-async      fsnE3nEntryGet
    ::= { xldv11E3NePPTPEntry 3 }

 xldv11E3nTrailTraceSendDefault OBJECT-TYPE
    -- info-LEAF:    xldv11E3nTrailTraceSendDefault
    -- info-TREE:    xldv11Tlm
    -- info-ACC:     rw
    -- info-SYNTAX:  Xldv11OperState
    -- info-VALUE:   enabled (default), disabled
    -- info-COMMENT: A default trace value (enabled) or the pattern
    -- info-COMMENT: defined in the xldv11E3nTrailTraceSend attribute (disabled) will
    -- info-COMMENT: be sent.
    -- info-ROU:     GET db SET tm
    -- info-IMPL:    V1.3A->
    -- info-VERCTRL: V1.1U..V1.2B: GET db SET blocked
    SYNTAX        Xldv11OperState
    ACCESS        read-write
    STATUS        mandatory
    DESCRIPTION
	 " This attribute is used to configure the trail trace send
	   functionality. A default trace value (enabled) or the pattern
	   defined in the xldv11E3nTrailTraceSend attribute (disabled) will
	   be sent.
	   Range of values: enabled (default), disabled ."
    --DEFAULT test-function-async     fsnE3nEntryTest
    --DEFAULT next-function-async     fsnE3nEntryNext
    --DEFAULT set-function-async      fsnE3nEntrySet
    --DEFAULT get-function-async      fsnE3nEntryGet
    ::= { xldv11E3NePPTPEntry 4 }


 xldv11E3nTrailTraceExpect OBJECT-TYPE
    -- info-LEAF:    xldv11E3nTrailTraceExpect
    -- info-TREE:    xldv11Tlm
    -- info-ACC:     rw
    -- info-SYNTAX:  OCTET STRING ( SIZE (0..16) )
    -- info-VALUE:   default : 15 * 0x00
    -- info-VALUE:   15 times [ 0x00 .. 0x7F ]
    -- info-COMMENT: expected pattern
    -- info-ROU:     GET db SET tm 
    -- info-IMPL:    V1.3A->
    -- info-VERCTRL: V1.1U..V1.2B: GET db SET blocked
    SYNTAX        OCTET STRING ( SIZE (0..16) )
    ACCESS        read-write
    STATUS        mandatory
    DESCRIPTION
	 " This attribute represents the expected result of a trail trace
	   operation. It will be compared with the value of the
	   E3nTrailTraceReceive attribute provided that the attribute
	   E3nTrailTraceTIMDetection is enabled. "
    --DEFAULT test-function-async     fsnE3nEntryTest
    --DEFAULT next-function-async     fsnE3nEntryNext
    --DEFAULT set-function-async      fsnE3nEntrySet
    --DEFAULT get-function-async      fsnE3nEntryGet
    ::= { xldv11E3NePPTPEntry 5 }

 xldv11E3nTrailTraceTIMDetectionActivate OBJECT-TYPE
    -- info-LEAF:    xldv11E3nTrailTraceTIMDetectionActivate
    -- info-TREE:    xldv11Tlm
    -- info-ACC:     rw
    -- info-SYNTAX:  Xldv11OperState
    -- info-VALUE:   enabled, disabled (default)
    -- info-COMMENT: enables/disables signal comparison
    -- info-ROU:     GET db SET tm
    -- info-IMPL:    V1.3A->
    -- info-VERCTRL: V1.1U..V1.2B: GET db SET blocked
    SYNTAX        Xldv11OperState
    ACCESS        read-write
    STATUS        mandatory
    DESCRIPTION
	 " This attribute activates the comparsion of the signals
	   E3nTrailTraceExpect and E3nTrailTraceReceive.
	   Range of values: enabled, disabled (default) . "
    --DEFAULT test-function-async     fsnE3nEntryTest
    --DEFAULT next-function-async     fsnE3nEntryNext
    --DEFAULT set-function-async      fsnE3nEntrySet
    --DEFAULT get-function-async      fsnE3nEntryGet
    ::= { xldv11E3NePPTPEntry 6 }

 xldv11E3nTrailTraceReceive OBJECT-TYPE
    -- info-LEAF:    xldv11E3nTrailTraceReceive
    -- info-TREE:    xldv11Tlm
    -- info-ACC:     ro
    -- info-SYNTAX:  OCTET STRING ( SIZE (0..16) )
    -- info-VALUE:   15 times <= 0x7F
    -- info-COMMENT: received pattern
    -- info-ROU:     GET tm
    -- info-IMPL:    V1.3A->
    -- info-VERCTRL: V1.1U..V1.2B: GET tmn SET blocked
    SYNTAX        OCTET STRING ( SIZE (0..16) )
    ACCESS        read-only
    STATUS        mandatory
    DESCRIPTION
	 " This attribute represents the received trail
	   trace value from the LE."
    --DEFAULT next-function-async     fsnE3nEntryNext
    --DEFAULT get-function-async      fsnE3nEntryGet
    ::= { xldv11E3NePPTPEntry 7 }

 xldv11E3nEmptyCellType OBJECT-TYPE
    -- info-LEAF:    xldv11E3nEmptyCellType
    -- info-TREE:    xldv11Tlm
    -- info-ACC:     rw
    -- info-SYNTAX:  Xldv11EmptyCellType
    -- info-VALUE:   idle (default), unassigned
    -- info-COMMENT: type of empty cells
    -- info-ROU:     GET db SET tm
    -- info-IMPL:    V1.3A->
    -- info-VERCTRL: V1.1U..V1.2B: GET db SET blocked
    SYNTAX        Xldv11EmptyCellType
    ACCESS        read-write
    STATUS        mandatory
    DESCRIPTION
	 " This attribute contains the type of empty cells.
	   Range of value: idle (default), unassigned . "
    --DEFAULT test-function-async     fsnE3nEntryTest
    --DEFAULT next-function-async     fsnE3nEntryNext
    --DEFAULT set-function-async      fsnE3nEntrySet
    --DEFAULT get-function-async      fsnE3nEntryGet
    ::= { xldv11E3NePPTPEntry 8 }

 xldv11E3nPayloadType OBJECT-TYPE
    -- info-LEAF:    xldv11E3nPayloadType
    -- info-TREE:    xldv11Tlm
    -- info-ACC:     ro
    -- info-SYNTAX:  Xldv11E3nPayloadType
    -- info-VALUE:   unequipped(1), nonSpecific(2),
    -- info-VALUE:   atm(3) (default) 
    -- info-COMMENT: received payload type
    -- info-ROU:     GET tm 
    -- info-IMPL:    V1.3A->
    -- info-VERCTRL: -
    SYNTAX        Xldv11E3nPayloadType
    ACCESS        read-only
    STATUS        mandatory
    DESCRIPTION
	 " This attribute contains the received payload type.
	   Range of value: unequipped, nonSpecific,
	   atm (default) ."
    --DEFAULT next-function-async     fsnE3nEntryNext
    --DEFAULT get-function-async      fsnE3nEntryGet
    ::= { xldv11E3NePPTPEntry 9 }

 xldv11E3nBandwidthUsage OBJECT-TYPE
    -- info-LEAF:    xldv11E3nBandwidthUsage
    -- info-TREE:    xldv11Tlm
    -- info-ACC:     ro
    -- info-SYNTAX:  INTEGER 
    -- info-VALUE:   (0..100) Default 0
    -- info-COMMENT: Used Bandwidth
    -- info-ROU:     GET db  
    -- info-IMPL:    V1.3A->
    -- info-VERCTRL: -
    SYNTAX        INTEGER (0..100)
    ACCESS        read-only
    STATUS        mandatory
    DESCRIPTION
	 " The used bandwidth in percent.
	   Range of value: 0 ..100 (default = 0 ). "
    --DEFAULT next-function-async     fsnE3nEntryNext
    --DEFAULT get-function-async      fsnE3nEntryGet
    ::= { xldv11E3NePPTPEntry 10 }



 -- --------------------------------------------------------------

 -- --------------------------------------------------------------
 --                 TLM STM1 near-end PPTP Table
 -- --------------------------------------------------------------
 --
 -- This managed entity represents the extension for the PPTP at
 -- the STM1 near-end interface. It includes the additional
 -- attributes to configure the STM1 link.
 -- Valid for XLDV1.1U
 --

 xldv11Stm1NePPTPTable OBJECT-TYPE
    -- info-NODE:    xldv11Stm1NePPTPTable
    -- info-TREE:    xldv11Tlm
    -- info-ACC:     nac
    -- info-SYNTAX:  SEQUENCE OF Xldv11Stm1NePPTPEntry
    -- info-COMMENT: The PPTP table for the STM1 IF.
    -- info-IMPL:    V1.0->
    SYNTAX        SEQUENCE OF Xldv11Stm1NePPTPEntry
    ACCESS        not-accessible
    STATUS        mandatory
    DESCRIPTION
	 " The physical path termination point table for the STM1 IF. "
    ::= { xldv11Tlm 9 }

 xldv11Stm1NePPTPEntry OBJECT-TYPE
    -- info-NODE:    xldv11Stm1NePPTPEntry
    -- info-TREE:    xldv11Tlm
    -- info-INDEX:   xldv11IfIndex
    -- info-ACC:     nac
    -- info-SYNTAX:  Xldv11Stm1NePPTPEntry
    -- info-COMMENT: An entry of the PPTP table.
    -- info-IMPL:    V1.0->
    SYNTAX        Xldv11Stm1NePPTPEntry
    ACCESS        not-accessible
    STATUS        mandatory
    DESCRIPTION
	 " An entry describing a termination point in the PPTP table.
	   Notifications : see xldv11IfEntry."
    INDEX         { xldv11IfIndex }
    ::= { xldv11Stm1NePPTPTable 1 }

 Xldv11Stm1NePPTPEntry ::=
    SEQUENCE { xldv11S1nLineType                 Xldv11LineType,
	       xldv11S1nPathTraceSend            OCTET STRING,
	       xldv11S1nPathTraceSendDefault     Xldv11OperState,
	       xldv11S1nPathTraceExpect          OCTET STRING,
	       xldv11S1nPathTraceTIMDetectionActivate  Xldv11OperState,
	       xldv11S1nPathTraceReceive         OCTET STRING,
	       xldv11S1nHpEberThreshold          Xldv11S1nS3nEberThreshold,
	       xldv11S1nMsEberThreshold          Xldv11S1nS3nEberThreshold,
	       xldv11S1nRsEberThreshold          Xldv11S1nS3nEberThreshold,
	       xldv11S1nSDThreshold              Xldv11S1nS3nSDThreshold,
	       xldv11S1nRDIAISOnEber             Xldv11OperState,
	       xldv11S1nSignalLabelReceive       Integer32,
	       xldv11S1nEmptyCellType            Xldv11EmptyCellType ,
	       xldv11S1nBandwidthUsage           INTEGER }

 xldv11S1nLineType OBJECT-TYPE
    -- info-LEAF:    xldv11S1nLineType
    -- info-TREE:    xldv11Tlm
    -- info-ACC:     ro
    -- info-SYNTAX:  Xldv11LineType 
    -- info-VALUE:   mediumSingleMode,
    -- info-VALUE:   longSingleMode(V1.2A->), coax(V1.3->)
    -- info-COMMENT: line type
    -- info-ROU:     GET db
    -- info-IMPL:    V1.3A->
    SYNTAX        Xldv11LineType
    ACCESS        read-only
    STATUS        mandatory
    DESCRIPTION
	 " The physical medium of the line used for transmission.
	   XLDV1.0, XLDV1.1U : only mediumSingleMode,
	   XLDV1.2 : only mediumSingleMode or longSingleMode. "
    --DEFAULT next-function-async     fsnS1nEntryNext
    --DEFAULT get-function-async      fsnS1nEntryGet
    ::= { xldv11Stm1NePPTPEntry 1 }

 xldv11S1nPathTraceSend OBJECT-TYPE
    -- info-LEAF:    xldv11S1nPathTraceSend
    -- info-TREE:    xldv11Tlm
    -- info-ACC:     rw
    -- info-SYNTAX:  OCTET STRING ( SIZE (0..16) )
    -- info-VALUE:   1'st byte: any value (CRC incl. Sync-Bit)
    -- info-VALUE:   1'st byte: inserted value will be ignored by ONU and
    -- info-VALUE:   generated itself by ONU.                        
    -- info-VALUE:   2'nd-16'th byte: value <= 0x7F
    -- info-COMMENT: Pattern to be sent to the LE (CRC + 15 bytes)
    -- info-ROU:     GET db  SET tm 
    -- info-IMPL:    V1.0->
    -- info-VERCTRL: -
    SYNTAX        OCTET STRING ( SIZE (0..16) )
    ACCESS        read-write
    STATUS        mandatory
    DESCRIPTION
	 " This attribute represents the input signal used for the path
	   trace send functionality.
	   1'st byte: any value (CRC incl. Sync-Bit) .
	   1'st byte: inserted value will be ignored by ONU and generated
		      itself by ONU. 
	   2'nd-16'th byte: value <=0x7F. "
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 2 }

 xldv11S1nPathTraceSendDefault OBJECT-TYPE
    -- info-LEAF:    xldv11S1nPathTraceSendDefault
    -- info-TREE:    xldv11Tlm
    -- info-ACC:     rw
    -- info-SYNTAX:  Xldv11OperState
    -- info-VALUE:   enabled(1), disabled(2)
    -- info-VALUE:   default: enabled
    -- info-COMMENT: Configure the path trace send functionality.
    -- info-ROU:     GET db  SET tm 
    -- info-IMPL:    V1.1U->
    -- info-VERCTRL: -
    SYNTAX        Xldv11OperState
    ACCESS        read-write
    STATUS        mandatory
    DESCRIPTION
	 " This attribute is used to configure the path trace send
	   functionality.
	   A default path trace value (enabled) or the pattern
	   defined in the xldv11S1nPathTraceSend attribute (disabled) will
	   be sent.
	   Range of values: enabled (default), disabled ."
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 3 }

 xldv11S1nPathTraceExpect OBJECT-TYPE
    -- info-LEAF:    xldv11S1nPathTraceExpect
    -- info-TREE:    xldv11Tlm
    -- info-ACC:     rw
    -- info-SYNTAX:  OCTET STRING ( SIZE (0..16) )
    -- info-VALUE:   1'st byte: any value (CRC incl. Sync-Bit)
    -- info-VALUE:   1'st byte: inserted value will be ignored by ONU and
    -- info-VALUE:   generated itself by ONU.                        
    -- info-VALUE:   2'nd-16'th byte: value <= 0x7F
    -- info-COMMENT: Represents the expected result of a path trace operation.
    -- info-ROU:     GET db  SET tm
    -- info-IMPL:    V1.0->
    -- info-VERCTRL: -
    SYNTAX        OCTET STRING ( SIZE (0..16) )
    ACCESS        read-write
    STATUS        mandatory
    DESCRIPTION
	 " This attribute represents the expected result of a path trace
	   operation. This signal will be compared with the
	   S1nPathTraceReceive, when the Attribute
	   S1nPathTraceTIMDetectionActivate is enabled. If the comparison 
	   detects unequality an alarm notification (TIM) is sent.
	   1'st byte: any value (CRC incl. Sync-Bit).
	   1'st byte: inserted value will be ignored by ONU and generated itself by ONU. 
	   2'nd-16'th byte: value <= 0x7F"
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 4 }

 xldv11S1nPathTraceTIMDetectionActivate OBJECT-TYPE
    -- info-LEAF:    xldv11S1nPathTraceTIMDetectionActivate
    -- info-TREE:    xldv11Tlm
    -- info-ACC:     rw
    -- info-SYNTAX:  Xldv11OperState
    -- info-VALUE:   enabled(1), disabled(2) (default)
    -- info-COMMENT: A default value (enabled) or the pattern defined in the
    -- info-COMMENT: xldv11S1nPathTraceSend attribute will be sent.
    -- info-ROU:     GET db  SET tm
    -- info-IMPL:    V1.1U->
    -- info-VERCTRL: -
    SYNTAX        Xldv11OperState
    ACCESS        read-write
    STATUS        mandatory
    DESCRIPTION
	 " A default value (enabled) or the pattern defined in the
	   xldv11S1nPathTraceSend attribute will be sent.
	   Range of values: enabled, disabled (default) . "
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 5 }

 xldv11S1nPathTraceReceive OBJECT-TYPE
    -- info-LEAF:    xldv11S1nPathTraceReceive
    -- info-TREE:    xldv11Tlm
    -- info-ACC:     ro
    -- info-SYNTAX:  OCTET STRING ( SIZE (0..16) )
    -- info-VALUE:   1'st byte: CRC (incl. Sync-Bit)
    -- info-VALUE:   2'nd-16'th byte: value <= 0x7F
    -- info-COMMENT: Represents the received path trace value from the LE.
    -- info-ROU:     GET db
    -- info-IMPL:    V1.0->
    -- info-VERCTRL: -
    SYNTAX        OCTET STRING ( SIZE (0..16) )
    ACCESS        read-only
    STATUS        mandatory
    DESCRIPTION
	 " This attribute represents the received path trace value from the
	   LE. 1'st byte: CRC (incl. sync-bit) + 2'nd-16'th byte: value <= 0x7F. "
    --DEFAULT next-function-async     fsnS1nEntryNext
    --DEFAULT get-function-async      fsnS1nEntryGet
    ::= { xldv11Stm1NePPTPEntry 6 }

 xldv11S1nHpEberThreshold OBJECT-TYPE
    -- info-LEAF:    xldv11S1nHpEberThreshold
    -- info-TREE:    xldv11Tlm
    -- info-ACC:     rw
    -- info-SYNTAX:  Xldv11S1nS3nEberThreshold
    -- info-VALUE:   exp10E3(1), exp10E4(2), exp10E5(3), noSupervision(255)
    -- info-VALUE:   default: exp10E3
    -- info-COMMENT: Represents the threshold for the higher-order path
    -- info-COMMENT: excessive bit error check.
    -- info-COMMENT: Value corresponds to exponent 10E-3, ...., 10E-5
    -- info-ROU:     GET db  SET tm 
    -- info-IMPL:    V1.0->
    -- info-VERCTRL: -
    SYNTAX        Xldv11S1nS3nEberThreshold
    ACCESS        read-write
    STATUS        mandatory
    DESCRIPTION
	 " This attribute represents the threshold for the higher-order path
	   excessive bit error check.
	   Range of values:
	      noSupervision,
	      exp10E3 (default),
	      exp10E4,
	      exp10E5 . "
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 7 }

 xldv11S1nMsEberThreshold OBJECT-TYPE
    -- info-LEAF:    xldv11S1nMsEberThreshold
    -- info-TREE:    xldv11Tlm
    -- info-ACC:     rw
    -- info-SYNTAX:  Xldv11S1nS3nEberThreshold
    -- info-VALUE:   exp10E3(1), exp10E4(2), exp10E5(3), noSupervision(255)
    -- info-VALUE:   default: exp10E3
    -- info-COMMENT: Represents the threshold for the multiplexer
    -- info-COMMENT: section excessive bit error check.
    -- info-COMMENT: Value corresponds to exponent 10E-3, ...., 10E-5
    -- info-ROU:     GET db  SET tm 
    -- info-IMPL:    V1.0->
    -- info-VERCTRL: -
    SYNTAX        Xldv11S1nS3nEberThreshold
    ACCESS        read-write
    STATUS        mandatory
    DESCRIPTION
	 " This attribute represents the threshold for the multiplexer
	   section excessive bit error check.
	   Range of values:
	      noSupervision,
	      exp10E3 (default),
	      exp10E4,
	      exp10E5 . "
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 8 }

 xldv11S1nRsEberThreshold OBJECT-TYPE
    -- info-LEAF:    xldv11S1nRsEberThreshold
    -- info-TREE:    xldv11Tlm
    -- info-ACC:     rw
    -- info-SYNTAX:  Xldv11S1nS3nEberThreshold
    -- info-VALUE:   exp10E3(1), exp10E4(2), exp10E5(3), noSupervision(255)
    -- info-VALUE:   default: exp10E3
    -- info-COMMENT: Represents the threshold for the repeater section
    -- info-COMMENT: excessive bit error check.
    -- info-COMMENT: Value corresponds to exponent 10E-3, ...., 10E-5
    -- info-ROU:     GET db  SET tm 
    -- info-IMPL:    V1.0->
    -- info-VERCTRL: -
    SYNTAX        Xldv11S1nS3nEberThreshold
    ACCESS        read-write
    STATUS        mandatory
    DESCRIPTION
	 " This attribute represents the threshold for the repeater section
	   excessive bit error check.
	   Range of values:
	      noSupervision,
	      exp10E3 (default),
	      exp10E4,
	      exp10E5 . "
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 9 }

 xldv11S1nSDThreshold OBJECT-TYPE
    -- info-LEAF:    xldv11S1nSDThreshold
    -- info-TREE:    xldv11Tlm
    -- info-ACC:     rw
    -- info-SYNTAX:  Xldv11S1nS3nSDThreshold
    -- info-VALUE:   exp10E5(3), exp10E6(4), exp10E7(5), exp10E8(6), exp10E9(7),
    -- info-VALUE:   noSupervision(255)
    -- info-VALUE:   default: exp10E9
    -- info-COMMENT: Represents the threshold for the signal degration check.
    -- info-COMMENT: Value corresponds to exponent 10E-3, ...., 10E-5
    -- info-ROU:     GET db  SET tm 
    -- info-IMPL:    V1.0->
    -- info-VERCTRL: -
    SYNTAX        Xldv11S1nS3nSDThreshold
    ACCESS        read-write
    STATUS        mandatory
    DESCRIPTION
	 " This attribute represents the threshold for the signal degration
	   check.
	   Range of values:
	      noSupervision,
	      exp10E5,
	      exp10E6,
	      exp10E7,
	      exp10E8,
	      exp10E9 (default) . "
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 10 }


 xldv11S1nRDIAISOnEber OBJECT-TYPE
    -- info-LEAF:    xldv11S1nRDIAISOnEber
    -- info-TREE:    xldv11Tlm
    -- info-ACC:     rw
    -- info-SYNTAX:  Xldv11OperState
    -- info-VALUE:   enabled(1) (default), disabled(2)
    -- info-COMMENT: Used to configure the RDI-and VP-AIS generation
    -- info-COMMENT: on defect excessive bit ratio.
    -- info-ROU:     GET db  SET tm 
    -- info-IMPL:    V1.1U->
    -- info-VERCTRL: -
    SYNTAX        Xldv11OperState
    ACCESS        read-write
    STATUS        mandatory
    DESCRIPTION
	 " This attribute is used to configure the RDI-and VP-AIS generation
	   on defect excessive bit ratio.
	   Range of Values: enabled (default), disabled. "
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 11 }

 xldv11S1nSignalLabelReceive OBJECT-TYPE
    -- info-LEAF:    xldv11S1nSignalLabelReceive
    -- info-TREE:    xldv11Tlm
    -- info-ACC:     ro
    -- info-SYNTAX:  Integer32
    -- info-VALUE:   0 ... 255
    -- info-COMMENT: Represents the real result of a trace
    -- info-COMMENT: operation received signal label value from the LE.
    -- info-ROU:     GET tm 
    -- info-IMPL:    V1.1U->
    -- info-VERCTRL: -
    SYNTAX        Integer32
    ACCESS        read-only
    STATUS        mandatory
    DESCRIPTION
	  " This attribute represents the real result of a trace
	    operation received signal label value from
	    the LE." 

    --DEFAULT next-function-async     fsnS1nEntryNext
    --DEFAULT get-function-async      fsnS1nEntryGet
    ::= { xldv11Stm1NePPTPEntry 12 }


 xldv11S1nEmptyCellType OBJECT-TYPE
    -- info-LEAF:    xldv11S1nEmptyCellType
    -- info-TREE:    xldv11Tlm
    -- info-ACC:     rw
    -- info-SYNTAX:  Xldv11EmptyCellType
    -- info-VALUE:   idle (default), unassigned
    -- info-COMMENT: Type of empty cells.
    -- info-ROU:     GET db  SET tm 
    -- info-IMPL:    V1.1U->
    -- info-VERCTRL: -
    SYNTAX        Xldv11EmptyCellType
    ACCESS        read-write
    STATUS        mandatory
    DESCRIPTION
	 " This attribute contains the type of empty cells.
	   Range of value: idle (default), unassigned . "
    --DEFAULT test-function-async     fsnS1nEntryTest
    --DEFAULT next-function-async     fsnS1nEntryNext
    --DEFAULT set-function-async      fsnS1nEntrySet
    --DEFAULT get-function-async      fsnS1nEntryGet
    ::= { xldv11Stm1NePPTPEntry 13 }

 xldv11S1nBandwidthUsage OBJECT-TYPE
    -- info-LEAF:    xldv11S1nBandwidthUsage
    -- info-TREE:    xldv11Tlm
    -- info-ACC:     ro
    -- info-SYNTAX:  INTEGER 
    -- info-VALUE:   (0..100) Default 0
    -- info-COMMENT: Used Bandwidth
    -- info-ROU:     GET db  
    -- info-IMPL:    V1.13a->
    -- info-VERCTRL: -
    SYNTAX        INTEGER (0..100)
    ACCESS        read-only
    STATUS        mandatory
    DESCRIPTION
	 " The used Bandwidth in percent
	   Range of value: 0 ..100 (default = 0 ). "
    --DEFAULT next-function-async     fsnS1nEntryNext
    --DEFAULT get-function-async      fsnS1nEntryGet
    ::= { xldv11Stm1NePPTPEntry 14 }

 -- --------------------------------------------------------------
 --                 TLM STS3c near-end PPTP Table
 -- --------------------------------------------------------------
 --
 -- This managed entity represents the extension for the PPTP at
 -- the STS3 near end interface. It includes the additional
 -- attributes to configure the STS3 link.
 --

 xldv11Sts3NePPTPTable OBJECT-TYPE
    -- info-NODE:    xldv11Sts3NePPTPTable
    -- info-TREE:    xldv11Tlm
    -- info-ACC:     nac
    -- info-SYNTAX:  SEQUENCE OF Xldv11Sts3NePPTPEntry
    -- info-COMMENT: PPTP table for the STS3c IF.
    -- info-IMPL:    V1.2A->
    SYNTAX        SEQUENCE OF Xldv11Sts3NePPTPEntry
    ACCESS        not-accessible
    STATUS        mandatory
    DESCRIPTION
	 " The physical path termination point table for the STS3c IF. "
    ::= { xldv11Tlm 10 }

 xldv11Sts3NePPTPEntry OBJECT-TYPE
    -- info-NODE:    xldv11Sts3NePPTPEntry
    -- info-TREE:    xldv11Tlm
    -- info-INDEX:   xldv11IfIndex
    -- info-ACC:     nac
    -- info-SYNTAX:  Xldv11Sts3NePPTPEntry
    -- info-COMMENT: Entry of PPTP table for the STS3c IF.
    -- info-IMPL:    V1.2A->
    SYNTAX        Xldv11Sts3NePPTPEntry
    ACCESS        not-accessible
    STATUS        mandatory
    DESCRIPTION
	 " An entry describing a termination point in the PPTP table.
	   Notifications : see xldv11IfEntry."
    INDEX         { xldv11IfIndex }
    ::= { xldv11Sts3NePPTPTable 1 }

 Xldv11Sts3NePPTPEntry ::=
    SEQUENCE { xldv11S3nLineType                 Xldv11LineType,
	       xldv11S3nPathTraceSend            OCTET STRING ( SIZE (0..16) ),
	       xldv11S3nPathTraceSendDefault     Xldv11OperState,
	       xldv11S3nPathTraceExpect          OCTET STRING ( SIZE (0..16) ),
	       xldv11S3nPathTraceTIMDetectionActivate  Xldv11OperState,
	       xldv11S3nPathTraceReceive         OCTET STRING ( SIZE (0..16) ),
	       xldv11S3nPathTraceSync            Xldv11OperState,
	       xldv11S3nPathTraceSendCRCActivate     Xldv11OperState,
	       xldv11S3nPathTraceReceiveCRCActivate  Xldv11OperState,
	       xldv11S3nHpEberThreshold          Xldv11S1nS3nEberThreshold,
	       xldv11S3nMsEberThreshold          Xldv11S1nS3nEberThreshold,
	       xldv11S3nRsEberThreshold          Xldv11S1nS3nEberThreshold,
	       xldv11S3nSDThreshold              Xldv11S1nS3nSDThreshold,
	       xldv11S3nSignalLabelReceive       Integer32,
	       xldv11S3nEmptyCellType            Xldv11EmptyCellType,
	       xldv11S3nBandwidthUsage           INTEGER  }

 xldv11S3nLineType OBJECT-TYPE
    -- info-LEAF:    xldv11S3nLineType
    -- info-TREE:    xldv11Tlm
    -- info-ACC:     ro
    -- info-SYNTAX:  Xldv11LineType
    -- info-VALUE:   other(1), shortSingleMode(2), mediumSingleMode(3)
    -- info-VALUE:   longSingleMode(4), coax(5), utp(6)
    -- info-COMMENT: The physical medium of the line used for transmission.
    -- info-COMMENT: XLDV1.1U : only mediumSingleMode,
    -- info-COMMENT: XLDV1.1 : mediumSingleMode or longSingleMode.
    -- info-ROU:     GET db 
    -- info-IMPL:    V1.2A->
    -- info-VERCTRL: GET db
    SYNTAX        Xldv11LineType
    ACCESS        read-only
    STATUS        mandatory
    DESCRIPTION
	 " The physical medium of the line used for transmission.
	   XLDV1.1u : only mediumSingleMode,
	   XLDV1.1 : only mediumSingleMode or longSingleMode.
	   Range of value:
	      other,
	      shortSingleMode,
	      mediumSingleMode (default), 
	      longSingleMode,
	      coax,
	      utp . "
    --DEFAULT next-function-async     fsnS3nEntryNext
    --DEFAULT get-function-async      fsnS3nEntryGet
    ::= { xldv11Sts3NePPTPEntry 1 }

 xldv11S3nPathTraceSend OBJECT-TYPE
    -- info-LEAF:    xldv11S3nPathTraceSend
    -- info-TREE:    xldv11Tlm
    -- info-ACC:     rw
    -- info-SYNTAX:  OCTET STRING ( SIZE (0..16) )
    -- info-VALUE:   16 times <= 0x7F
    -- info-VALUE:   (case CRC enabled / Sync-Bit enabled):
    -- info-VALUE:   * 1'st byte: CRC+Sync-Bit +
    -- info-VALUE:     15 times less or equal 0x7F
    -- info-VALUE:     (default: 16 * 0x00)
    -- info-VALUE:   (case CRC enabled / Sync-Bit disabled):
    -- info-VALUE:   * 1'st byte: CRC-no-Sync-Bit +
    -- info-VALUE:     15 times less or equal 0x7F
    -- info-VALUE:     (default: 16 * 0x00)
    -- info-VALUE:   (case CRC disabled / Sync-Bit enabled):
    -- info-VALUE:   * 16 times less or equal 0x7F
    -- info-VALUE:     (default: 16 * 0x00)
    -- info-VALUE:     == value from set-request + Sync-Bit
    -- info-VALUE:   * The first bit of the first byte is set
    -- info-VALUE:   (case CRC disabled / Sync-Bit disabled):
    -- info-VALUE:   * 16 times less or equal 0x7F
    -- info-VALUE:     (default: 16 * 0x00)
    -- info-VALUE:      == value from set-request / no Sync-Bit
    -- info-VALUE:   * The first bit of the first byte is not set
    -- info-COMMENT: Represents the input signal used for the path
    -- info-COMMENT: trace send functionality.
    -- info-COMMENT: Pattern to be sent to the LE (15 bytes + CRC-byte).
    -- info-COMMENT: CRC enabled:  1'st byte: any value + 15 times less or equal 0x7F (default: 16 * 0x00)
    -- info-COMMENT: CRC disabled: 16 times less or equal 0x7F (default: 16 * 0x00)
    -- info-COMMENT: CRC disabled: The first bit of the first byte depends on the PathTraceSync flag.
    -- info-ROU:     GET db  SET tm 
    -- info-IMPL:    V1.2A->
    -- info-VERCTRL: GET db  SET asw
    SYNTAX        OCTET STRING ( SIZE (0..16) )
    ACCESS        read-write
    STATUS        mandatory
    DESCRIPTION
	 " This attribute represents the input signal used for the path
	   trace send functionality.
	  16 times <= 0x7F
	  (case CRC enabled / Sync-Bit enabled):
	  * 1'st byte: CRC+Sync-Bit +
	    15 times less or equal 0x7F
	    (default: 16 * 0x00)
	  (case CRC enabled / Sync-Bit disabled):
	  * 1'st byte: CRC-no-Sync-Bit +
	    15 times less or equal 0x7F
	    (default: 16 * 0x00)
	  (case CRC disabled / Sync-Bit enabled):
	  * 16 times less or equal 0x7F
	    (default: 16 * 0x00)
	    == value from set-request + Sync-Bit
	  * The first bit of the first byte is set
	  (case CRC disabled / Sync-Bit disabled):
	  * 16 times less or equal 0x7F
	    (default: 16 * 0x00)
	     == value from set-request / no Sync-Bit
	  * The first bit of the first byte is not set. "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 2 }

 xldv11S3nPathTraceSendDefault OBJECT-TYPE
    -- info-LEAF:    xldv11S3nPathTraceSendDefault
    -- info-TREE:    xldv11Tlm
    -- info-ACC:     rw
    -- info-SYNTAX:  Xldv11OperState
    -- info-VALUE:   enabled(1) (default), disabled(2)
    -- info-COMMENT: enabled: a default trace value will be sent (16*0x00).
    -- info-COMMENT: disabled: the pattern defined in the
    -- info-COMMENT: xldv11S3nPathTraceSend attribute will be sent.
    -- info-ROU:     GET db  SET tm 
    -- info-IMPL:    V1.2A->
    -- info-VERCTRL: GET db  SET asw
    SYNTAX        Xldv11OperState
    ACCESS        read-write
    STATUS        mandatory
    DESCRIPTION
	 " This attribute is used to configure the path trace send
	   functionality.
	   A default path trace value (enabled) or the pattern
	   defined in the xldv11S3nPathTraceSend attribute (disabled) will
	   be sent.
	   Range of values: enabled (default), disabled ."
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 3 }

 xldv11S3nPathTraceExpect OBJECT-TYPE
    -- info-LEAF:    xldv11S3nPathTraceExpect
    -- info-TREE:    xldv11Tlm
    -- info-ACC:     rw
    -- info-SYNTAX   OCTET STRING ( SIZE (0..16) )
    -- info-VALUE:   (case received CRC enabled):
    -- info-VALUE:   * 1'st byte: any value (will be ignored by the ONU and generated itself)
    -- info-VALUE:   (case received CRC disabled): * 16 times less or equal 0x7F.
    -- info-VALUE:   + 15 times less or equal 0x7F (default: 16 * 0x00).
    -- info-COMMENT: Represents the expected result of a path trace operation.
    -- info-ROU:     GET db  SET tm 
    -- info-IMPL:    V1.2A->
    -- info-VERCTRL: GET db  SET asw
    SYNTAX        OCTET STRING ( SIZE (0..16) )
    ACCESS        read-write
    STATUS        mandatory
    DESCRIPTION
	 " This attribute represents the expected result of a path trace
	   operation. This signal will be compared with the
	   S3nPathTraceReceive, when the Attribute
	   S3nPathTraceTIMDetectionActivate is enabled. If the comparison detects
	   unequality an alarm notification (TIM) is sent. When CRC is
	   activated, only the first 15 bytes are compared. 
	   (case received CRC enabled):
	   * 1'st byte: any value (will be ignored by the ONU and generated itself) +
			 15 times less or equal 0x7F
	   (case received CRC disabled):
	   * 16 times less or equal 0x7F ."
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 4 }

 xldv11S3nPathTraceTIMDetectionActivate OBJECT-TYPE
    -- info-LEAF:    xldv11S3nPathTraceTIMDetectionActivate
    -- info-TREE:    xldv11Tlm
    -- info-ACC:     rw
    -- info-SYNTAX:  Xldv11OperState
    -- info-VALUE:   enabled(1), disabled(2) (default)
    -- info-COMMENT: Activates the comparsion of the signals
    -- info-COMMENT: S3nPathTraceExpect and S3nPathTraceReceive.
    -- info-ROU:     GET db  SET tm 
    -- info-ROU:     GET db  SET tm 
    -- info-IMPL:    V1.2A->
    -- info-VERCTRL: GET db  SET asw
    SYNTAX        Xldv11OperState
    ACCESS        read-write
    STATUS        mandatory
    DESCRIPTION
	 " This attribute activates the comparsion of the signals
	   S3nPathTraceExpect and S3nPathTraceReceive.
	   Range of values: enabled, disabled (default) . "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 5 }

 xldv11S3nPathTraceReceive OBJECT-TYPE
    -- info-LEAF:    xldv11S3nPathTraceReceive
    -- info-TREE:    xldv11Tlm
    -- info-ACC:     ro
    -- info-SYNTAX:  OCTET STRING ( SIZE (0..16) )
    -- info-VALUE:   1'st byte: maybe CRC (incl. sync-bit) + 15 times <= 0x7F
    -- info-COMMENT: Represents the received path trace value from the LE.
    -- info-ROU:     GET tm 
    -- info-IMPL:    V1.2A->
    -- info-VERCTRL: GET asw
    SYNTAX        OCTET STRING ( SIZE (0..16) )
    ACCESS        read-only
    STATUS        mandatory
    DESCRIPTION
	 " This attribute represents the received path trace value from the
	   LE. * 1'st byte: maybe CRC (incl. sync-bit) + 15 times <= 0x7F. "
    --DEFAULT next-function-async     fsnS3nEntryNext
    --DEFAULT get-function-async      fsnS3nEntryGet
    ::= { xldv11Sts3NePPTPEntry 6 }

 xldv11S3nPathTraceSync OBJECT-TYPE
    -- info-LEAF:    xldv11S3nPathTraceSync
    -- info-TREE:    xldv11Tlm
    -- info-ACC:     rw
    -- info-SYNTAX:  Xldv11OperState
    -- info-VALUE:   enabled(1), disabled(2)
    -- info-COMMENT: Used to configure the sync-bit generation.
    -- info-COMMENT: Path trace synchronization enabled or disabled.
    -- info-ROU:     GET db  SET tm 
    -- info-IMPL:    V1.2A->
    -- info-VERCTRL: GET db  SET asw
    SYNTAX        Xldv11OperState
    ACCESS        read-write
    STATUS        mandatory
    DESCRIPTION
	 " This attribute is used to configure the sync-bit generation
	   for the path trace send attribute.
	   Range of value:
	      enabled (sync-bit send),
	      disabled (without sync-bit; default) . "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 7 }

 xldv11S3nPathTraceSendCRCActivate OBJECT-TYPE
    -- info-LEAF:    xldv11S3nPathTraceSendCRCActivate
    -- info-TREE:    xldv11Tlm
    -- info-ACC:     rw
    -- info-SYNTAX:  Xldv11OperState
    -- info-VALUE:   enabled(1), disabled(2)
    -- info-COMMENT: Represents thr functionality of the CRC generation
    -- info-COMMENT: for the path trace send attribute.
    -- info-COMMENT: First Trace Send byte ignored and used for
    -- info-COMMENT: CRC when CRC is enabled.
    -- info-ROU:     GET db  SET tm 
    -- info-IMPL:    V1.2A->
    -- info-VERCTRL: GET db  SET asw
    SYNTAX        Xldv11OperState
    ACCESS        read-write
    STATUS        mandatory
    DESCRIPTION
	 " This attribute represents the functionality of the CRC generation
	   for the path trace send attribute.
	   Range of value:
	      CRC enabled == ONU creates CRC Byte by its own,
	      CRC disabled (default) == ONU uses 1'st Byte of MIB-attribute xldv11S3nPathTraceSend . "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 8 }

 xldv11S3nPathTraceReceiveCRCActivate OBJECT-TYPE
    -- info-LEAF:    xldv11S3nPathTraceReceiveCRCActivate
    -- info-TREE:    xldv11Tlm
    -- info-ACC:     rw
    -- info-SYNTAX:  Xldv11OperState
    -- info-VALUE:   enabled(1), disabled(2)
    -- info-COMMENT: Represents thr functionality of the CRC generation
    -- info-COMMENT: for the path trace reveive attribute.
    -- info-ROU:     GET db  SET tm 
    -- info-IMPL:    V1.2A->
    -- info-VERCTRL: GET db  SET asw
    SYNTAX        Xldv11OperState
    ACCESS        read-write
    STATUS        mandatory
    DESCRIPTION
	 " This attribute represents thr functionality of the CRC generation
	   for the path trace reveive attribute.
	   Range of value:
	      enabled,
	      disabled (default) . "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 9 }

 xldv11S3nHpEberThreshold OBJECT-TYPE
    -- info-LEAF:    xldv11S3nHpEberThreshold
    -- info-TREE:    xldv11Tlm
    -- info-ACC:     rw
    -- info-SYNTAX:  Xldv11S1nS3nEberThreshold
    -- info-VALUE:   exp10E3(1), exp10E4(2), exp10E5(3), noSupervision(255)
    -- info-VALUE:   default: noSupervision
    -- info-COMMENT: Represents the threshold for the higher-order path
    -- info-COMMENT: excessive bit error check.
    -- info-COMMENT: Value corresponds to exponent 10E-3, ...., 10E-5
    -- info-ROU:     GET db  SET tm 
    -- info-IMPL:    V1.2A->
    -- info-VERCTRL: GET db  SET asw
    SYNTAX        Xldv11S1nS3nEberThreshold
    ACCESS        read-write
    STATUS        mandatory
    DESCRIPTION
	 " This attribute represents the threshold for the higher-order path
	   excessive bit error check.
	   Range of values:
	      noSupervision (default),
	      exp10E3,
	      exp10E4,
	      exp10E5 . "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 10 }

 xldv11S3nMsEberThreshold OBJECT-TYPE
    -- info-LEAF:    xldv11S3nMsEberThreshold
    -- info-TREE:    xldv11Tlm
    -- info-ACC:     rw
    -- info-SYNTAX:  Xldv11S1nS3nEberThreshold
    -- info-VALUE:   exp10E3(1), exp10E4(2), exp10E5(3), noSupervision(255)
    -- info-VALUE:   default: noSupervision
    -- info-COMMENT: Represents the threshold for the multiplexer section
    -- info-COMMENT: excessive bit error check.
    -- info-COMMENT: Value corresponds to exponent 10E-3, ...., 10E-5
    -- info-ROU:     GET db  SET tm
    -- info-IMPL:    V1.2A->
    -- info-VERCTRL: GET db  SET asw
    SYNTAX        Xldv11S1nS3nEberThreshold
    ACCESS        read-write
    STATUS        mandatory
    DESCRIPTION
	 " This attribute represents the threshold for the multiplexer
	   section excessive bit error check.
	   Range of values:
	      noSupervision (default),
	      exp10E3,
	      exp10E4,
	      exp10E5 . "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 11 }

 xldv11S3nRsEberThreshold OBJECT-TYPE
    -- info-LEAF:    xldv11S3nRsEberThreshold
    -- info-TREE:    xldv11Tlm
    -- info-ACC:     rw
    -- info-SYNTAX:  Xldv11S1nS3nEberThreshold
    -- info-VALUE:   exp10E3(1), exp10E4(2), exp10E5(3), noSupervision(255)
    -- info-VALUE:   default: noSupervision
    -- info-COMMENT: Represents the threshold for the repeater section
    -- info-COMMENT: excessive bit error check.
    -- info-COMMENT: Value corresponds to exponent 10E-3, ...., 10E-5
    -- info-ROU:     GET db  SET tm 
    -- info-IMPL:    V1.2A->
    -- info-VERCTRL: GET db  SET asw
    SYNTAX        Xldv11S1nS3nEberThreshold
    ACCESS        read-write
    STATUS        mandatory
    DESCRIPTION
	 " This attribute represents the threshold for the repeater section
	   excessive bit error check.
	   Range of values:
	      noSupervision (default),
	      exp10E3,
	      exp10E4,
	      exp10E5 . "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 12 }

 xldv11S3nSDThreshold OBJECT-TYPE
    -- info-LEAF:    xldv11S3nSDThreshold
    -- info-TREE:    xldv11Tlm
    -- info-ACC:     rw
    -- info-SYNTAX:  Xldv11S1nS3nSDThreshold
    -- info-VALUE:   exp10E5(1), exp10E6(2), exp10E7(3),exp10E8(2), exp10E9(3),
    -- info-VALUE:   noSupervision(255)
    -- info-VALUE:   default: exp10E9
    -- info-COMMENT: Represents the threshold for the signal degration check.
    -- info-COMMENT: Value corresponds to exponent 10E-5, ...., 10E-9
    -- info-ROU:     GET db  SET tm 
    -- info-IMPL:    V1.2A->
    -- info-VERCTRL: GET db  SET asw
    SYNTAX        Xldv11S1nS3nSDThreshold
    ACCESS        read-write
    STATUS        mandatory
    DESCRIPTION
	 " This attribute represents the threshold for the signal degration
	   check.
	   Range of values:
	      noSupervision,
	      exp10E5,
	      exp10E6,
	      exp10E7,
	      exp10E8,
	      exp10E9 (default) . "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 13 }

 xldv11S3nSignalLabelReceive OBJECT-TYPE
    -- info-LEAF:    xldv11S3nSignalLabelReceive
    -- info-TREE:    xldv11Tlm
    -- info-ACC:     ro
    -- info-SYNTAX:  Integer32
    -- info-VALUE:   0 ... 255
    -- info-COMMENT: Represents the real result of a trace operation
    -- info-COMMENT: received signal label value from the LE.
    -- info-ROU:     GET tm
    -- info-IMPL:    V1.2A->
    -- info-VERCTRL: GET asw
    SYNTAX        Integer32
    ACCESS        read-only
    STATUS        mandatory
    DESCRIPTION
	  " This attribute represents the real result of a trace operation
	    received signal label value from
	    the LE."
    --DEFAULT next-function-async     fsnS3nEntryNext
    --DEFAULT get-function-async      fsnS3nEntryGet
    ::= { xldv11Sts3NePPTPEntry 14 }

 xldv11S3nEmptyCellType OBJECT-TYPE
    -- info-LEAF:    xldv11S3nEmptyCellType
    -- info-TREE:    xldv11Tlm
    -- info-ACC:     rw
    -- info-SYNTAX:  Xldv11EmptyCellType
    -- info-VALUE:   idle, unassigned (default)
    -- info-COMMENT: Type of empty cells.
    -- info-ROU:     GET db  SET tm
    -- info-IMPL:    V1.2A->
    -- info-VERCTRL: GET db  SET asw
    SYNTAX        Xldv11EmptyCellType
    ACCESS        read-write
    STATUS        mandatory
    DESCRIPTION
	 " This attribute contains the type of empty cells.
	   Range of value: idle, unassigned (default) . "
    --DEFAULT test-function-async     fsnS3nEntryTest
    --DEFAULT next-function-async     fsnS3nEntryNext
    --DEFAULT set-function-async      fsnS3nEntrySet
    --DEFAULT get-function-async      fsnS3nEntryGet
    ::= { xldv11Sts3NePPTPEntry 15 }

 xldv11S3nBandwidthUsage OBJECT-TYPE
    -- info-LEAF:    xldv11S3nBandwidthUsage
    -- info-TREE:    xldv11Tlm
    -- info-ACC:     ro
    -- info-SYNTAX:  INTEGER 
    -- info-VALUE:   (0..100) Default 0
    -- info-COMMENT: Used Bandwidth
    -- info-ROU:     GET db  
    -- info-IMPL:    V1.13a->
    -- info-VERCTRL: -
    SYNTAX        INTEGER (0..100)
    ACCESS        read-only
    STATUS        mandatory
    DESCRIPTION
	 " The used Bandwidth in percent
	   Range of value: 0 ..100 (default = 0 ). "
    --DEFAULT next-function-async     fsnS3nEntryNext
    --DEFAULT get-function-async      fsnS3nEntryGet
    ::= { xldv11Sts3NePPTPEntry 16 }


 -- --------------------------------------------------------------
 --                 TLM TCA table (new: XLDV11u)
 -- --------------------------------------------------------------


 xldv11TcaTable  OBJECT-TYPE
    -- info-NODE:    xldv11TcaTable
    -- info-TREE:    xldv11Tlm
    -- info-ACC:     nac
    -- info-SYNTAX:  SEQUENCE OF Xldv11TcaEntry
    -- info-COMMENT: Table of TcaLoopLocId
    -- info-IMPL:    V1.1U->
    SYNTAX        SEQUENCE OF Xldv11TcaEntry
    ACCESS        not-accessible
    STATUS        mandatory
    DESCRIPTION
	 " The TCA Table"
    ::= { xldv11Tlm 11 }

 xldv11TcaEntry   OBJECT-TYPE
    -- info-NODE:    xldv11TcaEntry
    -- info-TREE:    xldv11Tlm 
    -- info-INDEX:   xldv11IfIndex
    -- info-ACC:     nac
    -- info-SYNTAX:  Xldv11TcaEntry
    -- info-COMMENT: Entry of Table TcaLoopLocId
    -- info-IMPL:    V1.1U->
    SYNTAX        Xldv11TcaEntry
    ACCESS        not-accessible
    STATUS        mandatory
    DESCRIPTION
	 " An entry in the TCA table.
	   Notifications : see xldv11IfEntry."
    INDEX         { xldv11IfIndex}
    ::= { xldv11TcaTable 1 }

 Xldv11TcaEntry ::=
    SEQUENCE { xldv11TcaLoopLocId   OCTET STRING  }

 xldv11TcaLoopLocId   OBJECT-TYPE
    -- info-LEAF:    xldv11TcaLoopLocId
    -- info-TREE:    xldv11Tlm 
    -- info-ACC:     rw
    -- info-SYNTAX:  OCTET STRING ( SIZE (0..16) )
    -- info-VALUE:   default: 0xFFFFFFFFFFFFFFFF
    -- info-COMMENT: A unique number known by the crafts person specifying
    -- info-COMMENT: the location where the OAM loopback cell shall be looped back.
    -- info-COMMENT: oopback point is either the TCA at the LU* (within the ONU)
    -- info-COMMENT: or the TCA of adrPPTP for Ethernet NT.  hexadecimal at TMN-OS.
    -- info-ROU:     GET db  SET tm
    -- info-IMPL:    V1.1U->
    -- info-VERCTRL: GET db  SET asw
    SYNTAX        OCTET STRING ( SIZE (0..16) ) 
    ACCESS        read-write
    STATUS        mandatory
    DESCRIPTION
    " A unique number known by the crafts person specifying 
      the location where the OAM loopback cell shall be 
      looped back.
      Loopback point is either the TCA at the LU* (within the ONU)
      or the TCA of adrPPTP for Ethernet NT.
      hexadecimal at TMN OS
      Default : 0xFFFFFFFFFFFFFFFF "
    --DEFAULT test-function-async     fsnTcaEntryTest
    --DEFAULT next-function-async     fsnTcaEntryNext
    --DEFAULT set-function-async      fsnTcaEntrySet
    --DEFAULT get-function-async      fsnTcaEntryGet
    ::= {xldv11TcaEntry 1 }






 -- --------------------------------------------------------------
 --                 TLM Physical Loop Test subgroup
 -- --------------------------------------------------------------

 xldv11PhyLoopTest OBJECT IDENTIFIER ::= { xldv11Tlm 12 }
    -- info-NODE:    xldv11PhyLoopTest
    -- info-TREE:    xldv11Tlm 
    -- info-ACC:     nac
    -- info-COMMENT: This group handles the TMN control request for starting
    -- info-COMMENT: a service interrupting physical layer loop diagnosis.
    -- info-IMPL:    V1.0->

 -- This group handles the TMN control request for starting a service
 -- interrupting physical layer loop diagnosis.
 --

 xldv11PltHwUnitIndex OBJECT-TYPE
    -- info-LEAF:    xldv11PltHwUnitIndex
    -- info-TREE:    xldv11Tlm 
    -- info-ACC:     rw
    -- info-SYNTAX:  Unsigned16
    -- info-VALUE:   0..65535
    -- info-COMMENT: Labels the location of the physical loopback. It can
    -- info-COMMENT: be the HW unit index of LI25:xx, LUxxxx, SUAD:16x,
    -- info-COMMENT: LTAD:xx, SUVD:4, NTAD:xx.
    -- info-ROU:     GET db  SET db 
    -- info-IMPL:    V1.0->
    -- info-VERCTRL: -
    SYNTAX        Unsigned16
    ACCESS        read-write
    STATUS        mandatory
    DESCRIPTION
	 " This attribute labels the location of the physical loopback. It
	   can be the HW unit index of LI25:xx, LUxxxx, SUAD:16x, LTAD:xx,
	   SUVD:4, NTAD:xx . "
    --DEFAULT test-function-async     fsnPltTest
    --DEFAULT next-function-async     fsnPltNext
    --DEFAULT set-function-async      fsnPltSet
    --DEFAULT get-function-async      fsnPltGet
    ::= { xldv11PhyLoopTest 1 }

 xldv11PltHwPortId OBJECT-TYPE
    -- info-LEAF:    xldv11PltHwPortId
    -- info-TREE:    xldv11Tlm 
    -- info-ACC:     rw
    -- info-SYNTAX:  INTEGER
    -- info-VALUE:   0..255
    -- info-COMMENT: Identifies the corresponding port the physical path
    -- info-COMMENT: terminates on. 
    -- info-ROU:     GET db  SET db 
    -- info-IMPL:    V1.0->
    -- info-VERCTRL: -
    SYNTAX        INTEGER (0..255)
    ACCESS        read-write
    STATUS        mandatory
    DESCRIPTION
	 " Identifies the corresponding port the physical path
	   terminates on. "
    --DEFAULT test-function-async     fsnPltTest
    --DEFAULT next-function-async     fsnPltNext
    --DEFAULT set-function-async      fsnPltSet
    --DEFAULT get-function-async      fsnPltGet
    ::= { xldv11PhyLoopTest 2 }

 xldv11PltControlReq OBJECT-TYPE
    -- info-LEAF:    xldv11PltControlReq
    -- info-TREE:    xldv11Tlm 
    -- info-ACC:     rw
    -- info-SYNTAX:  Xldv11ControlReq
    -- info-VALUE:   noRequest(command), commExecStarted, paramFaulty 
    -- info-VALUE:   loopDiagRequest(command), loopTestBusy ,loopTestReject 
    -- info-VALUE:   requestBusy(V1.3N->),setDataFailed(V1.3N->),
    -- info-VALUE:   aswTimeout(V1.3N->),
    -- info-COMMENT: Control Command.
    -- info-ROU:     GET db  SET tm 
    -- info-IMPL:    V1.0->
    -- info-VERCTRL: -
    SYNTAX        Xldv11ControlReq
    ACCESS        read-write
    STATUS        mandatory
    DESCRIPTION
	 " Marks the received command to start an OAM cell loopback test
	   (loopDiagRequest) or to abort a running test (noRequest).
	   Reject reasons are: faulty parameters from the SNMP agent
	   (response: paramFaulty, commExecStarted, loopTestReject)
	   or a loop diagnosis request while a running test (response:
	   loopTestBusy).
	   Notifications : 
	     xldv11TrPltTestResult ."
    --DEFAULT test-function-async     fsnPltTest
    --DEFAULT next-function-async     fsnPltNext
    --DEFAULT set-function-async      fsnPltSet
    --DEFAULT get-function-async      fsnPltGet
    ::= { xldv11PhyLoopTest 3 }

 xldv11PltControlStatus OBJECT-TYPE
    -- info-LEAF:    xldv11PltControlStatus
    -- info-TREE:    xldv11Tlm 
    -- info-ACC:     ro
    -- info-SYNTAX:  Xldv11ControlStatus
    -- info-VALUE:   requestIdle(1), requestBusy(2), requestPassed(3)
    -- info-VALUE:   requestFailed(4)
    -- info-COMMENT: Status of the control request. 
    -- info-ROU:     GET db
    -- info-IMPL:    V1.0->
    -- info-VERCTRL: -
    SYNTAX        Xldv11ControlStatus
    ACCESS        read-only
    STATUS        mandatory
    DESCRIPTION
	 " The status of the control request. The value requestIdle
	   will be set after startup/recovery or after a running
	   test was aborted by the SNMP manager.
	   Range of value:
	      requestIdle,
	      requestBusy,
	      requestPassed,
	      requestFailed . "
    --DEFAULT next-function-async     fsnPltNext
    --DEFAULT get-function-async      fsnPltGet
    ::= { xldv11PhyLoopTest 4 }

 xldv11PltControlTimer OBJECT-TYPE
    -- info-LEAF:    xldv11PltControlTimer
    -- info-TREE:    xldv11Tlm 
    -- info-ACC:     ro
    -- info-SYNTAX:  Integer32
    -- info-VALUE:   -2147483648..2147483647
    -- info-COMMENT: Maximal test time.
    -- info-ROU:     GET db
    -- info-IMPL:    V1.0->
    -- info-VERCTRL: -
    SYNTAX        Integer32
    ACCESS        read-only
    STATUS        mandatory
    DESCRIPTION
	 " This is the maximum duration of a physical loop diagnosis.
	   It is required by the SNMP manager to detect the end of a
	   physical loop diagnosis in case of the response
	   'xldv11TrPltTestResult' from pltloopTest was not received in time.
	   Range of value: maxTestTime. "
    --DEFAULT next-function-async     fsnPltNext
    --DEFAULT get-function-async      fsnPltGet
    ::= { xldv11PhyLoopTest 5 }

 xldv11PltControlReqResult OBJECT-TYPE
    -- info-LEAF:    xldv11PltControlReqResult
    -- info-TREE:    xldv11Tlm
    -- info-ACC:     ro
    -- info-SYNTAX:  Xldv11ControlReq
    -- info-VALUE:   noRequest, commExecStarted, paramFaulty 
    -- info-VALUE:   loopDiagRequest, loopTestBusy ,loopTestReject 
    -- info-VALUE:   requestBusy,setDataFailed,commandFailed
    -- info-VALUE:   aswTimeout
    -- info-VALUE:   tsrRequestIdle,tsrRequestBusy
    -- info-VALUE:   tsrRequestPassed,tsrRequestFailed
    -- info-COMMENT: specifies the result of user command
    -- info-ROU:     GET db
    -- info-IMPL:    V1.3N->
    -- info-VERCTRL: -
    SYNTAX        Xldv11ControlReq
    ACCESS        read-only
    STATUS        mandatory
    DESCRIPTION
	  " This read-only attribute informs about the result of 
	     the last user command."
    --DEFAULT next-function-async     fsnPltNext
    --DEFAULT get-function-async      fsnPltGet
    ::= { xldv11PhyLoopTest 6 }

  xldv11PltControlTimeStamp OBJECT-TYPE
     -- info-LEAF:    xldv11PltControlTimeStamp
     -- info-TREE:    xldv11Tlm
     -- info-ACC:     ro
     -- info-SYNTAX:  TimeTicks
     -- info-VALUE:   0..2Giga
     -- info-COMMENT: specifies the time stamp in seconds
     -- info-COMMENT: of the last command
     -- info-COMMENT: (end of command)
     -- info-ROU:     GET db
     -- info-IMPL:    V1.3N->
     -- info-VERCTRL: -
     SYNTAX        TimeTicks
     ACCESS        read-only
     STATUS        mandatory
     DESCRIPTION
        " This read-only attribute informs about the time stamp
        of the last command (end of command)."
    --DEFAULT next-function-async     fsnPltNext
    --DEFAULT get-function-async      fsnPltGet
    ::= { xldv11PhyLoopTest 7 }

 -- --------------------------------------------------------------
 --                  TLM ATM Loop Test subgroup
 -- --------------------------------------------------------------

 xldv11AtmLoopTest OBJECT IDENTIFIER ::= { xldv11Tlm 13 }
    -- info-NODE:    xldv11AtmLoopTest
    -- info-TREE:    xldv11Tlm 
    -- info-ACC:     nac
    -- info-COMMENT: Control group for Atm Loop Tests.
    -- info-IMPL:    V1.0->
    -- info-VERCTRL: -

 -- This subgroup is used to handle the TMN attribute control request
 -- for starting a non service interrupting OAM cell loopback test.
 -- It also used to insert and verify a default OAM loopback cell
 -- needed for testing a physical layer loop.
 --

 xldv11AltHwUnitIndex OBJECT-TYPE
    -- info-LEAF:    xldv11AltHwUnitIndex
    -- info-TREE:    xldv11Tlm 
    -- info-ACC:     rw
    -- info-SYNTAX:  Unsigned16
    -- info-VALUE:   0..65535
    -- info-COMMENT: Labels the loop direction (CPE customer premise
    -- info-COMMENT: equipment or LEi local exchange).  It is the
    -- info-COMMENT: hardware unit index of LUxxxx in LE direction or an LIxxxx
    -- info-COMMENT: in NE direction. It is consistent with VPIUni of xldv11AltVpi.
    -- info-COMMENT: V11U: ONU is loopback point only.
    -- info-COMMENT: V13B: ONU is originating point for loop test cells.
    -- info-ROU:     GET db  SET db
    -- info-IMPL:    V1.0->
    -- info-VERCTRL: -
    SYNTAX        Unsigned16
    ACCESS        read-write
    STATUS        mandatory
    DESCRIPTION
	 " This attribute labels the loop direction (CPE or LE).
	   It is the hardware unit index of LUxxxx in LE direction
	   or an LIxxxx in NE direction. It is consistent with VPIUni
	   of xldv11AltVpi. "
    --DEFAULT test-function-async     fsnAltTest
    --DEFAULT next-function-async     fsnAltNext
    --DEFAULT set-function-async      fsnAltSet
    --DEFAULT get-function-async      fsnAltGet
    ::= { xldv11AtmLoopTest 1 }

 xldv11AltHwPortId OBJECT-TYPE
    -- info-LEAF:    xldv11AltHwPortId
    -- info-TREE:    xldv11Tlm 
    -- info-ACC:     rw
    -- info-SYNTAX:  INTEGER
    -- info-VALUE:   0..255
    -- info-COMMENT: Corresponding port, where the physical path terminates.
    -- info-COMMENT: Consistent with xldv11AltVpi.
    -- info-ROU:     GET db  SET db
    -- info-IMPL:    V1.0->
    -- info-VERCTRL: -
    SYNTAX        INTEGER (0..255)
    ACCESS        read-write
    STATUS        mandatory
    DESCRIPTION
	 " The port ( within the card identified by the
	   xldv11AltHwUnitIndex ) where the physical path terminates. "
    --DEFAULT test-function-async     fsnAltTest
    --DEFAULT next-function-async     fsnAltNext
    --DEFAULT set-function-async      fsnAltSet
    --DEFAULT get-function-async      fsnAltGet
    ::= { xldv11AtmLoopTest 2 }

 xldv11AltVpi OBJECT-TYPE
    -- info-LEAF:    xldv11AltVpi
    -- info-TREE:    xldv11Tlm 
    -- info-ACC:     rw
    -- info-SYNTAX:  INTEGER
    -- info-VALUE:   0..4095
    -- info-COMMENT: The insertion point for OAM cells for f4 and f5 level test.
    -- info-COMMENT: Identifies the VPI which shall be tested. It is VPINni
    -- info-COMMENT: when test in LE direction or it is VPIUni when test in NT direction.
    -- info-ROU:     GET db  SET db
    -- info-IMPL:    V1.0->
    -- info-VERCTRL: -
    SYNTAX        INTEGER (0..4095)
    ACCESS        read-write
    STATUS        mandatory
    DESCRIPTION
	 " Identifies the VPI which shall be tested. It is VPINni 
	   when test in LE direction or it is VPIUni when test in
	   NT direction. "
    --DEFAULT test-function-async     fsnAltTest
    --DEFAULT next-function-async     fsnAltNext
    --DEFAULT set-function-async      fsnAltSet
    --DEFAULT get-function-async      fsnAltGet
    ::= { xldv11AtmLoopTest 3 }

 xldv11AltLoopLocId OBJECT-TYPE
    -- info-LEAF:    xldv11AltLoopLocId
    -- info-TREE:    xldv11Tlm
    -- info-ACC:     rw
    -- info-SYNTAX:  OCTET STRING (SIZE (0..16))
    -- info-VALUE:   Length 16 bytes, default = FF..FF
    -- info-COMMENT: Location where test cell should be looped back.
    -- info-COMMENT: Test cell loopback location. It is an identifier known
    -- info-COMMENT: by the crafts person identifying a ATM node in the ATM network.
    -- info-COMMENT: For EndToEnd loop test the default value is valid.
    -- info-ROU:     GET db  SET db
    -- info-IMPL:    V1.0->
    -- info-VERCTRL: -
    SYNTAX        OCTET STRING (SIZE (0..16))
    ACCESS        read-write
    STATUS        mandatory
    DESCRIPTION
	 " Test cell loopback location. It is an identifier known
	   by the crafts person identifying a ATM node in the ATM
	   network. "
    --DEFAULT test-function-async     fsnAltTest
    --DEFAULT next-function-async     fsnAltNext
    --DEFAULT set-function-async      fsnAltSet
    --DEFAULT get-function-async      fsnAltGet
    ::= { xldv11AtmLoopTest 4 }

 xldv11AltControlReq OBJECT-TYPE
    -- info-LEAF:    xldv11AltControlReq
    -- info-TREE:    xldv11Tlm 
    -- info-ACC:     rw
    -- info-SYNTAX:  Xldv11ControlReq
    -- info-VALUE:   noRequest(command), loopTestRequest(command), commExecStarted
    -- info-VAlUE:   paramFaulty,looptestBusy,looptestReject
    -- info-VALUE:   requestBusy(V1.3N->),setDataFailed(V1.3N->),
    -- info-VALUE:   aswTimeout(V1.3N->),
    -- info-COMMENT: Control Command.
    -- info-ROU:     GET db  SET tm 
    -- info-IMPL:    V1.0->
    -- info-VERCTRL: -
    SYNTAX        Xldv11ControlReq
    ACCESS        read-write
    STATUS        mandatory
    DESCRIPTION
	 " The value of this object marks the received command to
	   start an OAM cell loopback test (loopTestRequest) or to
	   abort a running test (noRequest).
	   Reject reasons are faulty parameters from the agent
	   (response: paramFaulty, commExecStarted, loopTestReject)
	   or a loop request during a running test (response:
	   loopTestBusy).
	   Notifications : 
	     xldv11TrAltTestResult ."
    --DEFAULT test-function-async     fsnAltTest
    --DEFAULT next-function-async     fsnAltNext
    --DEFAULT set-function-async      fsnAltSet
    --DEFAULT get-function-async      fsnAltGet
    ::= { xldv11AtmLoopTest 5 }

 xldv11AltControlStatus OBJECT-TYPE
    -- info-LEAF:    xldv11AltControlStatus
    -- info-TREE:    xldv11Tlm 
    -- info-ACC:     ro
    -- info-SYNTAX:  Xldv11ControlStatus
    -- info-VALUE:   requestIdle(1), requestBusy(2), requestPassed(3)
    -- info-VALUE:   requestFailed(4)
    -- info-COMMENT: Status of command handling.
    -- info-ROU:     GET db
    -- info-IMPL:    V1.0->
    -- info-VERCTRL: -
    SYNTAX        Xldv11ControlStatus
    ACCESS        read-only
    STATUS        mandatory
    DESCRIPTION
	 " The status of the command handling.
	   Range of value:
	      requestIdle,
	      requestBusy,
	      requestPassed,
	      requestFailed . "
    --DEFAULT next-function-async     fsnAltNext
    --DEFAULT get-function-async      fsnAltGet
    ::= { xldv11AtmLoopTest 6 }

 xldv11AltControlTimer OBJECT-TYPE
    -- info-LEAF:    xldv11AltControlTimer
    -- info-TREE:    xldv11Tlm 
    -- info-ACC:     ro
    -- info-SYNTAX:  Integer32
    -- info-VALUE:   -2147483648..2147483647
    -- info-COMMENT: Maximum duration of loop- back test.
    -- info-ROU:     GET db
    -- info-IMPL:    V1.0->
    -- info-VERCTRL: -
    SYNTAX        Integer32
    ACCESS        read-only
    STATUS        mandatory
    DESCRIPTION
	 " The value of this object marks the maximum duration of loop-
	   back test. It is required by the SNMP manager to detect the end
	   of loopback test in case of the response'xldv11TrAltTestResult' from
	   altloopTest was not received in time.
	   Range of value: maxTestTime. "
    --DEFAULT next-function-async     fsnAltNext
    --DEFAULT get-function-async      fsnAltGet
    ::= { xldv11AtmLoopTest 7 }


 xldv11AltOamLevel OBJECT-TYPE
    -- info-LEAF:    xldv11AltOamLevel
    -- info-TREE:    xldv11Tlm 
    -- info-ACC:     rw
    -- info-SYNTAX:  INTEGER
    -- info-VALUE:   f4 (4), f5 (5)
    -- info-COMMENT: The OAM level for loop test on VP/VC level.
    -- info-ROU:     GET db  SET db 
    -- info-IMPL:    V1.2B->
    -- info-VERCTRL: V1.1U->V1.2A: GET db  SET db
    SYNTAX        INTEGER { f4 (4),
			    f5 (5) }
    ACCESS        read-write
    STATUS        mandatory
    DESCRIPTION
	 " the OAM level for loop test on VP/VC level
	   Valid:    f4 (for VP )  f5 (for VC)
	   Default:  f4 "
    --DEFAULT test-function-async     fsnAltTest
    --DEFAULT next-function-async     fsnAltNext
    --DEFAULT set-function-async      fsnAltSet
    --DEFAULT get-function-async      fsnAltGet
    ::= { xldv11AtmLoopTest 8 }

 xldv11AltLoopTestType OBJECT-TYPE
    -- info-LEAF:    xldv11AltLoopTestType
    -- info-TREE:    xldv11Tlm 
    -- info-ACC:     rw
    -- info-SYNTAX:  INTEGER
    -- info-VALUE:   segment(1), endToEnd(2) 
    -- info-COMMENT: Type of loop test.
    -- info-COMMENT: For EndToEnd loop test loop location ID is FF..FF.
    -- info-ROU:     GET db  SET db 
    -- info-IMPL:    V1.2B->
    -- info-VERCTRL: V1.1U->V1.2A: GET db  SET db
    SYNTAX        INTEGER { segment      (1),
			    endToEnd     (2) }
    ACCESS        read-write
    STATUS        mandatory
    DESCRIPTION
	 " the type of loop test 
	   VALID:    segment     or endToEnd     
	   DEFAULT:  segment                " 
    --DEFAULT test-function-async     fsnAltTest
    --DEFAULT next-function-async     fsnAltNext
    --DEFAULT set-function-async      fsnAltSet
    --DEFAULT get-function-async      fsnAltGet
    ::= { xldv11AtmLoopTest 9 }

 xldv11AltVci OBJECT-TYPE
    -- info-LEAF:    xldv11AltVci
    -- info-TREE:    xldv11Tlm 
    -- info-ACC:     rw
    -- info-SYNTAX:  INTEGER
    -- info-VALUE:   0..65535
    -- info-COMMENT: Insertion point for OAM cells for F5 level.
    -- info-ROU:     GET db  SET db
    -- info-IMPL:    V1.2B->
    -- info-VERCTRL: V1.1U->V1.2A: GET db  SET db
    SYNTAX        INTEGER (0..65535)
    ACCESS        read-write
    STATUS        mandatory
    DESCRIPTION
	 " Insertion point for OAM cells for F5 level " 
    --DEFAULT test-function-async     fsnAltTest
    --DEFAULT next-function-async     fsnAltNext
    --DEFAULT set-function-async      fsnAltSet
    --DEFAULT get-function-async      fsnAltGet
    ::= { xldv11AtmLoopTest 10 }

 xldv11AltControlReqResult OBJECT-TYPE
    -- info-LEAF:    xldv11AltControlReqResult
    -- info-TREE:    xldv11Tlm
    -- info-ACC:     ro
    -- info-SYNTAX:  Xldv11ControlReq
    -- info-VALUE:   noRequest, loopTestRequest, commExecStarted
    -- info-VAlUE:   paramFaulty,looptestBusy,looptestReject
    -- info-VALUE:   requestBusy,setDataFailed,commandFailed
    -- info-VALUE:   aswTimeout
    -- info-VALUE:   tsrRequestIdle,tsrRequestBusy
    -- info-VALUE:   tsrRequestPassed,tsrRequestFailed
    -- info-COMMENT: specifies the result of user command
    -- info-ROU:     GET db
    -- info-IMPL:    V1.3N->
    -- info-VERCTRL: -
    SYNTAX        Xldv11ControlReq
    ACCESS        read-only
    STATUS        mandatory
    DESCRIPTION
	  " This read-only attribute informs about the result of 
	     the last user command."
    --DEFAULT next-function-async     fsnAltNext
    --DEFAULT get-function-async      fsnAltGet
    ::= { xldv11AtmLoopTest 11 }

  xldv11AltControlTimeStamp OBJECT-TYPE
     -- info-LEAF:    xldv11AltControlTimeStamp
     -- info-TREE:    xldv11Tlm
     -- info-ACC:     ro
     -- info-SYNTAX:  TimeTicks
     -- info-VALUE:   0..2Giga
     -- info-COMMENT: specifies the time stamp in seconds
     -- info-COMMENT: of the last command
     -- info-COMMENT: (end of command)
     -- info-ROU:     GET db
     -- info-IMPL:    V1.3N->
     -- info-VERCTRL: -
     SYNTAX        TimeTicks
     ACCESS        read-only
     STATUS        mandatory
     DESCRIPTION
        " This read-only attribute informs about the time stamp
        of the last command (end of command)."
    --DEFAULT next-function-async     fsnAltNext
    --DEFAULT get-function-async      fsnAltGet
    ::= { xldv11AtmLoopTest 12 }

 -- --------------------------------------------------------------
 --          TLM ATM Loopback subgroup (for V1.1U only)
 -- --------------------------------------------------------------
 --

 xldv11AtmLoopBack OBJECT IDENTIFIER ::= { xldv11Tlm 14 }
    -- info-NODE:    xldv11AtmLoopBack
    -- info-TREE:    xldv11Tlm 
    -- info-COMMENT: Control group for activating/deactivating
    -- info-COMMENT: the loopback function in the ATM ASIC BBM.
    -- info-IMPL:    V1.1U

 -- This group handles the TMN control request for activating/deactivating 
 -- the loopback function in the ATM ASIC BBM.
 --

 xldv11AlbHwUnitIndex OBJECT-TYPE
    -- info-LEAF:    xldv11AlbHwUnitIndex
    -- info-TREE:    xldv11Tlm 
    -- info-ACC:     rw
    -- info-SYNTAX:  Unsigned16
    -- info-VALUE:   0..65535
    -- info-COMMENT: Labels the hardware unit where the OAM test cell is sent from.
    -- info-COMMENT: The hardware unit is either the LUxxx in LE direction or LIxxxx
    -- info-COMMENT: in NT direction.
    -- info-ROU:     GET db  SET db 
    -- info-IMPL:    V1.1U
    -- info-VERCTRL: -
    SYNTAX        Unsigned16
    ACCESS        read-write
    STATUS        mandatory
    DESCRIPTION
	 " Labels the hardware unit where the OAM test cell is sent from. 
	   The hardware unit is either the LUxxx in LE direction or LIxxxx
	   in NT direction. "
    --DEFAULT test-function-async     fsnAlbTest
    --DEFAULT next-function-async     fsnAlbNext
    --DEFAULT set-function-async      fsnAlbSet
    --DEFAULT get-function-async      fsnAlbGet
    ::= { xldv11AtmLoopBack 1 }

 xldv11AlbHwPortId OBJECT-TYPE
    -- info-LEAF:    xldv11AlbHwPortId
    -- info-TREE:    xldv11Tlm 
    -- info-ACC:     rw
    -- info-SYNTAX:  INTEGER
    -- info-VALUE:   0..255
    -- info-COMMENT: Identifies the corresponding port of the hardware unit
    -- info-COMMENT: over which the loopback test will be performed. 
    -- info-ROU:     GET db SET db
    -- info-IMPL:    V1.1U
    -- info-VERCTRL: -
    SYNTAX        INTEGER (0..255)
    ACCESS        read-write
    STATUS        mandatory
    DESCRIPTION
	 " Identifies the corresponding port of the hardware unit
	   over which the loopback test will be performed. "
    --DEFAULT test-function-async     fsnAlbTest
    --DEFAULT next-function-async     fsnAlbNext
    --DEFAULT set-function-async      fsnAlbSet
    --DEFAULT get-function-async      fsnAlbGet
    ::= { xldv11AtmLoopBack 2 }

 xldv11AlbVpi OBJECT-TYPE
    -- info-LEAF:    xldv11AlbVpi
    -- info-TREE:    xldv11Tlm 
    -- info-ACC:     rw
    -- info-SYNTAX:  INTEGER
    -- info-VALUE:   0..4095
    -- info-COMMENT: Identifies the VPI which shall be tested. It is VPINni
    -- info-COMMENT: when test in LE direction or it is VPIUni when test
    -- info-COMMENT: in NT direction.
    -- info-ROU:     GET db  SET db
    -- info-IMPL:    V1.1U
    -- info-VERCTRL: -
    SYNTAX        INTEGER (0..4095)
    ACCESS        read-write
    STATUS        mandatory
    DESCRIPTION
	 " Identifies the VPI which shall be tested. It is VPINni
	   when test in LE direction or it is VPIUni when test in
	   NT direction. "
    --DEFAULT test-function-async     fsnAlbTest
    --DEFAULT next-function-async     fsnAlbNext
    --DEFAULT set-function-async      fsnAlbSet
    --DEFAULT get-function-async      fsnAlbGet
    ::= { xldv11AtmLoopBack 3 }

 xldv11AlbControlReq OBJECT-TYPE
    -- info-LEAF:    xldv11AlbControlReq
    -- info-TREE:    xldv11Tlm 
    -- info-ACC:     rw
    -- info-SYNTAX:  Xldv11ControlReq
    -- info-VALUE:   noRequest(command), loopBackRequest(command)
    -- info-VALUE:   paramFaulty,loopBackBusy,loopBackReject 
    -- info-VALUE:   requestBusy(V1.3N->),setDataFailed(V1.3N->),
    -- info-VALUE:   aswTimeout(V1.3N->),
    -- info-COMMENT: Command to activate an OAM cell loopback test
    -- info-COMMENT: (loopBackRequest) or to deactivate a running test (noRequest).
    -- info-ROU:     GET db  SET tm 
    -- info-IMPL:    V1.1U
    -- info-VERCTRL: -
    SYNTAX        Xldv11ControlReq
    ACCESS        read-write
    STATUS        mandatory
    DESCRIPTION
	 " Marks the received command to activate an OAM cell loopback test
	   (loopBackRequest) or to deactivate a running test (noRequest).
	   Reject reasons are faulty parameters from the SNMP agent
	   (response: paramFaulty, commExecStarted, loopBackReject) or a
	   loopback request while a running test (response: loopBackBusy).
	   Notifications :  none ."
    --DEFAULT test-function-async     fsnAlbTest
    --DEFAULT next-function-async     fsnAlbNext
    --DEFAULT set-function-async      fsnAlbSet
    --DEFAULT get-function-async      fsnAlbGet
    ::= { xldv11AtmLoopBack 4 }

 xldv11AlbControlStatus OBJECT-TYPE
    -- info-LEAF:    xldv11AlbControlStatus
    -- info-TREE:    xldv11Tlm 
    -- info-ACC:     ro
    -- info-SYNTAX:  Xldv11ControlStatus
    -- info-VALUE:   requestIdle(1), requestBusy(2), requestPassed(3)
    -- info-VALUE:   requestFailed(4)
    -- info-COMMENT: Control status of command.
    -- info-ROU:     GET db
    -- info-IMPL:    V1.1U
    -- info-VERCTRL: -
    SYNTAX        Xldv11ControlStatus
    ACCESS        read-only
    STATUS        mandatory
    DESCRIPTION
	 " The status of the control request. The value requestIdle will be
	   set after startup/recovery or after a running test was aborted by
	   the SNMP manager.
	   Range of value:
	      requestIdle,
	      requestBusy,
	      requestPassed,
	      requestFailed . "
    --DEFAULT next-function-async     fsnAlbNext
    --DEFAULT get-function-async      fsnAlbGet
    ::= { xldv11AtmLoopBack 5 }

 xldv11AlbControlReqResult OBJECT-TYPE
    -- info-LEAF:    xldv11AlbControlReqResult
    -- info-TREE:    xldv11Tlm
    -- info-ACC:     ro
    -- info-SYNTAX:  Xldv11ControlReq
    -- info-VALUE:   see xldv11AlbControlReq
    -- info-COMMENT: specifies the result of user command
    -- info-ROU:     GET db
    -- info-IMPL:    V1.1U
    -- info-VERCTRL: -
    SYNTAX        Xldv11ControlReq
    ACCESS        read-only
    STATUS        mandatory
    DESCRIPTION
	  " This read-only attribute informs about the result of 
	     the last user command."
    --DEFAULT next-function-async     fsnAlbNext
    --DEFAULT get-function-async      fsnAlbGet
    ::= { xldv11AtmLoopBack 6 }


 -- ==============================================================
 --                  A l a r m i n g   G r o u p
 -- ==============================================================
 
    -- List of values and meaning of the attribute xldv11AlmSpecProblem 
    -- for V1.1U, V1.2, V1.3:
    -- (almSpecProblem Abbreviation Description).
    -- This attribute is sent within alarm traps.
    --
    -- Note : For TLM alarms the value of almSpecProblem is identical with the trapId.
    -- For HWM alarms the value has a different meaning depending on the HW.
    --
    -- for CMU:
    --
    -- almSpecProblem Abbreviation Description
    --
    -- 0  Internal     Internal Fault
    -- 3  I2cRead      Inventory Data not  readable
    -- 4  WrongHw      Hardware Mismatch
    -- 5  WrongSw      Software Mismatch
    -- 9  SwMissing    Software not available on FTP- Server
    -- 11 Bbm          InternalError on BBM Chip
    -- 12 BbmUtopia    BBM Utopia Interface Error
    -- 13 BbmBus       BBM Bus Error
    -- 14 BbmGns       BBM Grant not served
    -- 15 Clk3888      Clock 38.88 Mhz Failure
    -- 16 RamCrc       RAM- Cyclic Redundancy Check Fault
    -- 17 FepromCrc    Flash-Eprom- Cyclic Redundancy Check Fault
    -- 18 AlpInternal  ALP internal fault
    -- 19 AlpCame      ALP CAME fault
    -- 20 AlpPolicing  ALP policing fault
    -- 21 AlpConRamUp  ALP upstream connection RAM fault
    -- 22 AlpConRamDwn ALP downstream connection RAM fault
    -- 23 AopInternal  AOP internal fault
    -- 24 AopConRamUp  AOP upstream connection RAM fault
    -- 25 AopConRamDwn AOP downstream connection RAM fault
    -- 26 Fpga1        FPGA1 fault
    -- 27 Fpga2        FPGA2 fault
    -- 28 BpDc         backpack DC fault
    -- 29 LuUtopia     LU Utopia Interface Error
    -- 30 BpUtopia     Backpack Utopia Interface Error
    --
    --
    -- for LIETH:
    --
    -- 0 Internal        Internal Fault
    -- 2 LossOfComm      Loss of Communication
    -- 4 WrongHw         Hardware Mismatch
    -- 5 WrongSW         Software Mismatch
    -- 6 resetThresh     Reset- Threshhold exceeded
    -- 8 IndeterminateHw Hardware Type not  readable during startup
    -- 9 SwMissing       Software not available on FTP- Server
    -- 11 NoHwAccess     Hardware not accessable
    -- 12 InternHw       Internal Hw-Errror occured
    -- 13 Port1          Error on Ethernet-Port1 occured
    -- 14 Port2          Error on Ethernet-Port2 occured
    -- 17 FepromCrc      Flash-Eprom CRC fault
    --
    --
    -- for LI25:
    --
    -- 0 Internal        Internal Fault
    -- 4 WrongHw         Hardware Mismatch
    -- 6 resetThresh     Reset-Threshhold exceeded
    -- 8 IndeterminateHw Hardware Type not  readable during startup
    -- 11 NoHwAccess     Hardware not accessable
    -- 12 internHw       Internal HW Errror occured
    -- 13 Port1          Error on ATMF-Port1 occured
    -- 14 Port2          Error on ATMF-Port2 occured
    -- 15 TcNt           Error on TC_NT- Chip occured
    --
    --
    -- for LIETH25:
    --
    -- 0 Internal        Internal Fault
    -- 2 LossOfComm      Loss of Communication
    -- 4 WrongHw         Hardware Mismatch
    -- 5 WrongSw         Software Mismatch
    -- 6 resetThresh     Reset-Threshhold exceeded
    -- 8 IndeterminateHw Hardware Type not  readable during startup
    -- 9 SwMissing       Software not available on FTP- Server
    -- 11 NoHwAccess     Hardware not accessable
    -- 12 internHw       Internal HW Errror occured
    -- 13 Port1          Error on Ethernet- Port occured
    -- 14 Port2          Error on ATMF- Port occured
    -- 17 FepromCrc      Flash-Eprom CRC fault
    --
    --
    -- for LT ADSL:
    --
    -- 0 Internal         Internal Fault
    -- 1 HwMissing        Hardware is removed when LT is unlocked
    -- 2 Loss of Comm     Loss of Communication
    -- 3 I2cRead          Inventory Data not  readable
    -- 4 WrongHw          Hardware Mismatch
    -- 5 WrongSW          Software Mismatch
    -- 6 resetThresh      Reset-Threshhold exceeded
    -- 7 selftest         Selftest failure
    -- 8 IndeterminateHw  Hardware Type not  readable during startup
    -- 9 SwMissing        Software not available on FTP- Server
    --
    --
    -- for LU155:
    --
    -- 0 Internal        Internal Fault
    -- 1 HwMissing       Hardware is removed when LU is unlocked
    -- 3 I2cRead         Inventory Data not  readable
    -- 4 WrongHw         Hardware Mismatch
    -- 7 selftest        Selftest failure
    -- 8 IndeterminateHw Hardware Type not  readable during startup
    -- 10 HwRemoved      Hardware is removed when LU is locked
    -- 11 Clk            SDHT- Clock Failure
    -- 12 Laser          Laser Failure
    -- 13 Sdht           Internal SDHT Chip Failure
    -- 14 Sdht           Utopia SDHT UTOPIA Failure
    --
    --
    -- for LUDSX3:
    --
    -- 0 Internal         Internal Fault
    -- 1 HwMissing        Hardware is removed when LU is unlocked
    -- 3 I2cRead          Inventory Data not  readable
    -- 4 WrongHw          Hardware Mismatch
    -- 7 selftest         Selftest failure
    -- 8 IndeterminateHw  Hardware Type not  readable during startup
    -- 10 HwRemoved       Hardware is removed when LU is locked
    -- 11 Clk             SDHT- Clock Failure
    -- 12 UtopiaIf        Utopia-Interface Failure
    --
    --
    -- for LUPON:
    --
    -- 0 Internal         Internal Fault
    -- 1 HwMissing        Hardware is removed when LU is unlocked
    -- 2 LossOfComm       Loss of Communication
    -- 3 I2cRead          Inventory Data not  readable
    -- 4 WrongHw          Hardware Mismatch
    -- 6 resetThresh      Reset-Threshhold exceeded
    -- 7 selftest         Selftest failure
    -- 8 IndeterminateHw  Hardware Type not  readable during startup
    -- 10 HwRemoved       Hardware is removed when LU is locked
    -- 11 Clk25           Clock25-  Failure
    -- 12 Laser           Laser Failure
    -- 13 UtopiaTx        Utopia- Transmit buffer
    -- 14 UtopiaRx        Utopia-  Receive buffer
    -- 15 Power           Power Failure
    --
    --
    -- for NT ADSL:
    --
    -- 0 Internal      Internal Fault
    -- 4 WrongHw       Hardware Mismatch
    -- 5 WrongSW       Software Mismatch
    -- 6 resetThresh   Reset- Threshhold exceeded
    -- 9 SwMissing     Software not available on FTP- Server
    --
    --
    -- for NT VDSL:
    --
    -- 0 Internal      Internal Fault
    -- 4 WrongHw       Hardware Mismatch
    -- 5 WrongSW       Software Mismatch
    -- 6 resetThresh   Reset- Threshhold exceeded
    -- 9 SwMissing     Software not available on FTP- Server
    -- 11 ModemChip    Error on Modem- Chip occured
    -- 12 AnalogChip   Error on Analog- Chip occured
    -- 13 UtopiaTx     Utopia- Transmitter Error
    -- 14 UtopiaRx     Utopia- Receiver Error
    -- 15 Wdt          Watchdog Timer Failure
    -- 16 Ram          Ram Fault
    -- 17 SwCrc        Software Cyclic Redundancy Check Fault
    -- 18 FwCrc        Firmware Cyclic Redundancy Check Fault
    --
    --
    -- for POSU:
    --
    -- 0 Internal      Internal Fault
    -- 3 I2cRead       Inventory Data not  readable
    -- 4 WrongHw       Hardware Mismatch
    --
    --
    -- for PS&AM:
    --
    -- 0 Internal      Internal Fault
    -- 3 I2cRead       Inventory Data not  readable
    -- 4 WrongHw       Hardware Mismatch
    --
    --
    -- for SUAD16:
    --
    -- 0 Internal          Internal Fault
    -- 1 HwMissing         Hardware is removed when LU is unlocked
    -- 2 LossOfComm        Loss of Communication
    -- 3 I2cRead           Inventory Data not  readable
    -- 4 WrongHw           Hardware Mismatch
    -- 5 WrongSW           Software Mismatch
    -- 6 resetThresh       Reset- Threshhold exceeded
    -- 8 IndeterminateHw   Hardware Type not  readable during startup
    -- 9 SwMissing         Software not available on FTP- Server
    -- 10 HwRemoved        Hardware is removed when LU is locked
    -- 11 Ut2aTcLt1Utopia  Error of UTOPIA- Interface  between UT2A and TC_LT- Chip1
    -- 12 Ut2aTcLt2Utopia  Error of UTOPIA- Interface  between UT2A and TC_LT- Chip2
    -- 13 Ut2aTcLt3Utopia  Error of UTOPIA- Interface  between UT2A and TC_LT- Chip3
    -- 14 Ut2aTcLt4Utopia  Error of UTOPIA- Interface  between UT2A and TC_LT- Chip4
    -- 15 Wdt              Watchdog Timer Failure
    -- 16 Ram              Ram Fault
    -- 17 SwCrc            Software  Cyclic Redundancy Check Fault
    -- 18 FwCrc            Firmware Cyclic Redundancy Check Fault
    -- 19 Ut2a1            Ut2a1Chip Error
    -- 20 Ut2a2            Ut2a2 Chip Error
    -- 21 TcLtCrc          TcLt  Cyclic Redundancy Check Fault
    -- 22 TcLt1            Error occured on TC_LT- Chip1
    -- 23 TcLt2            Error occured on TC_LT- Chip2
    -- 24 TcLt3            Error occured on TC_LT- Chip3
    -- 25 TcLt4            Error occured on TC_LT- Chip4
    -- 26 BBBClk           Broadbandmaster-Clock Failure
    --
    --
    -- for SUVDSL:
    --
    -- 0 Internal          Internal Fault
    -- 1 HwMissing         Hardware is removed when LU is unlocked
    -- 2 LossOfComm        Loss of Communication
    -- 3 I2c               Read Inventory Data not  readable
    -- 4 WrongHw           Hardware Mismatch
    -- 5 WrongSW           Software Mismatch
    -- 6 resetThresh       Reset- Threshhold exceeded
    -- 7 selftest          Selftest failure
    -- 8 IndeterminateHw   Hardware Type not  readable during startup
    -- 9 SwMissing         Software not available on FTP- Server
    -- 10 HwRemoved        Hardware is removed when LU is locked
    -- 11 ModemChip        Error on Modem- Chip occured
    -- 12 AnalogChip       Error on Analog- Chip occured
    -- 13 UtopiaTx0        Utopia- Transmitter Error
    -- 14 UtopiaRx0        Utopia- Receiver Error
    -- 15 Wdt              Watchdog Timer
    -- 16 Ram              Ram Fault
    -- 17 SwCrc            Software Cyclic Redundancy Check Fault
    -- 18 FwCrc            Firmware Cyclic Redundancy Check Fault
    -- 19 Ut2a0            Ut2a0Chip Error
    --
    --
    -- for UPL:
    --
    -- 0 Internal          Internal Fault
    -- 3 I2cRead           Inventory Data not  readable
    -- 4 WrongHw           Hardware Mismatch
    --
    --
    -- for Near End PPTP:
    --
    -- 0 Internal          ONU internal activation problems with PPTP
    -- 1 Lpr               Loss of Power (dying gasp)
    -- 2 Lol               Loss of Link (ADC Los without preceding ADR Lpr)
    -- 3 Los               Loss of Signal
    -- 4 Act               Activation of ADSL- Line not possible
    -- 5 ImmMNR            Margin Not Reached
    -- 6 Ais               Alarm Indication Signal
    -- 7 Lof               Loss of Frame
    -- 8 RsEber            Excessive Bit Error Ratio threshhold to be
    --                     configured, Parity Error. B1, 1 Byte, RSOH
    -- 9 MsAis             Muliplexer Section Line Alarm Indication Signal
    -- 10 MsEber            Excessive Bit Error threshhold to be configured,
    --                     Parity B2, 3 Byte, MSOH
    -- 11 MsSd              Multiplexer Section Line Signal Degrade, to be configured
    -- 12 Lop              Loss of Pointer
    -- 13 PAis             Path Alarm Indication Signal
    -- 14 HpEber           Excessive Bit Error threshhold to be configured,
    --                     Parity B3, 1 Byte, Path Overhead
    -- 15 HpUneq           Higher Order Path Unequipped
    -- 16 PlcpLof          Loss of Plcp (Physical Layer Convergence Protocol) Frame
    -- 17 Tim              Trace ID Mismatch
    -- 18 Slm              Signal Label Mismatch
    -- 19 HiBer            High Bit Error Fault
    -- 20 XmissionErr      Transmission Error on Ethernet- NT
    -- 21 Lomf             Loss of Multiframe
    --
    --
    -- for Far End PPTP:
    --
    -- 0 Internal          Activation Problems of a PPTP
    -- 1 Rdi               Remote Defect Indication
    -- 2 MsRdi             Multiplex Section Remote Defect Indication
    -- 3 PRdi              p:G1(bit5=1(Alarm) or 0(o.k.) Remote Defect Indication
    -- 4 PlcpRdi           Plcp (Physical Layer Convergence Protocol) Remote Defect Indication
    --
    --
    -- for TC Adaptor:
    --
    -- 0 Internal          Activation Problems of a TCA
    -- 1 Lcd               Loss of Cell Delineation (ATM- HEC)
    --
    --
    -- for VPL-TP/VCL-TP/VPC-TP/VCC-TP:
    --
    -- 0 DwnstrmAis        Downstream Alarm Indication Signal
    -- 1 DwnstrmRdi        Downstream Remote Defect Indication
    -- 2 UpstrmAis         Upstream Alarm Indication Signal
    -- 3 UpstrmRdi         Upstream Remote Defect Indication
    -- 4 LOC               Loss of Continuity
    --
    --
    -- for External Alarms:
    --
    -- 0 ExtAlm            External Alarm
    --
    --
    -- Open: ATM-Layer fault for TCA and PPTP, dying gasp fault for NT-ADSL, Loss of Link for
    -- PPTP
    --

 -- --------------------------------------------------------------
 --                    External Alarms Table (XLDV1.1U)
 -- --------------------------------------------------------------

 xldv11ExternalAlarmsTable OBJECT-TYPE
    -- info-NODE:    xldv11ExternalAlarmsTable
    -- info-TREE:    xldv11Alarming
    -- info-ACC:     nac
    -- info-SYNTAX:  SEQUENCE OF Xldv11ExternalAlarmEntry
    -- info-COMMENT: Table of external alarm objects
    -- info-IMPL:    V1.1U V1.3A->
    SYNTAX        SEQUENCE OF Xldv11ExternalAlarmEntry
    ACCESS        not-accessible
    STATUS        mandatory
    DESCRIPTION
	 " The entities of the table are used to control the
	   forwarding of external alarms to the TMN-OS and LCT. "
    ::= { xldv11Alarming 1 }

 xldv11ExternalAlarmEntry OBJECT-TYPE
    -- info-NODE:    xldv11ExternalAlarmEntry 
    -- info-TREE:    xldv11Tlm
    -- info-INDEX:   xldv11ExtAlarmIndex
    -- info-ACC:     nac
    -- info-SYNTAX:  Xldv11ExternalAlarmEntry
    -- info-COMMENT: entries of external alarm table
    -- info-IMPL:    V1.1U V1.3A->
    SYNTAX        Xldv11ExternalAlarmEntry
    ACCESS        not-accessible
    STATUS        mandatory
    DESCRIPTION
	 " The attributes of an external alarm.
	   Notifications : xldv11TrExternalAlarm."
    INDEX         { xldv11ExtAlarmIndex }
    ::= { xldv11ExternalAlarmsTable 1 }

 Xldv11ExternalAlarmEntry ::=
      SEQUENCE { xldv11ExtAlarmIndex           INTEGER,
		 xldv11ExtAlarmAdminState      Xldv11AdminState,
		 xldv11ExtAlarmOperState       Xldv11OperState,
		 xldv11ExtAlarmActivityState   Xldv11ExtAlarmActivityState,
		 xldv11ExtAlarmSeverityIndex   Xldv11AlmSevProfileIndex,
		 xldv11ExtAlarmFilteringIndex  Xldv11AlmFiltProfileIndex,
		 xldv11ExtAlarmName            OCTET STRING }

  xldv11ExtAlarmIndex  OBJECT-TYPE
    -- info-LEAF:    xldv11ExtAlarmIndex
    -- info-TREE:    xldv11Alarming
    -- info-ACC:     ro
    -- info-SYNTAX:  INTEGER
    -- info-VALUE:   1..8
    -- info-COMMENT: identifies an external alarm object
    -- info-ROU:     GET db
    -- info-IMPL:    V1.1U V1.3A->
    -- info-VERCTRL: V1.2A..V1.2B: GET db SET blocked
    SYNTAX        INTEGER (1..8)
    ACCESS        read-only
    STATUS        mandatory
    DESCRIPTION
	 " A unique number identifying an entry of the 
	   external alarm table. "
    --DEFAULT next-function-async     fsnExtEntryNext
    --DEFAULT get-function-async      fsnExtEntryGet
    ::= { xldv11ExternalAlarmEntry 1 }

 xldv11ExtAlarmAdminState OBJECT-TYPE
    -- info-LEAF:    xldv11ExtAlarmAdminState
    -- info-TREE:    xldv11Alarming
    -- info-ACC:     rw
    -- info-SYNTAX:  Xldv11AdminState
    -- info-VALUE:   unlocked(1), locked(2)
    -- info-COMMENT: This attribute is used to activate (unlock) and
    -- info-COMMENT: deactivate (lock) the external alarm input line.
    -- info-ROU:     GET db  SET gf
    -- info-IMPL:    V1.1U V1.3A->
    -- info-VERCTRL: V1.2A..V1.2B: GET db SET blocked
    SYNTAX        Xldv11AdminState
    ACCESS        read-write
    STATUS        mandatory
    DESCRIPTION
	 " This attribute is used to activate (unlock) and deactivate
	   (lock) the forwarding of the external alarm towards the
	   manager. 
	   The range of values is: unlocked, locked. "
    --DEFAULT test-function-async     fsnExtEntryTest
    --DEFAULT next-function-async     fsnExtEntryNext
    --DEFAULT set-function-async      fsnExtEntrySet
    --DEFAULT get-function-async      fsnExtEntryGet
    ::= { xldv11ExternalAlarmEntry 2 }

 xldv11ExtAlarmOperState OBJECT-TYPE
    -- info-LEAF:    xldv11ExtAlarmOperState
    -- info-TREE:    xldv11Alarming
    -- info-ACC:     ro
    -- info-SYNTAX:  Xldv11OperState
    -- info-VALUE:   enabled(1), disabled(2)
    -- info-COMMENT: Indicates whether or not the external alarm is
    -- info-COMMENT: capable of performing its normal functions.
    -- info-ROU:     GET db
    -- info-IMPL:    V1.1U V1.3A->
    -- info-VERCTRL: -
    SYNTAX        Xldv11OperState
    ACCESS        read-only
    STATUS        mandatory
    DESCRIPTION
	 " This attribute summarizes the extAlarmAdminState and the 
	   operational state of the CMU to indicate whether the external
	   alarm name is supervised at the moment. Only if the operational
	   state is enabled, larms will be generated for the objects.
	   The range of values is: enabled, disabled. "
    --DEFAULT next-function-async     fsnExtEntryNext
    --DEFAULT get-function-async      fsnExtEntryGet
    ::= { xldv11ExternalAlarmEntry 3 }

 xldv11ExtAlarmActivityState OBJECT-TYPE
    -- info-LEAF:    xldv11ExtAlarmActivityState
    -- info-TREE:    xldv11Alarming
    -- info-ACC:     ro
    -- info-SYNTAX:  Xldv11ExtAlarmActivityState
    -- info-VALUE:   undeterminate(0), on(1), off(2)
    -- info-COMMENT: status of external alarm
    -- info-ROU:     GET db
    -- info-IMPL:    V1.1U V1.3A->
    -- info-VERCTRL: -
    SYNTAX        Xldv11ExtAlarmActivityState
    ACCESS        read-only
    STATUS        mandatory
    DESCRIPTION
	 " This attribute indicates the status of the external alarm
	   input line. Only if the operational state is enabled
	   and the alarm state is on, an external alarm is generated
	   for this object.
	   The range of values is: undeterminate(0), on(1), off(2). "
    --DEFAULT next-function-async     fsnExtEntryNext
    --DEFAULT get-function-async      fsnExtEntryGet
    ::= { xldv11ExternalAlarmEntry 4 }

 xldv11ExtAlarmSeverityIndex OBJECT-TYPE
    -- info-LEAF:    xldv11ExtAlarmSeverityIndex
    -- info-TREE:    xldv11Alarming
    -- info-ACC:     rw
    -- info-SYNTAX:  Xldv11AlmSevProfileIndex
    -- info-VALUE:   1..40
    -- info-COMMENT: Pointer to the instance of the alarm severity
    -- info-COMMENT: profile that contains the severity assignments
    -- info-COMMENT: for the alarms reported by this external alarm object.
    -- info-ROU:     GET db  SET db
    -- info-IMPL:    V1.1U:ro->V1.3H:ro V1.3A->
    -- info-VERCTRL: GET db SET blocked
    SYNTAX        Xldv11AlmSevProfileIndex
    ACCESS        read-write
    STATUS        mandatory
    DESCRIPTION
	 " The index of the associated entry in the alarm severity
	   profile table. These entries contain the severity
	   assigments for the alarms reported by this managed
	   entity. Default is 1. "
    --DEFAULT test-function-async     fsnExtEntryTest
    --DEFAULT next-function-async     fsnExtEntryNext
    --DEFAULT set-function-async      fsnExtEntrySet
    --DEFAULT get-function-async      fsnExtEntryGet
    ::= { xldv11ExternalAlarmEntry 5 }

 xldv11ExtAlarmFilteringIndex OBJECT-TYPE
    -- info-LEAF:    xldv11ExtAlarmFilteringIndex
    -- info-TREE:    xldv11Alarming
    -- info-ACC:     ro
    -- info-SYNTAX:  Xldv11AlmFiltProfileIndex
    -- info-VALUE:   1..40
    -- info-COMMENT: Pointer to the instance of the alarm filtering profile
    -- info-COMMENT: that contains the filtering assignments for the alarms
    -- info-COMMENT: reported by this external alarm object.
    -- info-ROU:     GET db
    -- info-IMPL:    V1.x
    -- info-VERCTRL: V1.1U:GET db
    SYNTAX        Xldv11AlmFiltProfileIndex
    ACCESS        read-only
    STATUS        mandatory
    DESCRIPTION
	 " It is a pointer to the instance of the alarm filtering
	   assignment profile managed entity that contains the filtering
	   assignments for the alarms reported by this managed entity.
	   (Not implemented) "
    --DEFAULT next-function-async     fsnExtEntryNext
    --DEFAULT get-function-async      fsnExtEntryGet
    ::= { xldv11ExternalAlarmEntry 6 }

    xldv11ExtAlarmName OBJECT-TYPE
    -- info-LEAF:    xldv11ExtAlarmName
    -- info-TREE:    xldv11Alarming
    -- info-ACC:     rw
    -- info-SYNTAX:  OCTET STRING ( SIZE (0..50) ) 
    -- info-VALUE:   -
    -- info-COMMENT: text describing type of external alarm
    -- info-ROU:     GET db SET db
    -- info-IMPL:    V1.1U V1.3A->
    -- info-VERCTRL: -
    SYNTAX        OCTET STRING ( SIZE (0..50) )
    ACCESS        read-write
    STATUS        mandatory
    DESCRIPTION
	 " This text field is used to describe the input line
	   and the type of external alarm.
	   Default values on startup are :
	     XLDV1.1U :
	   index=1 : AND Battery
	   index=2 : OR Battery
	   index=3 : AND Power Supply
	   index=4 : OR Power Supply
	   index={n: 5<=n<=8} : External Alarm n.
	  XLDV1.1 :
	   index=1 : Fan Failure
	   index=2 : Fuse Failure
	   index=3 : High Temperature
	   index=4 : Door Open
	   index=5 : Main Connection Failure
	   index=6 : Power Supply Defect
	   index=7 : Battery Deep Discharge Failure
	   index=8 : External Alarm 8. "
    --DEFAULT test-function-async     fsnExtEntryTest
    --DEFAULT next-function-async     fsnExtEntryNext
    --DEFAULT set-function-async      fsnExtEntrySet
    --DEFAULT get-function-async      fsnExtEntryGet
    ::= { xldv11ExternalAlarmEntry 7 }

 -- --------------------------------------------------------------
 --               Alarm Severity Profile Table (XLDV1.1U)
 -- --------------------------------------------------------------

 xldv11AlarmSeverityProfileTable OBJECT-TYPE
    -- info-NODE:    xldv11AlarmSeverityProfileTable
    -- info-TREE:    xldv11Alarming
    -- info-ACC:     nac
    -- info-SYNTAX:  SEQUENCE OF Xldv11AlarmSeverityProfileEntry
    -- info-COMMENT: table of alarm severity profiles
    -- info-IMPL:    V1.3A->
    -- info-VERCTRL: V1.1U..V1.2B:GET db SET blocked
    SYNTAX        SEQUENCE OF Xldv11AlarmSeverityProfileEntry
    ACCESS        not-accessible
    STATUS        mandatory
    DESCRIPTION
	 " The alarm severity profile table.
	   This table specifies which profile exists. 
	   XLDV1.1 : profiles can be created or deleted dynamically.
	   Creating or deleting an entry in this table automatically creates
	   or deletes the corresponding entries in the
	   xldv11AlarmSevTable. "
    ::= { xldv11Alarming 2 }

 xldv11AlarmSeverityProfileEntry OBJECT-TYPE
    -- info-NODE:    xldv11AlarmSeverityProfileEntry
    -- info-TREE:    xldv11Alarming
    -- info-INDEX:   xldv11AlmSevProfileIndex
    -- info-ACC:     nac
    -- info-SYNTAX:  Xldv11AlarmSeverityProfileEntry
    -- info-COMMENT: entry of alarm severity profiles table
    -- info-IMPL:    V1.3A->
    -- info-VERCTRL: V1.1U..V1.2B:GET db SET blocked
    SYNTAX        Xldv11AlarmSeverityProfileEntry
    ACCESS        not-accessible
    STATUS        mandatory
    DESCRIPTION
	 " A group of severities, one for each alarm type in
	   the communications alarm group.
	   Notifications : none."
    INDEX         { xldv11AlmSevProfileIndex }
    ::= { xldv11AlarmSeverityProfileTable 1 }

 Xldv11AlarmSeverityProfileEntry ::=
    SEQUENCE { xldv11AlmSevProfileIndex      Xldv11AlmSevProfileIndex,
	       xldv11AlmSevProfileRowStatus  Xldv11RowStatus }

 xldv11AlmSevProfileIndex OBJECT-TYPE
    -- info-LEAF:    xldv11AlmSevProfileIndex
    -- info-TREE:    xldv11Alarming
    -- info-ACC:     ro
    -- info-SYNTAX:  Xldv11AlmSevProfileIndex
    -- info-VALUE:   1..40
    -- info-COMMENT: identifies this profile
    -- info-ROU:     GET db
    -- info-VALUE:   create(1), delete(2)
    -- info-VERCTRL: V1.1U->:GET db
    SYNTAX        Xldv11AlmSevProfileIndex
    ACCESS        read-only
    STATUS        mandatory
    DESCRIPTION
	 " A number identifying this alarm severity profile.
	   Default value: 1 . "
    --DEFAULT get-function-async      fsnAlmSevProfileEntryGet
    --DEFAULT next-function-async     fsnAlmSevProfileEntryNext
    ::= { xldv11AlarmSeverityProfileEntry 1 }

 xldv11AlmSevProfileRowStatus OBJECT-TYPE
    -- info-LEAF:    xldv11AlmSevProfileRowStatus
    -- info-TREE:    xldv11Alarming
    -- info-ACC:     rw
    -- info-SYNTAX:  Xldv11RowStatus
    -- info-VALUE:   create(1), delete(2)
    -- info-COMMENT: used to create or delete a profile
    -- info-ROU:     GET db SET db
    -- info-IMPL:    V1.3A->
    -- info-VERCTRL: V1.1U..V1.2B:GET db SET blocked
    SYNTAX        Xldv11RowStatus
    ACCESS        read-write
    STATUS        mandatory
    DESCRIPTION
	 " This object is used to create a new row or to delete
	   an existing row in the table.
	   Range of value: created, deleted.
	   Default value:
	       xldv11AlmSevProfileIndex = 1..10:  created
	       xldv11AlmSevProfileIndex = 11..40: deleted . "
    --DEFAULT test-function-async     fsnAlmSevProfileEntryTest
    --DEFAULT next-function-async     fsnAlmSevProfileEntryNext
    --DEFAULT set-function-async      fsnAlmSevProfileEntrySet
    --DEFAULT get-function-async      fsnAlmSevProfileEntryGet
    ::= { xldv11AlarmSeverityProfileEntry 2 }

 -- --------------------------------------------------------------
 --                    Alarm Severity Table
 -- --------------------------------------------------------------

 xldv11AlarmSeverityTable OBJECT-TYPE
    -- info-NODE:    xldv11AlarmSeverityTable
    -- info-TREE:    xldv11Alarming
    -- info-ACC:     nac
    -- info-SYNTAX:  SEQUENCE OF Xldv11AlarmSeverityEntry
    -- info-COMMENT: table of alarm severities
    -- info-IMPL:    V1.0->
    SYNTAX        SEQUENCE OF Xldv11AlarmSeverityEntry
    ACCESS        not-accessible
    STATUS        mandatory
    DESCRIPTION
	 " The XLDV11 alarm severity table. This table associates
	   profile index and trap ID pairs with severities to be
	   used for alarm traps that have occurred.
	   (Note that this table does not apply to cleared alarms). "
    ::= { xldv11Alarming 3 }

 xldv11AlarmSeverityEntry OBJECT-TYPE
    -- info-NODE:    xldv11AlarmSeverityEntry
    -- info-TREE:    xldv11Alarming
    -- info-INDEX:   xldv11AlmSevProfileIndex, xldv11AlmSevTrapId
    -- info-ACC:     nac
    -- info-SYNTAX:  Xldv11AlarmSeverityEntry
    -- info-COMMENT: entries of alarm severity table
    -- info-IMPL:    V1.0->
    SYNTAX        Xldv11AlarmSeverityEntry
    ACCESS        not-accessible
    STATUS        mandatory
    DESCRIPTION
	 " An entry in this table associates an alarm severity
	   profile index/trap ID pair with a severity to be used
	   for alarm traps.
	   The alarm severity profile index is referenced by the
	   'Alarm Severity assignment Profile Pointer' attribute
	   in the alarm-reporting managed entity e.g. plug-in unit
	   and TLM interface (tcAdaptor, Physical Path Termination
	   Point etc.).
	   Notifications : none."
    INDEX         { xldv11AlmSevProfileIndex,xldv11AlmSevTrapId }
    ::= { xldv11AlarmSeverityTable 1 }

 Xldv11AlarmSeverityEntry ::=
    SEQUENCE { xldv11AlmSevTrapId  Xldv11TrapIds,
	       xldv11AlmSeverity   Xldv11AlarmSeverity }

 xldv11AlmSevTrapId OBJECT-TYPE
    -- info-LEAF:    xldv11AlmSevTrapId
    -- info-TREE:    xldv11Alarming
    -- info-ACC:     ro
    -- info-SYNTAX:  Xldv11TrapIds
    -- info-VALUE:   trHpExcBER (1), trHpUNEQ (2)
    -- info-VALUE:   trLcd (3), trLof (4)
    -- info-VALUE:   trLop (5), trLos (6)
    -- info-VALUE:   trMsAIS (7), trMsExcBER (8)
    -- info-VALUE:   trMsRDI (9), trMsSD (10)
    -- info-VALUE:   trPAIS (11), trPRDI (12)
    -- info-VALUE:   trRsExcBER (13), trSlm (14)
    -- info-VALUE:   trTim (15), trActFault (16)
    -- info-VALUE:   trReplaceableUnitTypeMismatch (17)
    -- info-VALUE:   trReplaceableUnitFailure (18)
    -- info-VALUE:   trReplaceableUnitProblem (19)
    -- info-VALUE:   trReplaceableUnitNotInstalled (20)
    -- info-VALUE:   trReplaceableUnitSwMismatch(21)
    -- info-VALUE:   trHiBER(43)
    -- info-VALUE:   XLD V1.1U alarms :
    -- info-VALUE:   trLOMF(102) pon
    -- info-VALUE:   trFail(103) pon
    -- info-VALUE:   trLPS(104)  vdc, vdr
    -- info-VALUE:   trExternalAlarm(110),  external alarm
    -- info-VALUE:   trReplaceableUnitRemoved(113)
    -- info-VALUE:   trReplaceableUnitSwMissing(123)
    -- info-VALUE:   trInternalFault(124)
    -- info-VALUE:   XLD V1.1L alarms : 
    -- info-VALUE:   trXmissionErr(105) eth
    -- info-VALUE:   trVpcTpAIS(106) vpc
    -- info-VALUE:   trVpcTpRDI(107) vpc
    -- info-VALUE:   trVccTpAIS(108) vcc
    -- info-VALUE:   trVccTpRDI(109) vcc
    -- info-VALUE:   XLD V1.2A alarms : 
    -- info-VALUE:   trT3Los(114)   d3n, s1n
    -- info-VALUE:   trAIS(115)     d3n
    -- info-VALUE:   trRDI(116)     d3f
    -- info-VALUE:   trPlcpLof(117) d3n
    -- info-VALUE:   trPlcpRDI(118) d3n
    -- info-VALUE:   trReplaceableUnitSwMissing(122)
    -- info-VALUE:   trInternalFault(123)
    -- info-VALUE:   XLD V1.3A alarms : 
    -- info-VALUE:   trImmMNR(132)  adc
    -- info-VALUE:   trLpr(133)     adr
    -- info-VALUE:   trLol(134)     adc
    -- info-VALUE:   trAtmMultiLayerAlarm(137) vpcTp, vccTp
    -- info-COMMENT: ID of trap this entry applies to
    -- info-ROU:     GET db
    -- info-IMPL:    V1.0->
    -- info-VERCTRL: -
    SYNTAX        Xldv11TrapIds
    ACCESS        read-only
    STATUS        mandatory
    DESCRIPTION
	 " The ID of the trap type this entry applies to.
	   Note that XLDV1.1 inherits all traps from XLDV1.0.
	   Range of values:
	      XLD V1.0 alarms : 
		xldv11TrHpExcBER (1)
		xldv11TrHpUNEQ (2)
		xldv11TrLcd (3)
		xldv11TrLof (4)
		xldv11TrLop (5)
		xldv11TrLos (6)
		xldv11TrMsAIS (7)
		xldv11TrMsExcBER (8)
		xldv11TrMsRDI (9)
		xldv11TrMsSD (10)
		xldv11TrPAIS (11)
		xldv11TrPRDI (12)
		xldv11TrRsExcBER (13)
		xldv11TrSlm (14)
		xldv11TrTim (15)
		xldv11TrActFault (16)
		xldv11TrReplaceableUnitTypeMismatch (17)
		xldv11TrReplaceableUnitFailure (18)
		xldv11TrReplaceableUnitProblem (19)
		xldv11TrReplaceableUnitNotInstalled (20)
		xldv11TrReplaceableUnitSwMismatch(21)
		xldv11TrHiBER(43)
	      XLD V1.1U alarms :
		xldv11TrLOMF(102)           -- pon
		xldv11TrFail(103)           -- pon
		xldv11TrLPS(104)            -- vdc, vdr
		xldv11TrExternalAlarm(110)  -- external alarm
		xldv11TrReplaceableUnitRemoved(113)
		xldv11TrReplaceableUnitSwMissing(123)
		xldv11TrInternalFault(124)
	      XLD V1.1L alarms : 
		xldv11TrXmissionErr(105)    -- eth
		xldv11TrVpcTpAIS(106)       -- vpc
		xldv11TrVpcTpRDI(107)       -- vpc
		xldv11TrVccTpAIS(108)       -- vcc
		xldv11TrVccTpRDI(109)       -- vcc
	      XLD V1.2A alarms : 
		xldv11TrT3Los(114)          -- d3n, s1n
		xldv11TrAIS(115)            -- d3n
		xldv11TrRDI(116)            -- d3f
		xldv11TrPlcpLof(117)        -- d3n
		xldv11TrPlcpRDI(118)        -- d3n
		xldv11TrReplaceableUnitSwMissing(122)
		xldv11TrInternalFault(123)
	      XLD V1.3A alarms : 
		xldv11TrImmMNR(132)         -- adc
		xldv11TrLpr(133)            -- adr
		xldv11TrLol(134)            -- adc
		xldv11TrAtmMultiLayerAlarm(137) -- vpcTp, vccTp
		."
    --DEFAULT get-function-async     fsnAlmSevEntryGet
    --DEFAULT next-function-async    fsnAlmSevEntryNext
    ::= { xldv11AlarmSeverityEntry 1 }

 xldv11AlmSeverity OBJECT-TYPE
    -- info-LEAF:    xldv11AlmSeverity
    -- info-TREE:    xldv11Alarming
    -- info-ACC:     rw
    -- info-SYNTAX:  Xldv11AlarmSeverity 
    -- info-VALUE:   critical(1), major(2)
    -- info-VALUE:   minor(3), warning(4), noAlarming(5)
    -- info-COMMENT: severity of alarm
    -- info-ROU:     GET db SET db
    -- info-IMPL:    V1.0->
    -- info-VERCTRL: V1.0..V1.2B:GET db SET blocked 
    SYNTAX        Xldv11AlarmSeverity
    ACCESS        read-write
    STATUS        mandatory
    DESCRIPTION
	 " The severity to be used for this trap type when the
	   entry is selected. "
    --DEFAULT test-function-async     fsnAlmSevEntryTest
    --DEFAULT next-function-async     fsnAlmSevEntryNext
    --DEFAULT set-function-async      fsnAlmSevEntrySet
    --DEFAULT get-function-async      fsnAlmSevEntryGet
    ::= { xldv11AlarmSeverityEntry 2 }

 -- --------------------------------------------------------------
 --                Alarm Filtering Profile Table (XLDV1.x)
 -- --------------------------------------------------------------

 xldv11AlarmFilteringProfileTable OBJECT-TYPE
    -- info-NODE:    xldv11AlarmFilteringProfileTable
    -- info-TREE:    xldv11Alarming
    -- info-ACC:     nac
    -- info-SYNTAX:  SEQUENCE OF Xldv11AlarmFilteringProfileEntry
    -- info-COMMENT: table of alarm filtering profiles
    -- info-IMPL:    V1.x
    SYNTAX        SEQUENCE OF Xldv11AlarmFilteringProfileEntry
    ACCESS        not-accessible
    STATUS        mandatory
    DESCRIPTION
	 " The alarm filtering profile table.
	   This table specifies which profile exists. Creating or
	   deleting an entry in this table automatically creates
	   or deletes the corresponding entries in the
	   xldv11AlarmFilteringTable. "
    ::= { xldv11Alarming 4 }

 xldv11AlarmFilteringProfileEntry OBJECT-TYPE
    -- info-NODE:    xldv11AlarmFilteringProfileEntry
    -- info-TREE:    xldv11Alarming
    -- info-INDEX:   xldv11AlmFiltProfileIndex
    -- info-ACC:     nac
    -- info-SYNTAX:  Xldv11AlarmFilteringProfileEntry
    -- info-COMMENT: entry of alarm filtering profile table
    -- info-IMPL:    V1.x
    SYNTAX        Xldv11AlarmFilteringProfileEntry
    ACCESS        not-accessible
    STATUS        mandatory
    DESCRIPTION
	 " A group of severities, one for each alarm type in
	   the communications alarm group. "
    INDEX         { xldv11AlmFiltProfileIndex }
    ::= { xldv11AlarmFilteringProfileTable 1 }

 Xldv11AlarmFilteringProfileEntry ::=
    SEQUENCE { xldv11AlmFiltProfileIndex      Xldv11AlmFiltProfileIndex,
	       xldv11AlmFiltProfileRowStatus  Xldv11RowStatus }

 xldv11AlmFiltProfileIndex OBJECT-TYPE
    -- info-LEAF:    xldv11AlmFiltProfileIndex
    -- info-TREE:    xldv11Alarming
    -- info-ACC:     ro
    -- info-SYNTAX:  Xldv11AlmFiltProfileIndex
    -- info-VALUE:   1..40
    -- info-COMMENT: identifies this profile
    -- info-ROU:     GET db
    -- info-IMPL:    V1.x
    -- info-VERCTRL: V1.1U->:GET db
    SYNTAX        Xldv11AlmFiltProfileIndex
    ACCESS        read-only 
    STATUS        mandatory
    DESCRIPTION
	 " A number identifying this alarm filtering profile.
	   Range of value: 1..40
	   Default value: 1 . "
    --DEFAULT next-function-async     fsnAlmFiltProfileEntryNext
    --DEFAULT get-function-async      fsnAlmFiltProfileEntryGet
    ::= { xldv11AlarmFilteringProfileEntry 1 }

 xldv11AlmFiltProfileRowStatus OBJECT-TYPE
    -- info-LEAF:    xldv11AlmFiltProfileRowStatus
    -- info-TREE:    xldv11Alarming
    -- info-ACC:     ro
    -- info-SYNTAX:  Xldv11RowStatus
    -- info-VALUE:   create(1), delete(2)
    -- info-COMMENT: used to create or delete a profile
    -- info-ROU:     GET db
    -- info-IMPL:    V1.x
    -- info-VERCTRL: V1.1U->:GET db
    SYNTAX        Xldv11RowStatus
    ACCESS        read-only
    STATUS        mandatory
    DESCRIPTION
	 " This object is used to create a new row or to delete
	   an existing row in the table.
	   Default value: xldv11AlmFiltProfileIndex = 1: created
			  xldv11AlmFiltProfileIndex = 2 .. 300: deleted . "
    --DEFAULT next-function-async     fsnAlmFiltProfileEntryNext
    --DEFAULT get-function-async      fsnAlmFiltProfileEntryGet
    ::= { xldv11AlarmFilteringProfileEntry 2 }

 -- --------------------------------------------------------------
 --                   Alarm Filtering Table (XLDV1.1)
 -- --------------------------------------------------------------

 xldv11AlarmFilteringTable OBJECT-TYPE
    -- info-NODE:    xldv11AlarmFilteringTable
    -- info-TREE:    xldv11Alarming
    -- info-ACC:     nac
    -- info-SYNTAX:  SEQUENCE OF Xldv11AlarmFilteringEntry
    -- info-COMMENT: table of alarm filtering
    -- info-IMPL:    V1.x
    SYNTAX        SEQUENCE OF Xldv11AlarmFilteringEntry
    ACCESS        not-accessible
    STATUS        mandatory
    DESCRIPTION
	 " The XLDV11 alarm filtering table. This table is used for
	   temporairy filtering of alarms. "
    ::= { xldv11Alarming 5 }

 xldv11AlarmFilteringEntry OBJECT-TYPE
    -- info-NODE:    xldv11AlarmFilteringEntry
    -- info-TREE:    xldv11Alarming
    -- info-INDEX:   xldv11AlmFiltProfileIndex, xldv11AlmFiltTrapId
    -- info-ACC:     nac
    -- info-SYNTAX:  Xldv11AlarmFilteringEntry
    -- info-COMMENT: entry of alarm filtering table
    -- info-IMPL:    V1.x
    SYNTAX        Xldv11AlarmFilteringEntry
    ACCESS        not-accessible
    STATUS        mandatory
    DESCRIPTION
	 " An entry in this table associates a trap id/ temporal
	   filter parameter with a xlv11AlmFiltProfileIndex.
	   Notifications : none."
    INDEX   { xldv11AlmFiltProfileIndex,
	      xldv11AlmFiltTrapId }
    ::= { xldv11AlarmFilteringTable 1 }

 Xldv11AlarmFilteringEntry ::=
    SEQUENCE { xldv11AlmFiltTrapId   Xldv11TrapIds,
	       xldv11AlmTempFilter   INTEGER }

 xldv11AlmFiltTrapId OBJECT-TYPE
    -- info-LEAF:    xldv11AlmFiltTrapId
    -- info-TREE:    xldv11Alarming
    -- info-ACC:     ro
    -- info-SYNTAX:  Xldv11TrapIds
    -- info-VALUE:   see xldv11AlmSevTrapId
    -- info-COMMENT: ID of trap this entry applies to
    -- info-ROU:     GET db
    -- info-IMPL:    V1.x
    -- info-VERCTRL: V1.1U->:GET db
    SYNTAX        Xldv11TrapIds
    ACCESS        read-only 
    STATUS        mandatory
    DESCRIPTION
	 " The ID of the trap type this entry applies to.
	   Range of values:  see xldv11AlmSevTrapId."
    --DEFAULT next-function-async     fsnAlmFiltEntryNext
    --DEFAULT get-function-async      fsnAlmFiltEntryGet
    ::= { xldv11AlarmFilteringEntry 1 }

 xldv11AlmTempFilter OBJECT-TYPE
    -- info-LEAF:    xldv11AlmTempFilter
    -- info-TREE:    xldv11Alarming
    -- info-ACC:     ro
    -- info-SYNTAX:  INTEGER
    -- info-VALUE:   1..86400
    -- info-COMMENT: temporal filtering period in sec
    -- info-COMMENT: 0 means no filtering
    -- info-ROU:     GET db
    -- info-IMPL:    V1.x
    -- info-VERCTRL: V1.1U->:GET db
    SYNTAX        INTEGER (0..86400)
    ACCESS        read-only
    STATUS        mandatory
    DESCRIPTION
	 " The temporal filtering period in seconds.
	   The value 0 means no filtering. "
    --DEFAULT next-function-async     fsnAlmFiltEntryNext
    --DEFAULT get-function-async      fsnAlmFiltEntryGet
    ::= { xldv11AlarmFilteringEntry 2 }

 -- --------------------------------------------------------------
 --                      Alarm List Table
 -- --------------------------------------------------------------

 xldv11AlarmListTable OBJECT-TYPE
    -- info-NODE:    xldv11AlarmListTable
    -- info-TREE:    xldv11Alarming
    -- info-ACC:     nac
    -- info-SYNTAX:  SEQUENCE OF Xldv11AlarmListEntry
    -- info-COMMENT: alarm list table
    -- info-IMPL:    V1.0->
    SYNTAX        SEQUENCE OF Xldv11AlarmListEntry
    ACCESS        not-accessible
    STATUS        mandatory
    DESCRIPTION
	 " This managed entity is used to store all alarms reported by HWM,
	   TLM, CallP or GFH. Most of the attributes are identical to the
	   parameters (varBindList) of the alarm trap. "
    ::= { xldv11Alarming 6 }

 xldv11AlarmListEntry OBJECT-TYPE
    -- info-NODE:    xldv11AlarmListEntry
    -- info-TREE:    xldv11Alarming
    -- info-INDEX:   xldv11AlmIndex
    -- info-ACC:     nac
    -- info-SYNTAX:  Xldv11AlarmListEntry
    -- info-COMMENT: alarm list table
    -- info-IMPL:    V1.0->
    SYNTAX        Xldv11AlarmListEntry
    ACCESS        not-accessible
    STATUS        mandatory
    DESCRIPTION
	 " Entry of the alarm list table.
	   Notifications : none."
    INDEX         { xldv11AlmIndex }
    ::= { xldv11AlarmListTable 1 }

 Xldv11AlarmListEntry ::=
    SEQUENCE { xldv11AlmIndex               INTEGER,
	       xldv11AlmNatureOfAlarm       Xldv11TrapIds,
	       xldv11AlmSpecProblem         INTEGER,
	       xldv11AlmRepEntityId         Integer32,
	       xldv11AlmRepSource           Xldv11RepSource,
	       xldv11AlmFailedComponent     Integer32,
	       xldv11AlmFailedComponentRepSource  Xldv11RepSource,
	       xldv11AlmSeverityOfFailure   Xldv11AlarmSeverity,
	       xldv11AlmPropRepairAction    Integer32,
	       xldv11AlmTimeAndDate         Integer32 }

 xldv11AlmIndex OBJECT-TYPE
    -- info-LEAF:    xldv11AlmIndex
    -- info-TREE:    xldv11Alarming
    -- info-ACC:     ro
    -- info-SYNTAX:  INTEGER
    -- info-VALUE:   1..200
    -- info-COMMENT: identifies this profile
    -- info-ROU:     GET db
    -- info-IMPL:    V1.0->
    -- info-VERCTRL: -
    SYNTAX        INTEGER (1..200)
    ACCESS        read-only
    STATUS        mandatory
    DESCRIPTION
	 " Unique value to identify an entry in the alarm list when the
	   entry is read or cleared, when the entry is created. "
    --DEFAULT next-function-async     fsnAlmListEntryNext
    --DEFAULT get-function-async      fsnAlmListEntryGet
    ::= { xldv11AlarmListEntry 1 }

 xldv11AlmNatureOfAlarm OBJECT-TYPE
    -- info-LEAF:    xldv11AlmNatureOfAlarm
    -- info-TREE:    xldv11Alarming
    -- info-ACC:     ro
    -- info-SYNTAX:  Xldv11TrapIds
    -- info-VALUE:   see xldv11AlmSevTrapId
    -- info-COMMENT: nature of alarm (trap ID)
    -- info-ROU:     GET db
    -- info-IMPL:    V1.0->
    -- info-VERCTRL: -
    SYNTAX        Xldv11TrapIds
    ACCESS        read-only
    STATUS        mandatory
    DESCRIPTION
	 " Nature of alarm ( trap ID ) . "
    --DEFAULT next-function-async     fsnAlmListEntryNext
    --DEFAULT get-function-async      fsnAlmListEntryGet
    ::= { xldv11AlarmListEntry 2 }

 xldv11AlmSpecProblem OBJECT-TYPE
    -- info-LEAF:    xldv11AlmSpecProblem
    -- info-TREE:    xldv11Alarming
    -- info-ACC:     ro
    -- info-SYNTAX:  INTEGER
    -- info-VALUE:   0..255 
    -- info-COMMENT: -
    -- info-ROU:     GET db
    -- info-IMPL:    V1.0->
    -- info-VERCTRL: -
    SYNTAX        INTEGER (0..255)
    ACCESS        read-only
    STATUS        mandatory
    DESCRIPTION
	 " Description of further information about an alarm. "
    --DEFAULT next-function-async     fsnAlmListEntryNext
    --DEFAULT get-function-async      fsnAlmListEntryGet
    ::= { xldv11AlarmListEntry 3 }

 xldv11AlmRepEntityId OBJECT-TYPE
    -- info-LEAF:    xldv11AlmRepEntityId
    -- info-TREE:    xldv11Alarming
    -- info-ACC:     ro
    -- info-SYNTAX:  Integer32
    -- info-VALUE:   -
    -- info-COMMENT: ID of managed entity that reported the alarm
    -- info-ROU:     GET db
    -- info-IMPL:    V1.0->
    -- info-VERCTRL: -
    SYNTAX        Integer32
    ACCESS        read-only
    STATUS        mandatory
    DESCRIPTION
	 " The managed entity that reported the alarm. In case of a HWM /
	   TLM / CallP / GFH object it is the HW unit index / interface
	   index / vpcTP or vccTp index /  External Alarm index. "
    --DEFAULT next-function-async     fsnAlmListEntryNext
    --DEFAULT get-function-async      fsnAlmListEntryGet
    ::= { xldv11AlarmListEntry 4 }

 xldv11AlmRepSource OBJECT-TYPE
    -- info-LEAF:    xldv11AlmRepSource
    -- info-TREE:    xldv11Alarming
    -- info-ACC:     ro
    -- info-SYNTAX:  Xldv11RepSource
    -- info-VALUE:   hwm(1), tlm(2), callpNni(3)
    -- info-VALUE:   callpUni(4), extAlarm(5), vccTp(6), vpcTp(7)
    -- info-COMMENT: ID of managed entity that reported the alarm
    -- info-ROU:     GET db
    -- info-IMPL:    V1.0->
    -- info-VERCTRL: -
    SYNTAX        Xldv11RepSource
    ACCESS        read-only
    STATUS        mandatory
    DESCRIPTION
	 " Source reporting the alarm. "
    --DEFAULT next-function-async     fsnAlmListEntryNext
    --DEFAULT get-function-async      fsnAlmListEntryGet
    ::= { xldv11AlarmListEntry 5 }

 xldv11AlmFailedComponent OBJECT-TYPE
    -- info-LEAF:    xldv11AlmFailedComponent
    -- info-TREE:    xldv11Alarming
    -- info-ACC:     ro
    -- info-SYNTAX:  Integer32
    -- info-VALUE:   -
    -- info-COMMENT: managed entity that reported the alarm
    -- info-ROU:     GET db
    -- info-IMPL:    V1.0->
    -- info-VERCTRL: -
    SYNTAX        Integer32
    ACCESS        read-only
    STATUS        mandatory
    DESCRIPTION
	 " The managed entity which is defective. "
    --DEFAULT next-function-async     fsnAlmListEntryNext
    --DEFAULT get-function-async      fsnAlmListEntryGet
    ::= { xldv11AlarmListEntry 6 }

 xldv11AlmFailedComponentRepSource OBJECT-TYPE
    -- info-LEAF:    xldv11AlmFailedComponentRepSource
    -- info-TREE:    xldv11Alarming
    -- info-ACC:     ro
    -- info-SYNTAX:  Xldv11RepSource
    -- info-VALUE:   hwm(1), tlm(2), callpNni(3)
    -- info-VALUE:   callpUni(4), extAlarm(5), vccTp(6), vpcTp(7)
    -- info-COMMENT: managed entity that isolated the failed component
    -- info-ROU:     GET db
    -- info-IMPL:    V1.0->
    -- info-VERCTRL: -
    SYNTAX        Xldv11RepSource
    ACCESS        read-only
    STATUS        mandatory
    DESCRIPTION
	 " Source (HWM, TLM, CallP, GFH) isolating the failed component. "
    --DEFAULT next-function-async     fsnAlmListEntryNext
    --DEFAULT get-function-async      fsnAlmListEntryGet
    ::= { xldv11AlarmListEntry 7 }

 xldv11AlmSeverityOfFailure OBJECT-TYPE
    -- info-LEAF:    xldv11AlmSeverityOfFailure
    -- info-TREE:    xldv11Alarming
    -- info-ACC:     ro
    -- info-SYNTAX:  Xldv11AlarmSeverity
    -- info-VALUE:   critical(1), major(2)
    -- info-VALUE:   minor(3), warning(4), noAlarming(5)
    -- info-COMMENT: severity of alarm
    -- info-ROU:     GET db
    -- info-IMPL:    V1.0->
    -- info-VERCTRL: -
    SYNTAX        Xldv11AlarmSeverity 
    ACCESS        read-only
    STATUS        mandatory
    DESCRIPTION
	 " Thew severity of an alarm.
	   Range of value:
	      critical,
	      major,
	      minor,
	      warning,
	      noAlarming . "
    --DEFAULT next-function-async     fsnAlmListEntryNext
    --DEFAULT get-function-async      fsnAlmListEntryGet
    ::= { xldv11AlarmListEntry 8 }

 xldv11AlmPropRepairAction OBJECT-TYPE
    -- info-LEAF:    xldv11AlmPropRepairAction
    -- info-TREE:    xldv11Alarming
    -- info-ACC:     ro
    -- info-SYNTAX:  Integer32
    -- info-VALUE:   -
    -- info-COMMENT: suggestion of solutions to fix the problem
    -- info-ROU:     GET db
    -- info-IMPL:    V1.0->
    -- info-VERCTRL: -
    SYNTAX        Integer32
    ACCESS        read-only
    STATUS        mandatory
    DESCRIPTION
	 " Suggestion of solutions to fix the problem. "
    --DEFAULT next-function-async     fsnAlmListEntryNext
    --DEFAULT get-function-async      fsnAlmListEntryGet
    ::= { xldv11AlarmListEntry 9 }

 xldv11AlmTimeAndDate OBJECT-TYPE
    -- info-LEAF:    xldv11AlmTimeAndDate
    -- info-TREE:    xldv11Alarming
    -- info-ACC:     ro
    -- info-SYNTAX:  Integer32
    -- info-VALUE:   -
    -- info-COMMENT: Entry time of the report into the log
    -- info-ROU:     GET db
    -- info-IMPL:    V1.0->
    -- info-VERCTRL: -
    SYNTAX        Integer32
    ACCESS        read-only
    STATUS        mandatory
    DESCRIPTION
	 " Entry time of the report into the log. "
    --DEFAULT next-function-async     fsnAlmListEntryNext
    --DEFAULT get-function-async      fsnAlmListEntryGet
    ::= { xldv11AlarmListEntry 10 }


 -- --------------------------------------------------------------
 --                     Alarm Control group 
 -- --------------------------------------------------------------

 xldv11AlmControl OBJECT IDENTIFIER ::= { xldv11Alarming 7 }
    -- info-NODE:    xldv11AlmControl
    -- info-TREE:    xldv11Alarming
    -- info-ACC:     nac
    -- info-COMMENT: alarm control object
    -- info-IMPL:    V1.2B->

 -- This managed entity manages the update of the alarm list
 -- (xldv11AlarmListTable) and the alarming filtering table.
 -- The craft person has to update the alarm list when he/she has changed
 -- alarm severities.
 -- The craft person has to update the alarm filtering table when he/she has
 -- changed temporal filter in the alarm filtering table.
 --
 -- The TMN-OS can request the ONU to send Atm layer multi alarm traps.
 --

 xldv11AlmControlReq OBJECT-TYPE
    -- info-LEAF:    xldv11AlmControlReq
    -- info-TREE:    xldv11Alarming
    -- info-ACC:     rw
    -- info-SYNTAX:  Xldv11ControlReq
    -- info-VALUE:   updateAlmList(210)(V1.3A->)(command)
    -- info-VALUE:   updateFiltList(211)(V1.x->)(command)
    -- info-VALUE:   commandFailed(212)(V1.2B),
    -- info-VALUE:   startSendingAlarms(213)(V1.2B)(command)
    -- info-VALUE:   requestBusy(V1.3N->),setDataFailed(V1.3N->),
    -- info-VALUE:   aswTimeout(V1.3N->),
    -- info-COMMENT: alarm control request
    -- info-ROU:     GET db SET gf
    -- info-IMPL:    V1.3A->
    -- info-VERCTRL: V1.1U..V1.2B:GET db SET blocked
    SYNTAX        Xldv11ControlReq
    ACCESS        read-write
    STATUS        mandatory
    DESCRIPTION
	 " Marks the received command to update the alarm list
	   (updateAlmList) or the alarming filtering table
	   (updateFiltList) or the request of Atm layer multi 
	   alarm traps (startSendingAlarms).
	   Reject reasons are faulty parameters from the SNMP agent
	   (response: paramFaulty)
	   or command failed (response: commandFailed)
	   or no current alarms (noCurrentAlarms).
	   Notifications :
		none ."
    --DEFAULT test-function-async     fsnAlmTest
    --DEFAULT next-function-async     fsnAlmNext
    --DEFAULT set-function-async      fsnAlmSet
    --DEFAULT get-function-async      fsnAlmGet
    ::= { xldv11AlmControl 1 }

 xldv11AlmControlStatus OBJECT-TYPE
    -- info-LEAF:    xldv11AlmControlStatus
    -- info-TREE:    xldv11Alarming
    -- info-ACC:     ro
    -- info-SYNTAX:  Xldv11ControlStatus
    -- info-VALUE:   requestIdle(1), requestBusy(2), requestPassed(3)
    -- info-VALUE:   requestFailed(4)
    -- info-COMMENT: Control status of command.
    -- info-ROU:     GET db
    -- info-IMPL:    V1.3A->
    -- info-VERCTRL: -
    SYNTAX        Xldv11ControlStatus
    ACCESS        read-only
    STATUS        mandatory
    DESCRIPTION
	 " The status of the control request. The value requestIdle
	   will be set after startup/recovery or after a running
	   test was aborted by the SNMP manager.
	   Range of values is:
	      requestIdle,
	      requestBusy,
	      requestPassed,
	      requestFailed . "
    --DEFAULT next-function-async     fsnAlmNext
    --DEFAULT get-function-async      fsnAlmGet
    ::= { xldv11AlmControl 2 }

 xldv11AlmControlReqResult OBJECT-TYPE
    -- info-LEAF:    xldv11AlmControlReqResult
    -- info-TREE:    xldv11Alarming
    -- info-ACC:     ro
    -- info-SYNTAX:  Xldv11ControlReq
    -- info-VALUE:   see xldv11AlmControlReq
    -- info-COMMENT: specifies the result of user command
    -- info-ROU:     GET db
    -- info-IMPL:    V1.3N->
    -- info-VERCTRL: -
    SYNTAX        Xldv11ControlReq
    ACCESS        read-only
    STATUS        mandatory
    DESCRIPTION
	  " This read-only attribute informs about the result of 
	     the last user command."
    --DEFAULT next-function-async     fsnAlmNext
    --DEFAULT get-function-async      fsnAlmGet
    ::= { xldv11AlmControl 3 }

  xldv11AlmControlTimeStamp OBJECT-TYPE
     -- info-LEAF:    xldv11AlmControlTimeStamp
     -- info-TREE:    xldv11Tlm
     -- info-ACC:     ro
     -- info-SYNTAX:  TimeTicks
     -- info-VALUE:   0..2Giga
     -- info-COMMENT: specifies the time stamp in seconds
     -- info-COMMENT: of the last command
     -- info-COMMENT: (end of command)
     -- info-ROU:     GET db
     -- info-IMPL:    V1.3N->
     -- info-VERCTRL: -
     SYNTAX        TimeTicks
     ACCESS        read-only
     STATUS        mandatory
     DESCRIPTION
        " This read-only attribute informs about the time stamp
        of the last command (end of command)."
    --DEFAULT next-function-async     fsnAlmNext
    --DEFAULT get-function-async      fsnAlmGet
    ::= { xldv11AlmControl 4 }


 -- --------------------------------------------------------------
 --                         Reset group 
 -- --------------------------------------------------------------

 xldv11Reset OBJECT IDENTIFIER ::= { xldv11Alarming 8 }
    -- info-NODE:    xldv11Reset
    -- info-TREE:    xldv11Alarming
    -- info-ACC:     nac
    -- info-COMMENT: reset control object
    -- info-IMPL:    V1.0->


-- Performs the reset of one plugInUnit or of all applicable plug in units.
-- Not all kinds of reset can be performed on every unit.
-- For Version 1.1U the System wide reset is not supported, this feature will
-- be made available with Version 1.1.

 xldv11RstControlReq OBJECT-TYPE
    -- info-LEAF:    xldv11RstControlReq
    -- info-TREE:    xldv11Alarming
    -- info-ACC:     rw
    -- info-SYNTAX:  Xldv11ControlReq
    -- info-VALUE:   warm(2)(command),cold(3)(command),reload(4)(command)
    -- info-VALUE:   noRequest(1), commExecStarted(5)
    -- info-VALUE:   rjUpgRunning(6),rjRstRunning(7),rjPiuNotAvail(8)
    -- info-VALUE:   rjResetNotSupported(9),loopDiagRequest(10),paramFaulty(11)
    -- info-VALUE:   requestBusy(V1.3N->),setDataFailed(V1.3N->),
    -- info-VALUE:   aswTimeout(V1.3N->),
    -- info-COMMENT: reset control request
    -- info-ROU:     GET db SET gf
    -- info-IMPL:    V1.0->
    -- info-VERCTRL: -
    SYNTAX        Xldv11ControlReq
    ACCESS        read-write
    STATUS        mandatory
    DESCRIPTION
	 " Request to perform a reset.
	   Range of value:
	    noRequest,
	    reload(command),
	    cold(command),
	    warm(command),
	    commExecStarted,
	    rjUpgRunning,
	    rjRstRunning,
	    rjPiuNotAvail,
	    rjResetNotSupported .
	   Notifications : 
	   xldv11TrReplaceableUnitReset at beginning of reset PIU,
	   xldv11TrReplaceableUnitResetEnd at end of reset PIU,
	   xldv11TrRstResult for reset of CMU in case of a failure occured
	   after the reset has been accepted. "
    --DEFAULT test-function-async     fsnRstTest
    --DEFAULT next-function-async     fsnRstNext
    --DEFAULT set-function-async      fsnRstSet
    --DEFAULT get-function-async      fsnRstGet
    ::= { xldv11Reset 1 }

 xldv11RstControlStatus OBJECT-TYPE
    -- info-LEAF:    xldv11RstControlStatus
    -- info-TREE:    xldv11Alarming
    -- info-ACC:     ro
    -- info-SYNTAX:  Xldv11ControlStatus
    -- info-VALUE:   requestIdle(1), requestBusy(2), requestPassed(3)
    -- info-VALUE:   requestFailed(4)
    -- info-COMMENT: Control status of command.
    -- info-ROU:     GET db
    -- info-IMPL:    V1.0->
    -- info-VERCTRL: -
    SYNTAX        Xldv11ControlStatus
    ACCESS        read-only
    STATUS        mandatory
    DESCRIPTION
	 " The actual status of the reset procedure.
	   Range of values is:
	      requestIdle,
	      requestBusy,
	      requestPassed,
	      requestFailed . "
    --DEFAULT next-function-async     fsnRstNext
    --DEFAULT get-function-async      fsnRstGet
    ::= { xldv11Reset 2 }

 xldv11RstLevel OBJECT-TYPE
    -- info-LEAF:    xldv11RstLevel
    -- info-TREE:    xldv11Alarming
    -- info-ACC:     rw
    -- info-SYNTAX:  Xldv11ResetLevel
    -- info-VALUE:   plugInUnit(V1.0->),system (V1.3x)
    -- info-COMMENT: reset level
    -- info-ROU:     GET db SET db
    -- info-IMPL:    V1.0->
    -- info-VERCTRL: -
    SYNTAX        Xldv11ResetLevel
    ACCESS        read-write
    STATUS        mandatory
    DESCRIPTION
	 " With this attribute the TMN-OS can deside to make a reset for one
	   unit or the whole system.
	   Range of values is:
	      plugInUnit,
	      system . "
    --DEFAULT test-function-async     fsnRstTest
    --DEFAULT next-function-async     fsnRstNext
    --DEFAULT set-function-async      fsnRstSet
    --DEFAULT get-function-async      fsnRstGet
    ::= { xldv11Reset 3 }

 xldv11RstHwUnitIndex OBJECT-TYPE
    -- info-LEAF:    xldv11RstHwUnitIndex
    -- info-TREE:    xldv11Alarming
    -- info-ACC:     rw
    -- info-SYNTAX:  Unsigned16
    -- info-VALUE:   -
    -- info-COMMENT: HwUnitIndex of PIU to be reset
    -- info-ROU:     GET db SET db
    -- info-IMPL:    V1.0->
    -- info-VERCTRL: -
    SYNTAX        Unsigned16
    ACCESS        read-write
    STATUS        mandatory
    DESCRIPTION
	 " This attribute determines which unit object should get the
	   reset. "
    --DEFAULT test-function-async     fsnRstTest
    --DEFAULT next-function-async     fsnRstNext
    --DEFAULT set-function-async      fsnRstSet
    --DEFAULT get-function-async      fsnRstGet
    ::= { xldv11Reset 4 }

 xldv11RstControlTimer OBJECT-TYPE
    -- info-LEAF:    xldv11RstControlTimer
    -- info-TREE:    xldv11Alarming
    -- info-ACC:     ro
    -- info-SYNTAX:  Integer32
    -- info-VALUE:   -2147483648..2147483647
    -- info-COMMENT: Maximum duration of reset
    -- info-ROU:     GET db
    -- info-IMPL:    V1.0->
    -- info-VERCTRL: -
    SYNTAX        Integer32
    ACCESS        read-only
    STATUS        mandatory
    DESCRIPTION
	 " Timer value for the trap response. Only valid if
	   xldv11RstControlStatus indicates requestBusy. "
    --DEFAULT next-function-async     fsnRstNext
    --DEFAULT get-function-async      fsnRstGet
    ::= { xldv11Reset 5 }

 xldv11RstControlReqResult OBJECT-TYPE
    -- info-LEAF:    xldv11RstControlReqResult
    -- info-TREE:    xldv11Alarming
    -- info-ACC:     ro
    -- info-SYNTAX:  Xldv11ControlReq
    -- info-VALUE:   noRequest, reload, cold,
    -- info-VALUE:   warm, commExecStarted,
    -- info-VALUE:   rjUpgRunning,rjRstRunning,rjPiuNotAvail
    -- info-VALUE:   rjResetNotSupported,paramFaulty
    -- info-VALUE:   requestBusy,setDataFailed
    -- info-VALUE:   aswTimeout
    -- info-VALUE:   rstRequestFailed
    -- info-COMMENT: specifies the result of user command
    -- info-ROU:     GET db
    -- info-IMPL:    V1.3N->
    -- info-VERCTRL: -
    SYNTAX        Xldv11ControlReq
    ACCESS        read-only
    STATUS        mandatory
    DESCRIPTION
	  " This read-only attribute informs about the result of 
	     the last user command."
    --DEFAULT next-function-async     fsnRstNext
    --DEFAULT get-function-async      fsnRstGet
    ::= { xldv11Reset 6 }

  xldv11RstControlTimeStamp OBJECT-TYPE
     -- info-LEAF:    xldv11RstControlTimeStamp
     -- info-TREE:    xldv11Alarming
     -- info-ACC:     ro
     -- info-SYNTAX:  TimeTicks
     -- info-VALUE:   0..2Giga
     -- info-COMMENT: specifies the time stamp in seconds
     -- info-COMMENT: of the last command
     -- info-COMMENT: (end of command)
     -- info-ROU:     GET db
     -- info-IMPL:    V1.3N->
     -- info-VERCTRL: -
     SYNTAX        TimeTicks
     ACCESS        read-only
     STATUS        mandatory
     DESCRIPTION
        " This read-only attribute informs about the time stamp
        of the last command (end of command)."
    --DEFAULT next-function-async     fsnRstNext
    --DEFAULT get-function-async      fsnRstGet
    ::= { xldv11Reset 7 }


 -- ==============================================================
 --       S o f t w a r e   M a i n t e n a n c e   G r o u p
 -- ==============================================================

 -- --------------------------------------------------------------
 --                    Log Handler subgroup
 -- --------------------------------------------------------------

 xldv11SwmLogHandler OBJECT IDENTIFIER ::= { xldv11Swm 1 }
    -- info-NODE:    xldv11SwmLogHandler
    -- info-TREE:    xldv11Swm
    -- info-ACC:     nac
    -- info-COMMENT: log handler control object
    -- info-IMPL:    V1.0->

 xldv11DbuControlReq OBJECT-TYPE
    -- info-LEAF:    xldv11DbuControlReq
    -- info-TREE:    xldv11Swm
    -- info-ACC:     rw
    -- info-SYNTAX:  Xldv11ControlReq
    -- info-VALUE:   noRequest, commExecStarted
    -- info-VALUE:   paramFaulty, dbuReadRequest(command)
    -- info-VALUE:   requestBusy(V1.3N->),setDataFailed(V1.3N->),
    -- info-VALUE:   aswTimeout(V1.3N->),
    -- info-COMMENT: log handler control request
    -- info-ROU:     GET db SET ut
    -- info-IMPL:    V1.0->
    -- info-VERCTRL: -
    SYNTAX        Xldv11ControlReq
    ACCESS        read-write
    STATUS        mandatory
    DESCRIPTION
	 " This attribute serves to launch a read request on either the
	   Software Errorlog, the Software Tracelog or the Hardware
	   Maintenancelog on the CMU.
	   Range of value:
	      noRequest,
	      commExecStarted,
	      paramFaulty,
	      dbuReadRequest (command) .
	   Notifications : 
	      xldv11TrSweLogRead,
	      xldv11TrHwmLogRead,
	      xldv11TrTraceLogRead ."
    --DEFAULT test-function-async     fsnDbuTest
    --DEFAULT next-function-async     fsnDbuNext
    --DEFAULT set-function-async      fsnDbuSet
    --DEFAULT get-function-async      fsnDbuGet
    ::= { xldv11SwmLogHandler 1 }

 xldv11DbuControlStatus OBJECT-TYPE
    -- info-LEAF:    xldv11DbuControlStatus
    -- info-TREE:    xldv11Swm
    -- info-ACC:     ro
    -- info-SYNTAX:  Xldv11ControlStatus
    -- info-VALUE:   requestIdle(1), requestBusy(2), requestPassed(3)
    -- info-VALUE:   requestFailed(4)
    -- info-COMMENT: Control status of command.
    -- info-ROU:     GET db
    -- info-IMPL:    V1.0->
    -- info-VERCTRL: -
    SYNTAX        Xldv11ControlStatus
    ACCESS        read-only
    STATUS        mandatory
    DESCRIPTION
	 " The status of the current read request.
	   Possible values:
	     requestIdle,
	     requestBusy,
	     requestPassed,
	     requestFailed. "
    --DEFAULT next-function-async     fsnDbuNext
    --DEFAULT get-function-async      fsnDbuGet
    ::= { xldv11SwmLogHandler 2 }

 xldv11DbuResultFilePath OBJECT-TYPE
    -- info-LEAF:    xldv11DbuResultFilePath
    -- info-TREE:    xldv11Swm
    -- info-ACC:     rw
    -- info-SYNTAX:  OCTET STRING ( SIZE (0..150) )
    -- info-VALUE:   -
    -- info-COMMENT: path and file name of resulting file
    -- info-ROU:     GET db SET db
    -- info-IMPL:    V1.0->
    -- info-VERCTRL: -
    SYNTAX        OCTET STRING ( SIZE (0..150) )
    ACCESS        read-write
    STATUS        mandatory
    DESCRIPTION
	 " This attribute contains the path (including the file name)
	   where the file resulting from the read request should be
	   stored. If this attribute does not contain a valid path
	   the results will be printed on screen. "
    --DEFAULT test-function-async     fsnDbuTest
    --DEFAULT next-function-async     fsnDbuNext
    --DEFAULT set-function-async      fsnDbuSet
    --DEFAULT get-function-async      fsnDbuGet
    ::= { xldv11SwmLogHandler 3 }

 xldv11DbuLogType OBJECT-TYPE
    -- info-LEAF:    xldv11DbuLogType
    -- info-TREE:    xldv11Swm
    -- info-ACC:     rw
    -- info-SYNTAX:  Xldv11LogType
    -- info-VALUE:   sweLog, swTraceLog, hwmLog
    -- info-COMMENT: the log to be read
    -- info-ROU:     GET db SET db
    -- info-IMPL:    V1.0->
    -- info-VERCTRL: -
    SYNTAX        Xldv11LogType
    ACCESS        read-write
    STATUS        mandatory
    DESCRIPTION
	 " The value of this object selects the log to be read by the
	   mandatory read request.
	   Range of value:
	      sweLog,
	      swTraceLog,
	      hwmLog . "
    --DEFAULT test-function-async     fsnDbuTest
    --DEFAULT next-function-async     fsnDbuNext
    --DEFAULT set-function-async      fsnDbuSet
    --DEFAULT get-function-async      fsnDbuGet
    ::= { xldv11SwmLogHandler 4 }

 xldv11DbuNumEntries OBJECT-TYPE
    -- info-LEAF:    xldv11DbuNumEntries
    -- info-TREE:    xldv11Swm
    -- info-ACC:     rw
    -- info-SYNTAX:  INTEGER
    -- info-VALUE:   0..65536
    -- info-COMMENT: number of log entries to be read
    -- info-ROU:     GET db SET db
    -- info-IMPL:    V1.0->
    -- info-VERCTRL: -
    SYNTAX        INTEGER (0..65536)
    ACCESS        read-write
    STATUS        mandatory
    DESCRIPTION
	 " The number of log entries to be read by the mandatory read
	   request. If it is 0 or if the passed number exceeds the
	   number of entries mandatoryly in the log, the entire log
	   will be read. "
    --DEFAULT test-function-async     fsnDbuTest
    --DEFAULT next-function-async     fsnDbuNext
    --DEFAULT set-function-async      fsnDbuSet
    --DEFAULT get-function-async      fsnDbuGet
    ::= { xldv11SwmLogHandler 5 }

 xldv11DbuControlTimer OBJECT-TYPE
    -- info-LEAF:    xldv11DbuControlTimer
    -- info-TREE:    xldv11Swm
    -- info-ACC:     ro
    -- info-SYNTAX:  Integer32
    -- info-VALUE:   -2147483648..2147483647
    -- info-COMMENT: Maximum duration of log reading
    -- info-ROU:     GET db
    -- info-IMPL:    V1.0->
    -- info-VERCTRL: -
    SYNTAX        Integer32
    ACCESS        read-only
    STATUS        mandatory
    DESCRIPTION
	 " The timer value for trap response.
	   Range of value: maxResetTime "
    --DEFAULT next-function-async     fsnDbuNext
    --DEFAULT get-function-async      fsnDbuGet
    ::= { xldv11SwmLogHandler 6 }

 xldv11DbuControlReqResult OBJECT-TYPE
    -- info-LEAF:    xldv11DbuControlReqResult
    -- info-TREE:    xldv11Swm
    -- info-ACC:     ro
    -- info-SYNTAX:  Xldv11ControlReq
    -- info-VALUE:   noRequest, commExecStarted
    -- info-VALUE:   paramFaulty, dbuReadRequest
    -- info-VALUE:   dbuReadComplete,dbuReadFailed
    -- info-VALUE:   dbuFileCreationFailed,dbuFileTransmissionFailed
    -- info-COMMENT: specifies the result of user command
    -- info-ROU:     GET db
    -- info-IMPL:    V1.3N->
    -- info-VERCTRL: -
    SYNTAX        Xldv11ControlReq
    ACCESS        read-only
    STATUS        mandatory
    DESCRIPTION
	  " This read-only attribute informs about the result of 
	     the last user command."
    --DEFAULT next-function-async     fsnDbuNext
    --DEFAULT get-function-async      fsnDbuGet
    ::= { xldv11SwmLogHandler 7 }

  xldv11DbuControlTimeStamp OBJECT-TYPE
     -- info-LEAF:    xldv11DbuControlTimeStamp
     -- info-TREE:    xldv11Swm
     -- info-ACC:     ro
     -- info-SYNTAX:  TimeTicks
     -- info-VALUE:   0..2Giga
     -- info-COMMENT: specifies the time stamp in seconds
     -- info-COMMENT: of the last command
     -- info-COMMENT: (end of command)
     -- info-ROU:     GET db
     -- info-IMPL:    V1.3N->
     -- info-VERCTRL: -
     SYNTAX        TimeTicks
     ACCESS        read-only
     STATUS        mandatory
     DESCRIPTION
        " This read-only attribute informs about the time stamp
        of the last command (end of command)."
    --DEFAULT next-function-async     fsnDbuNext
    --DEFAULT get-function-async      fsnDbuGet
    ::= { xldv11SwmLogHandler 8 }

 -- --------------------------------------------------------------
 --                   Upgrade control subgroup
 -- --------------------------------------------------------------

 -- This managed entity represents the control group for SW upgrade user commands.
 -- The following user commands are implemented :
 -- sucUpgrStartRequest:    
 -- V1.0-V1.2B: start upgrade for the CMU in the background.
 --       xldv11SucPathname, xldv11SucFilename specify the CMU load,
 --       xldv11SucAllOfType=sucUpgrSingle specifies upgrade of a single PIU;
 -- V1.3A: start upgrade for the CMU in the background.
 --        as for background loadable PIUs
 --    start upgrade of  background loadable PIUs :
 --       xldv11SucAllOfType specifies upgrade of a single PIU or all PIUs of same type,
 --       xldv11SucSwVersion specifies a particular or the default SW version (\0);
 --    start upgrade of foreground loadable PIUs : parameter as for background loadable
 --    PIUs. 
 --       The PIUs will have to in state locked before starting the upgrade. 
 --       The PIUs run with the new load after unlock.
 -- sucActivateLoad:
 --    Activate a background loaded SW applicable as well for the CMU as for PIUs. 
 --    Single activation (xldv11SucAllOfType=sucUpgrSingle, xldv11SucUnit
 --    (same format as xldv11EqhAccPiuTypes), xldv11SucHwUnitIndex of PIU)
 --    and also the activation of all background loaded SW
 --    (xldv11SucAllOfType=sucUpgrAll) for all PIUs that wait for activation is possible. 
 -- sucReadSAPSContentFile : 
 --    The SAPS (Sytem Application Software) content file describes an assignment of
 --    available SW loads to loadable PIUs and for XLDV1.3 for the CMU.
 --    If there is a new SAPs content file at the FTP
 --    server f.ex. because of bug fix release the crafts person has to request the
 --    reading of the SAPS content file so that the information is available in the ONU.
 --    The SAPS content file is automatically read after reload or after activation
 --    of a CMU load.
 -- sucGetSwVersions:
 --    Read the available SW version and two predecessor versions of a PIU before starting
 --    upgrade of PIUs.
 --    The information is available via 
 --       xldv11SucDefaultSwVerson,
 --       xldv11SucPredecessorSwVersion,
 --       xldv11SucPrePredecessorSwVersion. 


 xldv11SwmUpgradeControl OBJECT IDENTIFIER ::= { xldv11Swm 2 }
    -- info-NODE:    xldv11SwmUpgradeControl
    -- info-TREE:    xldv11Swm
    -- info-ACC:     nac
    -- info-COMMENT: Sw upgrade control object
    -- info-IMPL:    V1.0->

 xldv11SucUnit OBJECT-TYPE
    -- info-LEAF:    xldv11SucUnit
    -- info-TREE:    xldv11Swm
    -- info-ACC:     rw
    -- info-SYNTAX:  OCTET STRING ( SIZE (0..20) )
    -- info-VALUE:   same format as xldv11EqhAccPiuTypes
    -- info-COMMENT: type of PIU to be upgraded
    -- info-ROU:     GET db SET db
    -- info-IMPL:    V1.0->
    -- info-VERCTRL: -
    SYNTAX        OCTET STRING ( SIZE (0..20) )
    ACCESS        read-write
    STATUS        mandatory
    DESCRIPTION
	 " The value of this object indicates the plug-in unit type 
	   to be downloaded. "
    --DEFAULT test-function-async     fsnSucTest
    --DEFAULT next-function-async     fsnSucNext
    --DEFAULT set-function-async      fsnSucSet
    --DEFAULT get-function-async      fsnSucGet
    ::= { xldv11SwmUpgradeControl 1 }

 xldv11SucAllOfType OBJECT-TYPE
    -- info-LEAF:    xldv11SucAllOfType
    -- info-TREE:    xldv11Swm
    -- info-ACC:     rw
    -- info-SYNTAX:  Xldv11SucAllOfType
    -- info-VALUE:   sucUpgrAll, sucUpgrSingle
    -- info-COMMENT: indicates all or single upgrade
    -- info-ROU:     GET db SET db
    -- info-IMPL:    V1.0->
    -- info-VERCTRL: -
    SYNTAX        Xldv11SucAllOfType
    ACCESS        read-write
    STATUS        mandatory
    DESCRIPTION
	 " The attribute indicates that the loading for the dedicated
	   unit type may be started n-times ( sucUpgrAll ) regarding
	   to the number of boards of the same type within the ONU
	   or for a single unit (sucUpgrSingle ). "
    --DEFAULT test-function-async     fsnSucTest
    --DEFAULT next-function-async     fsnSucNext
    --DEFAULT set-function-async      fsnSucSet
    --DEFAULT get-function-async      fsnSucGet
    ::= { xldv11SwmUpgradeControl 2 }

 xldv11SucVersionNo OBJECT-TYPE
    -- info-LEAF:    xldv11SucVersionNo
    -- info-TREE:    xldv11Swm
    -- info-ACC:     rw
    -- info-SYNTAX:  OCTET STRING ( SIZE (0..10) )
    -- info-VALUE:   -
    -- info-COMMENT: string of APS version
    -- info-COMMENT: \0 is default. V11U->:If \0, default Sw Version loaded.
    -- info-ROU:     GET db SET db
    -- info-IMPL:    V1.0->
    -- info-VERCTRL: -
    SYNTAX        OCTET STRING ( SIZE (0..10) )
    ACCESS        read-write
    STATUS        mandatory
    DESCRIPTION
	 " String containing the APS version coded into the load for
	   the different board types (destination version).
	   Default value is \0. Then the default SW version should
	   be loaded. "
    --DEFAULT test-function-async     fsnSucTest
    --DEFAULT next-function-async     fsnSucNext
    --DEFAULT set-function-async      fsnSucSet
    --DEFAULT get-function-async      fsnSucGet
    ::= { xldv11SwmUpgradeControl 3 }

 xldv11SucHwUnitIndex OBJECT-TYPE
    -- info-LEAF:    xldv11SucHwUnitIndex
    -- info-TREE:    xldv11Swm
    -- info-ACC:     rw
    -- info-SYNTAX:  Unsigned16
    -- info-VALUE:   -
    -- info-COMMENT: HwUnitIndex of PIU to be loaded
    -- info-COMMENT: (single upgrade)
    -- info-ROU:     GET db SET db
    -- info-IMPL:    V1.0->
    -- info-VERCTRL: -
    SYNTAX        Unsigned16
    ACCESS        read-write
    STATUS        mandatory
    DESCRIPTION
	 " The value of this object indicates the hardware unit index
	   of the plug-in unit to be loaded in case of an single
	   upgrade. "
    --DEFAULT test-function-async     fsnSucTest
    --DEFAULT next-function-async     fsnSucNext
    --DEFAULT set-function-async      fsnSucSet
    --DEFAULT get-function-async      fsnSucGet
    ::= { xldv11SwmUpgradeControl 4 }

 xldv11SucPathName OBJECT-TYPE
    -- info-LEAF:    xldv11SucPathName
    -- info-TREE:    xldv11Swm
    -- info-ACC:     rw
    -- info-SYNTAX:  OCTET STRING ( SIZE (0..121) )
    -- info-VALUE:   -
    -- info-COMMENT: V10: pathname of each PIus loadfile.
    -- info-COMMENT: V11U: pathname of SAPS content file or.
    -- info-COMMENT: pathname of CMU load file.
    -- info-COMMENT: V13: pathname of SAPS content file.
    -- info-ROU:     GET db SET db
    -- info-IMPL:    V1.0->
    -- info-VERCTRL: -
    SYNTAX        OCTET STRING ( SIZE (0..121) )
    ACCESS        read-write
    STATUS        mandatory
    DESCRIPTION
	 " The content of this attribute depends on the XLD Version :
	   V1.0: the pathname of each PIus loadfile.
	   V1.1U: pathname of SAPS content file or
	   V1.1U: pathname of CMU load file
	   V1.3:  pathname of SAPS content file."
    --DEFAULT test-function-async     fsnSucTest
    --DEFAULT next-function-async     fsnSucNext
    --DEFAULT set-function-async      fsnSucSet
    --DEFAULT get-function-async      fsnSucGet
    ::= { xldv11SwmUpgradeControl 5 }

 xldv11SucFileName OBJECT-TYPE
    -- info-LEAF:    xldv11SucFileName
    -- info-TREE:    xldv11Swm
    -- info-ACC:     rw
    -- info-SYNTAX:  OCTET STRING ( SIZE (0..33) )
    -- info-VALUE:   -
    -- info-COMMENT: V10: filename of each PIus loadfile.
    -- info-COMMENT: V11U: filename of SAPS content file or.
    -- info-COMMENT: V11U: filename of CMU load file.
    -- info-COMMENT: V13: filename of SAPS content file.
    -- info-ROU:     GET db SET db
    -- info-IMPL:    V1.0->
    -- info-VERCTRL: -
    SYNTAX        OCTET STRING ( SIZE (0..33) )
    ACCESS        read-write
    STATUS        mandatory
    DESCRIPTION
	 " The content of this attribute depends on the XLD Version :
	   V1.0:  filename of each PIus loadfile.
	   V1.1U: filename of SAPS content file or
	   V1.1U: filename of CMU load file
	   V1.3:  filename of SAPS content file."
    --DEFAULT test-function-async     fsnSucTest
    --DEFAULT next-function-async     fsnSucNext
    --DEFAULT set-function-async      fsnSucSet
    --DEFAULT get-function-async      fsnSucGet
    ::= { xldv11SwmUpgradeControl 6 }

 xldv11SucControlReq OBJECT-TYPE
    -- info-LEAF:    xldv11SucControlReq
    -- info-TREE:    xldv11Swm
    -- info-ACC:     rw
    -- info-SYNTAX:  Xldv11ControlReq
    -- info-VALUE:   sucUpgrStartRequest(command),
    -- info-VALUE:   noRequest, commExecStarted
    -- info-VALUE:   sucActivateLoad(command), sucReadSAPSContentFile(command),
    -- info-VALUE:   sucGetSwVersions(V1.1U->)(command)
    -- info-VALUE:   sucUpgrMissParameter(V1.1U->),
    -- info-VALUE:   sucGetSwVersionsFailed(V1.1U->)
    -- info-VALUE:   requestBusy(V1.3N->),setDataFailed(V1.3N->),
    -- info-VALUE:   aswTimeout(V1.3N->),
    -- info-VALUE:   sucUpgrEndRequest(V1.3H->) (command) 
    -- info-VALUE:   sucUpgrTaskCreationFault(V1.3N->),
    -- info-VALUE:   sucUpgrDbAccessFault(V1.3N->)
    -- info-VALUE:   rjResetNotSupported(V1.3N->)
    -- info-COMMENT: Sw upgrade control request
    -- info-ROU:     GET db SET up
    -- info-IMPL:    V1.0->
    -- info-VERCTRL: -
    SYNTAX        Xldv11ControlReq
    ACCESS        read-write
    STATUS        mandatory
    DESCRIPTION
	 " The command request from TMN.
	   Possible values are:
	     noRequest,
	     commExecStarted,
	     sucUpgrStartRequest(command),
	     sucActivateLoad(command),
	     sucReadSAPSContentFile(command),
	     sucGetSwVersions(command),
	     sucUpgrMissParameter,
	     sucGetSwVersionsFailed,
	     sucUpgrEndRequest(command),
	     rjResetNotSupported.
	   Notifications :
	     xldv11TrCmuReadyForReset,
	     xldv11TrUnitReadyForReset,
	     xldv11TrActivateLoadResult,
	     xldv11TrPuUpgradeResult,
	     xldv11TrFTPError,       
	     xldv11TrUpgradeCanceled,
	     xldv11TrSwVersionsSet,
	     xldv11TrReadSAPSContentFileReady,
	     xldv11TrUpgradeEndRequestResult,
	     xldv11TrUnitUpgradeNotRequested."
    --DEFAULT test-function-async     fsnSucTest
    --DEFAULT next-function-async     fsnSucNext
    --DEFAULT set-function-async      fsnSucSet
    --DEFAULT get-function-async      fsnSucGet
    ::= { xldv11SwmUpgradeControl 7 }

 xldv11SucControlStatus OBJECT-TYPE
    -- info-LEAF:    xldv11SucControlStatus
    -- info-TREE:    xldv11Swm
    -- info-ACC:     ro
    -- info-SYNTAX:  Xldv11ControlStatus
    -- info-VALUE:   requestIdle(1), requestBusy(2), requestPassed(3)
    -- info-VALUE:   requestFailed(4)
    -- info-COMMENT: Control status of command.
    -- info-ROU:     GET db
    -- info-IMPL:    V1.0->
    -- info-VERCTRL: -
    SYNTAX        Xldv11ControlStatus
    ACCESS        read-only
    STATUS        mandatory
    DESCRIPTION
	 " The status of the current request.
	   Possible values are:
	     requestIdle,
	     requestBusy,
	     requestPassed,
	     requestFailed . "
    --DEFAULT next-function-async     fsnSucNext
    --DEFAULT get-function-async      fsnSucGet
    ::= { xldv11SwmUpgradeControl 8 }

 xldv11SucControlTimer OBJECT-TYPE
    -- info-LEAF:    xldv11SucControlTimer
    -- info-TREE:    xldv11Swm
    -- info-ACC:     ro
    -- info-SYNTAX:  Integer32
    -- info-VALUE:   -2147483648..2147483647
    -- info-COMMENT: Maximum duration of upgrade command
    -- info-ROU:     GET db
    -- info-IMPL:    V1.0->
    -- info-VERCTRL: -
    SYNTAX        Integer32
    ACCESS        read-only
    STATUS        mandatory
    DESCRIPTION
	 " Wait time in seconds after complete upgrade for a
	   unit type. "
    --DEFAULT next-function-async     fsnSucNext
    --DEFAULT get-function-async      fsnSucGet
    ::= { xldv11SwmUpgradeControl 9 }

 xldv11SucNumberOfTraps OBJECT-TYPE
    -- info-LEAF:    xldv11SucNumberOfTraps
    -- info-TREE:    xldv11Swm
    -- info-ACC:     ro
    -- info-SYNTAX:  Integer32
    -- info-VALUE:   -2147483648..2147483647
    -- info-COMMENT: number of traps to be expected
    -- info-ROU:     GET db
    -- info-IMPL:    V1.0->
    -- info-VERCTRL: -
    SYNTAX        Integer32
    ACCESS        read-only
    STATUS        mandatory
    DESCRIPTION
	 " Number of traps which have to be expected. "
    --DEFAULT next-function-async     fsnSucNext
    --DEFAULT get-function-async      fsnSucGet
    ::= { xldv11SwmUpgradeControl 10 }

 xldv11SucDefaultSwVersion OBJECT-TYPE
    -- info-LEAF:    xldv11SucDefaultSwVersion
    -- info-TREE:    xldv11Swm
    -- info-ACC:     ro
    -- info-SYNTAX:  DisplayString (SIZE (0..10))
    -- info-VALUE:   -
    -- info-COMMENT: default Sw version
    -- info-COMMENT: result of GetSwVersion command
    -- info-COMMENT: Default value: \0
    -- info-ROU:     GET db
    -- info-IMPL:    V1.1U->
    -- info-VERCTRL: -
    SYNTAX        DisplayString (SIZE (0..10))
    ACCESS        read-only
    STATUS        mandatory
    DESCRIPTION
	 " Result of the command GetSwVersions.
	   Default value: \0 "
    --DEFAULT next-function-async     fsnSucNext
    --DEFAULT get-function-async      fsnSucGet
    ::= { xldv11SwmUpgradeControl 11 }

 xldv11SucPredecessorSwVersion OBJECT-TYPE
    -- info-LEAF:    xldv11SucPredecessorSwVersion
    -- info-TREE:    xldv11Swm
    -- info-ACC:     ro
    -- info-SYNTAX:  DisplayString (SIZE (0..10))
    -- info-VALUE:   0..10
    -- info-COMMENT: predecessor Sw version
    -- info-COMMENT: result of GetSwVersion command
    -- info-COMMENT: Default value: \0
    -- info-ROU:     GET db
    -- info-IMPL:    V1.1U->
    -- info-VERCTRL: -
    SYNTAX        DisplayString (SIZE (0..10))
    ACCESS        read-only
    STATUS        mandatory
    DESCRIPTION
	 " Result of the command GetSwVersions.
	   Default value: \0 "
    --DEFAULT next-function-async     fsnSucNext
    --DEFAULT get-function-async      fsnSucGet
    ::= { xldv11SwmUpgradeControl 12 }

 xldv11SucPrePredecessorSwVersion OBJECT-TYPE
    -- info-LEAF:    xldv11SucPrePredecessorSwVersion
    -- info-TREE:    xldv11Swm
    -- info-ACC:     ro
    -- info-SYNTAX:  DisplayString (SIZE (0..10))
    -- info-VALUE:   0..10
    -- info-COMMENT: pre predecessor Sw version
    -- info-COMMENT: result of GetSwVersion command
    -- info-COMMENT: Default value: \0
    -- info-ROU:     GET db
    -- info-IMPL:    V1.1U->
    -- info-VERCTRL: -
    SYNTAX        DisplayString (SIZE (0..10))
    ACCESS        read-only
    STATUS        mandatory
    DESCRIPTION
	 " Result of the command GetSwVersions.
	   Default value: \0 "
    --DEFAULT next-function-async     fsnSucNext
    --DEFAULT get-function-async      fsnSucGet
    ::= { xldv11SwmUpgradeControl 13 }

 xldv11SucControlReqResult OBJECT-TYPE
    -- info-LEAF:    xldv11SucControlReqResult
    -- info-TREE:    xldv11Swm
    -- info-ACC:     ro
    -- info-SYNTAX:  Xldv11ControlReq
    -- info-VALUE:   noRequest, commExecStarted sucUpgrStartRequest,
    -- info-VALUE:   sucActivateLoad, sucReadSAPSContentFile,
    -- info-VALUE:   sucGetSwVersions(V1.1U->), sucUpgrMissParameter(V1.1U->),
    -- info-VALUE:   sucGetSwVersionsFailed(V1.1U->)
    -- info-VALUE:   sucOk ,sucNotOk
    -- info-VALUE:   sucDbAccessFailed ,sucPiuUnlocked
    -- info-VALUE:   sucTransmissionError ,sucWrongSwVersion
    -- info-VALUE:   sucUnitTypeMismatch
    -- info-VALUE:   sucFtpTransError ,sucFtpCrcError
    -- info-VALUE:   sucSwHwMismatch ,sucUpgrWrongAvState
    -- info-VALUE:   sucFepromCopyFault ,sucUpdateDescFileFailed
    -- info-VALUE:   sucFtpServerNoteAvailable ,sucFtpSendError
    -- info-VALUE:   sucDbBackupFault ,sucUpgradeComplete
    -- info-VALUE:   sucUpgradeNotComplete
    -- info-VALUE:   sucUpgrTaskCreationFault
    -- info-VALUE:   sucUpgrDbAccessFault,
    -- info-VALUE:   rjResetNotSupported
    -- info-COMMENT: specifies the result of user command
    -- info-ROU:     GET db
    -- info-IMPL:    V1.3N->
    -- info-VERCTRL: -
    SYNTAX        Xldv11ControlReq
    ACCESS        read-only
    STATUS        mandatory
    DESCRIPTION
	  " This read-only attribute informs about the result of 
	     the last user command."
    --DEFAULT next-function-async     fsnSucNext
    --DEFAULT get-function-async      fsnSucGet
    ::= { xldv11SwmUpgradeControl 14 }

  xldv11SucControlTimeStamp OBJECT-TYPE
     -- info-LEAF:    xldv11SucControlTimeStamp
     -- info-TREE:    xldv11Swm
     -- info-ACC:     ro
     -- info-SYNTAX:  TimeTicks
     -- info-VALUE:   0..2Giga
     -- info-COMMENT: specifies the time stamp in seconds
     -- info-COMMENT: of the last command
     -- info-COMMENT: (end of command)
     -- info-ROU:     GET db
     -- info-IMPL:    V1.3N->
     -- info-VERCTRL: -
     SYNTAX        TimeTicks
     ACCESS        read-only
     STATUS        mandatory
     DESCRIPTION
        " This read-only attribute informs about the time stamp
        of the last command (end of command)."
    --DEFAULT next-function-async     fsnSucNext
    --DEFAULT get-function-async      fsnSucGet
    ::= { xldv11SwmUpgradeControl 15 }

 -- --------------------------------------------------------------
 --               Secure Telnet control subgroup
 -- --------------------------------------------------------------

 -- This managed entity represents the control group for Secure Telnet.
 -- The secure telnet session will be enabled / disabled via a SET
 -- request to the attribute xldv11StcTelnetAccess.


 xldv11StcSecureTelnetControl OBJECT IDENTIFIER ::= { xldv11Swm 3 }
    -- info-NODE:    xldv11StcSecureTelnetControl
    -- info-TREE:    xldv11Swm
    -- info-ACC:     nac
    -- info-COMMENT: Secure telnet control object.
    -- info-IMPL:    V1.3A->

 xldv11StcTelnetAccess OBJECT-TYPE
    -- info-LEAF:    xldv11StcTelnetAccess
    -- info-TREE:    xldv11Swm
    -- info-ACC:     rw
    -- info-SYNTAX:  Xldv11TelnetAccess
    -- info-VALUE:   read(1), trace(2),
    -- info-VALUE:   write(3), noAccess(4)
    -- info-COMMENT: access mode of telnet session
    -- info-COMMENT: enable of a telnet session with
    -- info-COMMENT: access read/write/trace.
    -- info-COMMENT: disable a telnet session using noAccess.
    -- info-ROU:     GET db  SET st
    -- info-IMPL:    V1.3A->
    -- info-VERCTRL: V1.1U->V1.2B: GET db  SET blocked
    SYNTAX        Xldv11TelnetAccess
    ACCESS        read-write
    STATUS        mandatory
    DESCRIPTION
	 " The access mode of a telnet session.
	 The setting of values read, trace, write will enable 
	 a secure telnet session with the corresponding access right.
	 The setting of value noAccess will disable a telnet session."
    --DEFAULT test-function-async     fsnStcTest
    --DEFAULT next-function-async     fsnStcNext
    --DEFAULT set-function-async      fsnStcSet
    --DEFAULT get-function-async      fsnStcGet
    ::= { xldv11StcSecureTelnetControl 1 }

     -- --------------------------------------------------------------
     --                      SW Upgrade Task Table
     -- --------------------------------------------------------------
 
     xldv11SwUpgradeTaskTable OBJECT-TYPE
        -- info-NODE:    xldv11SwUpgradeTaskTable
        -- info-TREE:    xldv11Swm
        -- info-ACC:     nac
        -- info-SYNTAX:  SEQUENCE OF Xldv11SutTaskTableEntry
        -- info-COMMENT: SW upgrade task table
        -- info-IMPL:    V1.3N->
        SYNTAX        SEQUENCE OF Xldv11SutTaskTableEntry
        ACCESS        not-accessible
        STATUS        mandatory
        DESCRIPTION
             " This managed entity is used to store
               the current active or failed tasks of SW upgrade.
               Entries for successfull loading tasks are removed
               from the table.
               This table is used to display the upgrade status for
               single plugin units at the TMN. "
        ::= { xldv11Swm 4 }
 
     xldv11SutTaskTableEntry OBJECT-TYPE
        -- info-NODE:    xldv11SutTaskTableEntry
        -- info-TREE:    xldv11Swm
        -- info-INDEX:   xldv11SutIndex
        -- info-ACC:     nac
        -- info-SYNTAX:  Xldv11SutTaskTableEntry
        -- info-COMMENT: entry of xldv11SwUpgradeTaskTable
        -- info-IMPL:    V1.3N->
        SYNTAX        Xldv11SutTaskTableEntry
        ACCESS        not-accessible
        STATUS        mandatory
        DESCRIPTION
             " Entry of the SW upgrade task table.
               Notifications : none."
        INDEX         { xldv11SutIndex }
        ::= { xldv11SwUpgradeTaskTable 1 }
 
     Xldv11SutTaskTableEntry ::=
        SEQUENCE { xldv11SutIndex               Unsigned16,
                   xldv11SutPiuType             OCTET STRING,
                   xldv11SutHwUnitIndex         Unsigned16,
                   xldv11SutSwVersion           OCTET STRING,
                   xldv11SutRequester           Xldv11Requester,
                   xldv11SutUpgradeState        Xldv11ControlReq,
                   xldv11SutUpgradeResult       Xldv11ControlReq,
                   xldv11SutTimeStamp           TimeTicks
                   }
 
     xldv11SutIndex OBJECT-TYPE
        -- info-LEAF:    xldv11SutIndex
        -- info-TREE:    xldv11Swm
        -- info-ACC:     ro
        -- info-SYNTAX:  Unsigned16
        -- info-VALUE:   -
        -- info-COMMENT: identifies this task
        -- info-ROU:     GET db
        -- info-IMPL:    V1.3N->
        -- info-VERCTRL: -
        SYNTAX        Unsigned16
        ACCESS        read-only
        STATUS        mandatory
        DESCRIPTION
             " Unique value to identify an entry of this table. "
        --DEFAULT next-function-async     fsnSutEntryNext
        --DEFAULT get-function-async      fsnSutEntryGet
        ::= { xldv11SutTaskTableEntry 1 }

     xldv11SutPiuType OBJECT-TYPE
        -- info-LEAF:    xldv11SutPiuType
        -- info-TREE:    xldv11Swm
        -- info-ACC:     ro
        -- info-SYNTAX:  OCTET STRING ( SIZE (0..20) )
        -- info-COMMENT: the type of plug-in unit which is upgraded
        -- info-ROU:     GET db
        -- info-IMPL:    V1.3N->
        -- info-VERCTRL: -
        SYNTAX        OCTET STRING ( SIZE (0..20) )
        ACCESS        read-only
        STATUS        mandatory
        DESCRIPTION
	 " The value of this object indicates the plug-in unit type 
	   to be loaded. "
        --DEFAULT next-function-async     fsnSutEntryNext
        --DEFAULT get-function-async      fsnSutEntryGet
        ::= { xldv11SutTaskTableEntry 2 }

     xldv11SutHwUnitIndex OBJECT-TYPE
        -- info-LEAF:    xldv11SutHwUnitIndex
        -- info-TREE:    xldv11Swm
        -- info-ACC:     ro
        -- info-SYNTAX:  Unsigned16
        -- info-VALUE:   -
        -- info-COMMENT: HwUnitIndex of PIU to be loaded
        -- info-COMMENT: From this value the TMN calculates 
        -- info-COMMENT: the location shelf/slot of the plug-in unit
        -- info-COMMENT: and displays it at the GUI
        -- info-ROU:     GET db
        -- info-IMPL:    V1.3N->
        -- info-VERCTRL: -
        SYNTAX        Unsigned16
        ACCESS        read-only
        STATUS        mandatory
        DESCRIPTION
	 " The value of this object indicates the hardware unit index
	   of the plug-in unit to be loaded in case of an single
	   upgrade.
           From this value the TMN calculates the location shelf/slot
           of the plug-in unit and displays it at the GUI. "
        --DEFAULT next-function-async     fsnSutEntryNext
        --DEFAULT get-function-async      fsnSutEntryGet
        ::= { xldv11SutTaskTableEntry 3 }

    xldv11SutSwVersion OBJECT-TYPE
       -- info-LEAF:    xldv11SutSwVersion
       -- info-TREE:    xldv11Swm
       -- info-ACC:     ro
       -- info-SYNTAX:  OCTET STRING ( SIZE (0..10) )
       -- info-VALUE:   -
       -- info-COMMENT: string of APS version
       -- info-COMMENT: which is loaded      
       -- info-ROU:     GET db
       -- info-IMPL:    V1.3N->
       -- info-VERCTRL: -
       SYNTAX        OCTET STRING ( SIZE (0..10) )
       ACCESS        read-only
       STATUS        mandatory
       DESCRIPTION
	 " String containing the APS version which is loaded
	   into the plug-in unit ."
        --DEFAULT next-function-async     fsnSutEntryNext
        --DEFAULT get-function-async      fsnSutEntryGet
        ::= { xldv11SutTaskTableEntry 4 }

     xldv11SutRequester OBJECT-TYPE
        -- info-LEAF:    xldv11SutRequester
        -- info-TREE:    xldv11Swm
        -- info-ACC:     ro
        -- info-SYNTAX:  Xldv11Requester
        -- info-VALUE:   tmn, hwm
        -- info-COMMENT: identifies the requesting unit of
        -- info-COMMENT: the current upgrade task 
        -- info-ROU:     GET db
        -- info-IMPL:    V1.3N->
        -- info-VERCTRL: -
        SYNTAX        Xldv11Requester
        ACCESS        read-only
        STATUS        mandatory
        DESCRIPTION
             " Identifies the requesting unit of
               the current upgrade task. "
        --DEFAULT next-function-async     fsnSutEntryNext
        --DEFAULT get-function-async      fsnSutEntryGet
        ::= { xldv11SutTaskTableEntry 5 }

     xldv11SutUpgradeState OBJECT-TYPE
        -- info-LEAF:    xldv11SutUpgradeState
        -- info-TREE:    xldv11Swm
        -- info-ACC:     ro
        -- info-SYNTAX:  Xldv11ControlReq
        -- info-VALUE:   sutInitialized, sutToDo
        -- info-VALUE:   sutStarted, sutCrashed, sutFtpDone
        -- info-VALUE:   sutDone, sutReadyForReset
        -- info-VALUE:   sutObsolete
        -- info-COMMENT: identifies the current processing state
        -- info-COMMENT: of the upgrade task
        -- info-ROU:     GET db
        -- info-IMPL:    V1.3N->
        -- info-VERCTRL: -
        SYNTAX        Xldv11ControlReq
        ACCESS        read-only
        STATUS        mandatory
        DESCRIPTION
             " Identifies the current processing state of
               the upgrade task. "
        --DEFAULT next-function-async     fsnSutEntryNext
        --DEFAULT get-function-async      fsnSutEntryGet
        ::= { xldv11SutTaskTableEntry 6 }

    xldv11SutUpgradeResult OBJECT-TYPE
        -- info-LEAF:    xldv11SutUpgradeResult
        -- info-TREE:    xldv11Swm
        -- info-ACC:     ro
        -- info-SYNTAX:  Xldv11ControlReq
        -- info-VALUE:   commExecStarted sucUpgrStartRequest,
        -- info-VALUE:   sucActivateLoad, sucReadSAPSContentFile,
        -- info-VALUE:   sucGetSwVersions, sucUpgrMissParameter,
        -- info-VALUE:   sucGetSwVersionsFailed
        -- info-VALUE:   sucOk ,sucNotOk
        -- info-VALUE:   sucDbAccessFailed ,sucPiuUnlocked
        -- info-VALUE:   sucTransmissionError ,sucWrongSwVersion
        -- info-VALUE:   sucUnitTypeMismatch
        -- info-VALUE:   sucFtpTransError ,sucFtpCrcError
        -- info-VALUE:   sucSwHwMismatch ,sucUpgrWrongAvState
        -- info-VALUE:   sucFepromCopyFault ,sucUpdateDescFileFailed
        -- info-VALUE:   sucFtpServerNoteAvailable ,sucFtpSendError
        -- info-VALUE:   sucDbBackupFault ,sucUpgradeComplete
        -- info-VALUE:   sucUpgradeNotComplete
        -- info-VALUE:   sucUpgrTaskCreationFault
        -- info-VALUE:   sucUpgrDbAccessFault
        -- info-COMMENT: specifies the result of the upgrade
        -- info-ROU:     GET db
        -- info-IMPL:    V1.3N->
        -- info-VERCTRL: -
        SYNTAX        Xldv11ControlReq
        ACCESS        read-only
        STATUS        mandatory
        DESCRIPTION
	  " This read-only attribute informs about the result of 
	    the performes upgrade (in case of failed upgrade
            the error reason). "
        --DEFAULT next-function-async     fsnSutEntryNext
        --DEFAULT get-function-async      fsnSutEntryGet
        ::= { xldv11SutTaskTableEntry 7 }

  xldv11SutTimeStamp OBJECT-TYPE
     -- info-LEAF:    xldv11SutTimeStamp
     -- info-TREE:    xldv11Swm
     -- info-ACC:     ro
     -- info-SYNTAX:  TimeTicks
     -- info-VALUE:   0..2Giga
     -- info-COMMENT: specifies the time stamp in seconds
     -- info-COMMENT: set when task was started
     -- info-COMMENT: and anytime when the state of the task
     -- info-COMMENT: changes
     -- info-ROU:     GET db
     -- info-IMPL:    V1.3N->
     -- info-VERCTRL: -
     SYNTAX        TimeTicks
     ACCESS        read-only
     STATUS        mandatory
     DESCRIPTION
        " The time stamp of the task. It is updated anytime the
        upgrade task state changes. "
        --DEFAULT next-function-async     fsnSutEntryNext
        --DEFAULT get-function-async      fsnSutEntryGet
        ::= { xldv11SutTaskTableEntry 8 }


 -- ==============================================================
 --       D a t a B a s e   M a n a g e m e n t   G r o u p
 -- ==============================================================

 -- --------------------------------------------------------------
 --             DataBase Management control subgroup
 -- --------------------------------------------------------------

 xldv11DbmControl OBJECT IDENTIFIER ::= { xldv11Dbm 1 }
    -- info-NODE:    xldv11DbmControl
    -- info-TREE:    xldv11Dbm
    -- info-ACC:     nac
    -- info-COMMENT: Database Management control object.
    -- info-IMPL:    V1.3H->

 -- This managed entity manages the control request for storage
 -- of the database.

 xldv11DbmControlReq OBJECT-TYPE
    -- info-LEAF:    xldv11DbmControlReq
    -- info-TREE:    xldv11Dbm
    -- info-ACC:     rw
    -- info-SYNTAX:  Xldv11ControlReq
    -- info-VALUE:   noRequest, commExecStarted
    -- info-VALUE:   backupDb(command)
    -- info-VALUE:   localBackupOk, remoteBackupOk,
    -- info-VALUE:   localBackupFailed, remoteBackupFailed,
    -- info-VALUE:   flashAccessFailed, dbReadFailed 
    -- info-VALUE:   requestBusy,setDataFailed
    -- info-VALUE:   aswTimeout
    -- info-COMMENT: Database Management control request
    -- info-ROU:     GET db SET dm
    -- info-IMPL:    V1.3H->
    -- info-VERCTRL: V1.1U..V1.3B:GET db SET blocked
    SYNTAX        Xldv11ControlReq
    ACCESS        read-write
    STATUS        mandatory
    DESCRIPTION
	 " Marks the received command to store the database
	   (backupDb) into the FEPROM of the ONU.
	   The return value commExecStarted indicates the beginning
	   of DB storage.
	   Notifications : xldv11TrDbBackup indicates the end and 
	   the result of the database storage."
    --DEFAULT set-function-async      fsnDbmSet
    --DEFAULT next-function-async     fsnDbmNext
    --DEFAULT test-function-async     fsnDbmTest
    --DEFAULT get-function-async      fsnDbmGet
    ::= { xldv11DbmControl 1 }

 xldv11DbmControlStatus OBJECT-TYPE
    -- info-LEAF:    xldv11DbmControlStatus
    -- info-TREE:    xldv11Dbm
    -- info-ACC:     ro
    -- info-SYNTAX:  Xldv11ControlStatus
    -- info-VALUE:   requestIdle(1), requestBusy(2), requestPassed(3)
    -- info-VALUE:   requestFailed(4)
    -- info-COMMENT: Control status of command.
    -- info-ROU:     GET db
    -- info-IMPL:    V1.3H->
    -- info-VERCTRL: V1.1U->V1.3B: GET db
    SYNTAX        Xldv11ControlStatus
    ACCESS        read-only
    STATUS        mandatory
    DESCRIPTION
	 " The status of the control request. The value requestIdle
	   will be set after startup/recovery or after a running
	   test was aborted by the SNMP manager.
	   Range of values is:
	      requestIdle,
	      requestBusy,
	      requestPassed,
	      requestFailed . "
    --DEFAULT next-function-async     fsnDbmNext
    --DEFAULT get-function-async      fsnDbmGet
    ::= { xldv11DbmControl 2 }

 xldv11DbmControlTimer OBJECT-TYPE
    -- info-LEAF:    xldv11DbmControlTimer
    -- info-TREE:    xldv11Dbm
    -- info-ACC:     ro
    -- info-SYNTAX:  Integer32
    -- info-VALUE:   -2147483648..2147483647
    -- info-COMMENT: Maximum duration of backup command
    -- info-ROU:     GET db
    -- info-IMPL:    V1.3H->
    -- info-VERCTRL: V1.1U->V1.3B: GET db
    SYNTAX        Integer32
    ACCESS        read-only
    STATUS        mandatory
    DESCRIPTION
	  " The maximum wait time for the manager when a DB storage
	    request cannot be executed immediately (value commExecStarted
	    in the GetResponse for xldv11DbmControlReq).
	    The manager reads this value from the ONU.
	    The end of request indicates the trap xldv11TrDbBackup."
    --DEFAULT next-function-async     fsnDbmNext
    --DEFAULT get-function-async      fsnDbmGet
    ::= { xldv11DbmControl 3 }

 xldv11DbmBackupPeriod OBJECT-TYPE
    -- info-LEAF:    xldv11DbmBackupPeriod
    -- info-TREE:    xldv11Dbm
    -- info-ACC:     rw
    -- info-SYNTAX:  INTEGER
    -- info-VALUE:   12..48 (unit = hour)
    -- info-VALUE:   default = 24
    -- info-COMMENT: Interval between two backups in hours
    -- info-ROU:     GET db SET dm
    -- info-IMPL:    V1.3H->
    -- info-VERCTRL: V1.1U->V1.3B: GET db SET blocked
    SYNTAX        INTEGER (12..48)
	ACCESS        read-write
	STATUS        mandatory
	DESCRIPTION
	      " Interval between two backup operations in hours."
	--DEFAULT test-function-async     fsnDbmTest
	--DEFAULT next-function-async     fsnDbmNext
	--DEFAULT set-function-async      fsnDbmSet
	--DEFAULT get-function-async      fsnDbmGet
	::= { xldv11DbmControl 4 }

 xldv11DbmBackupStartTime OBJECT-TYPE
    -- info-LEAF:    xldv11DbmBackupStartTime
    -- info-TREE:    xldv11Dbm
    -- info-ACC:     rw
    -- info-SYNTAX:  INTEGER
    -- info-VALUE:   0..86400
    -- info-COMMENT: start time of next backup in sec
    -- info-ROU:     GET db SET db
    -- info-IMPL:    V1.3H->
    -- info-VERCTRL: V1.1U->V1.3B: GET db SET db
	SYNTAX        INTEGER (0..86400)
	ACCESS        read-write
	STATUS        mandatory
	DESCRIPTION
	      " Start time of next DB backup in seconds. "
	--DEFAULT test-function-async     fsnDbmTest
	--DEFAULT next-function-async     fsnDbmNext
	--DEFAULT set-function-async      fsnDbmSet
	--DEFAULT get-function-async      fsnDbmGet
	::= { xldv11DbmControl 5 }

 xldv11DbmControlReqResultLocal OBJECT-TYPE
    -- info-LEAF:    xldv11DbmControlReqResultLocal
    -- info-TREE:    xldv11Dbm
    -- info-ACC:     ro
    -- info-SYNTAX:  Xldv11ControlReq
    -- info-VALUE:   see xldv11DbmControlReq
    -- info-COMMENT: result of last local backup request
    -- info-ROU:     GET db
    -- info-IMPL:    V1.3H->
    -- info-VERCTRL: -
    SYNTAX        Xldv11ControlReq
    ACCESS        read-only
    STATUS        mandatory
    DESCRIPTION
	  " This read-only attribute informs about the result of 
	     the local backup request."
    --DEFAULT next-function-async     fsnDbmNext
    --DEFAULT get-function-async      fsnDbmGet
    ::= { xldv11DbmControl 6 }

 xldv11DbmControlReqResultRemote OBJECT-TYPE
    -- info-LEAF:    xldv11DbmControlReqResultRemote
    -- info-TREE:    xldv11Dbm
    -- info-ACC:     ro
    -- info-SYNTAX:  Xldv11ControlReq
    -- info-VALUE:   noRequest, commExecStarted
    -- info-VALUE:   backupDb
    -- info-VALUE:   flashAccessFailed, dbReadFailed 
    -- info-VALUE:   localBackupOk, remoteBackupOk,
    -- info-VALUE:   localBackupFailed, remoteBackupFailed,
    -- info-VALUE:   flashAccessFailed, dbReadFailed 
    -- info-VALUE:   requestBusy,setDataFailed
    -- info-VALUE:   aswTimeout
    -- info-COMMENT: the result of last remote backup request
    -- info-ROU:     GET db
    -- info-IMPL:    V1.3H->
    -- info-VERCTRL: -
    SYNTAX        Xldv11ControlReq
    ACCESS        read-only
    STATUS        mandatory
    DESCRIPTION
	  " This read-only attribute informs about the result of 
	     the last remote backup request."
    --DEFAULT next-function-async     fsnDbmNext
    --DEFAULT get-function-async      fsnDbmGet
    ::= { xldv11DbmControl 7 }

 xldv11DbmPathAndFileName OBJECT-TYPE
    -- info-LEAF:    xldv11DbmPathAndFileName
    -- info-TREE:    xldv11Dbm
    -- info-ACC:     rw
    -- info-SYNTAX:  OCTET STRING ( SIZE (0..150) )
    -- info-VALUE:   -
    -- info-COMMENT: path and file name relative to FTP root 
    -- info-COMMENT: for remote backup
    -- info-ROU:     GET db SET db
    -- info-IMPL:    V1.3H->
    -- info-VERCTRL: -
    SYNTAX        OCTET STRING ( SIZE (0..150) )
    ACCESS        read-write
    STATUS        mandatory
    DESCRIPTION
	 " The content of this attribute is the path and filename
	 (relative to the FTP root) of the DB backup file needed
	 for the remote backup feature."
    --DEFAULT test-function-async     fsnDbmTest
    --DEFAULT next-function-async     fsnDbmNext
    --DEFAULT set-function-async      fsnDbmSet
    --DEFAULT get-function-async      fsnDbmGet
    ::= { xldv11DbmControl 8 }

  xldv11DbmControlTimeStamp OBJECT-TYPE
     -- info-LEAF:    xldv11DbmControlTimeStamp
     -- info-TREE:    xldv11Dbm
     -- info-ACC:     ro
     -- info-SYNTAX:  TimeTicks
     -- info-VALUE:   0..2Giga
     -- info-COMMENT: specifies the time stamp in seconds
     -- info-COMMENT: of the last command
     -- info-COMMENT: (end of command)
     -- info-ROU:     GET db
    -- info-IMPL:    V1.3N->
     -- info-VERCTRL: -
     SYNTAX        TimeTicks
     ACCESS        read-only
     STATUS        mandatory
     DESCRIPTION
        " This read-only attribute informs about the time stamp
        of the last command (end of command)."
    --DEFAULT next-function-async     fsnDbmNext
    --DEFAULT get-function-async      fsnDbmGet
    ::= { xldv11DbmControl 9 }

     -- ==============================================================
     --                       Trap ID group
     -- ==============================================================

     -- --------------------------------------------------------------
     --                   Trap variables subgroup
     -- --------------------------------------------------------------

     xldv11TrapVars OBJECT IDENTIFIER ::= { xldv11Traps 1 }
	-- info-NODE:    xldv11TrapVars
	-- info-TREE:    xldv11Traps
	-- info-ACC:     nac
	-- info-IMPL:    V1.0->

     xldv11TvStartupResult OBJECT-TYPE
	-- info-LEAF:    xldv11TvStartupResult
	-- info-TREE:    xldv11Traps
	-- info-ACC:     nac
	-- info-SYNTAX:  Xldv11StartupResult
	-- info-VALUE:   suFinished(1)..suFailed(2)
	-- info-COMMENT: -
	-- info-IMPL:    V1.0->
	SYNTAX        Xldv11StartupResult
	ACCESS        not-accessible
	STATUS        mandatory
	DESCRIPTION
	     " Indicates the end of startup. "
	::= { xldv11TrapVars 1 }

     xldv11TvStartupType OBJECT-TYPE
	-- info-LEAF:    xldv11TvStartupType
	-- info-TREE:    xldv11Traps
	-- info-ACC:     nac
	-- info-SYNTAX:  Xldv11StartupType
	-- info-VALUE:   warm(2),cold(3),reload(4)
	-- info-COMMENT: -
	-- info-IMPL:    V1.0->
	SYNTAX        Xldv11StartupType
	ACCESS        not-accessible
	STATUS        mandatory
	DESCRIPTION
	     " Reset type corresponding to values of xldv11RstControlReq. "
	::= { xldv11TrapVars 2 }

     xldv11TvSnmLctSession OBJECT-TYPE
	-- info-LEAF:    xldv11TvSnmLctSession
	-- info-TREE:    xldv11Traps
	-- info-ACC:     nac
	-- info-SYNTAX:  Xldv11SnmLctSession
	-- info-VALUE:   connected(1),disconnected(2)
	-- info-VALUE:   sessionCancelled(3),sessionTimeout(4)
	-- info-VALUE:   onuCutSession(5) (V1.3A->)
	-- info-COMMENT: connected(1): LCT connected from NE initiated 
	-- info-COMMENT: by LCT sent to TMN-OS.
	-- info-COMMENT: disconnected(2): LCT disconnected from NE 
	-- info-COMMENT: initiated by LCT sent to TMN-OS.        
	-- info-COMMENT: sessionCancelled(3): Sent to LCT and TMN
	-- info-COMMENT: after timeout or TMN cancelling of LCT session.
	-- info-COMMENT: sessionTimeout(4): in case of a time out
	-- info-COMMENT: sent to TMN-OS.
	-- info-COMMENT: onuCutSessio(5): In case of an update of SNMP
	-- info-COMMENT: configuration file with LCT-IP address 
	-- info-COMMENT: removed sent to TMN-OS and LCT.
	-- info-IMPL:    V1.0->
	SYNTAX        Xldv11SnmLctSession
	ACCESS        not-accessible
	STATUS        mandatory
	DESCRIPTION
	     " Indicates the state of a LCT session . "
	::= { xldv11TrapVars 3 }

     xldv11TvRepEntity OBJECT-TYPE
	-- info-LEAF:    xldv11TvRepEntity
	-- info-TREE:    xldv11Traps
	-- info-ACC:     nac
	-- info-SYNTAX:  Integer32
	-- info-VALUE:   -2147483648..2147483647
	-- info-COMMENT: range: xldv11HwUnitIndex (HWM) or
	-- info-COMMENT: xldv11IfIndex (TLM) or range of Callp objects.
	-- info-IMPL:    V1.0->
	SYNTAX        Integer32
	ACCESS        not-accessible
	STATUS        mandatory
	DESCRIPTION
	     " The hardware unit index (HWM) or interface index (TLM)
	       or index of CallP reporting entities. "
	::= { xldv11TrapVars 4 }

     xldv11TvRepSource OBJECT-TYPE
	-- info-LEAF:    xldv11TvRepSource
	-- info-TREE:    xldv11Traps
	-- info-ACC:     nac
	-- info-SYNTAX:  Xldv11RepSource
	-- info-VALUE:   hwm(1),tlm(2),callpNni(3),callpUni(4)
	-- info-VALUE:   extAlarm(5),vccTp(6),vpcTp(7)
	-- info-COMMENT: to identify the reporting source.
	-- info-IMPL:    V1.0->
	SYNTAX        Xldv11RepSource
	ACCESS        not-accessible
	STATUS        mandatory
	DESCRIPTION
	      " Indicates the source of a reporting entity. "
	::= { xldv11TrapVars 5 }

     xldv11TvTimeAndDate OBJECT-TYPE
	-- info-LEAF:    xldv11TvTimeAndDate
	-- info-TREE:    xldv11Traps
	-- info-ACC:     nac
	-- info-SYNTAX:  Integer32
	-- info-VALUE:   -2147483648..2147483647
	-- info-COMMENT: time stamp in seconds
	-- info-IMPL:    V1.0->
	SYNTAX        Integer32
	ACCESS        not-accessible
	STATUS        mandatory
	DESCRIPTION
	     " The time and data value. "
	::= { xldv11TrapVars 6 }

     xldv11TvActCcReloadResult OBJECT-TYPE
	-- info-LEAF:    xldv11TvActCcReloadResult
	-- info-TREE:    xldv11Traps
	-- info-ACC:     nac
	-- info-SYNTAX:  INTEGER
	-- info-VALUE:   ok(1),notOk(2),lineIndexFaulty(3) (V1.1U->)
	-- info-COMMENT: -
	-- info-IMPL:    V1.0->
	SYNTAX        INTEGER {
			 ok(1),
			 notOk(2),
			 lineIndexFaulty(3)
		      }
	ACCESS        not-accessible
	STATUS        mandatory
	DESCRIPTION
	     " The result of the cross connection reload. "
	::= { xldv11TrapVars 7 }

     xldv11TvActCcStatus OBJECT-TYPE
    -- info-LEAF:    xldv11TvActCcStatus
    -- info-TREE:    xldv11Traps
    -- info-ACC:     nac
    -- info-SYNTAX:  Integer32
    -- info-VALUE:   -2147483648..2147483647
    -- info-COMMENT: Identifies a faulty CC
    -- info-IMPL:    V1.0->
	SYNTAX        Integer32
	ACCESS        not-accessible
	STATUS        mandatory
	DESCRIPTION
	     " The index (xldv11ActVpiNni) of faulty cross connect
	       in the table xldv11AtmCrossConnectTable. "
	::= { xldv11TrapVars 8 }

     xldv11TvAlmNatureOfAlarm OBJECT-TYPE
	-- info-LEAF:    xldv11TvAlmNatureOfAlarm
	-- info-TREE:    xldv11Traps
	-- info-ACC:     nac
	-- info-SYNTAX:  Xldv11TrapIds
	-- info-VALUE:   see xldv11AlmSevTrapId
	-- info-COMMENT: the nature of alarm (trap ID)
	-- info-IMPL:    V1.0->
	SYNTAX        Xldv11TrapIds
	ACCESS        not-accessible
	STATUS        mandatory
	DESCRIPTION
	     " The nature of an alarm (trap ID). "
	::= { xldv11TrapVars 9 }

     xldv11TvAlmSpecProblem OBJECT-TYPE
	-- info-LEAF:    xldv11TvAlmSpecProblem
	-- info-TREE:    xldv11Traps
	-- info-ACC:     nac
	-- info-SYNTAX:  Integer32
	-- info-VALUE:   -2147483648..2147483647
	-- info-COMMENT: -
	-- info-IMPL:    V1.0->
	SYNTAX        Integer32
	ACCESS        not-accessible
	STATUS        mandatory
	DESCRIPTION
	     " The specific problem reported by alarming. "
	::= { xldv11TrapVars 10 }

     xldv11TvAlmFailedComponent OBJECT-TYPE
	-- info-LEAF:    xldv11TvAlmFailedComponent
	-- info-TREE:    xldv11Traps
	-- info-ACC:     nac
	-- info-SYNTAX:  Integer32
	-- info-VALUE:   -2147483648..2147483647
	-- info-COMMENT: -
	-- info-IMPL:    V1.0->
	SYNTAX        Integer32
	ACCESS        not-accessible
	STATUS        mandatory
	DESCRIPTION
	     " Describes the failed component. "
	::= { xldv11TrapVars 11 }

     xldv11TvAlmSeverityOfFailure OBJECT-TYPE
	-- info-LEAF:    xldv11TvAlmSeverityOfFailure
	-- info-TREE:    xldv11Traps
	-- info-ACC:     nac
	-- info-SYNTAX:  Integer32
	-- info-VALUE:   -2147483648..2147483647
	-- info-COMMENT: severity of alarm.
	-- info-IMPL:    V1.0->
	SYNTAX        Xldv11AlarmSeverity
	ACCESS        not-accessible
	STATUS        mandatory
	DESCRIPTION
	     " The severity of the repoprted failure. "
	::= { xldv11TrapVars 12 }

     xldv11TvAlmStatus OBJECT-TYPE
	-- info-LEAF:    xldv11TvAlmStatus
	-- info-TREE:    xldv11Traps
	-- info-ACC:     nac
	-- info-SYNTAX:  INTEGER
	-- info-VALUE:   present(0)..cleared(1)
	-- info-COMMENT: flag indicating whether alarm appears or is cleared.
	-- info-IMPL:    V1.0->
	SYNTAX        INTEGER {
			 present(0),
			 cleared(1)
		      }
	ACCESS        not-accessible
	STATUS        mandatory
	DESCRIPTION
	     " The severity of the repoprted failure. "
	::= { xldv11TrapVars 13 }

     xldv11TvAlmPropRepairAction OBJECT-TYPE
	-- info-LEAF:    xldv11TvAlmPropRepairAction
	-- info-TREE:    xldv11Traps
	-- info-ACC:     nac
	-- info-SYNTAX:  Integer32
	-- info-VALUE:   -2147483648..2147483647
	-- info-COMMENT: the proposed proper repair action
	-- info-IMPL:    V1.0->
	SYNTAX        Integer32
	ACCESS        not-accessible
	STATUS        mandatory
	DESCRIPTION
	     " Indicates proposed repair actions reported by the agent
	       for the problem identified by the alarm. "
	::= { xldv11TrapVars 14 }

     xldv11TvAlmFailedComponentRepSource OBJECT-TYPE
	-- info-LEAF:    xldv11TvAlmFailedComponentRepSource
	-- info-TREE:    xldv11Traps
	-- info-ACC:     nac
	-- info-SYNTAX:  Xldv11RepSource
	-- info-VALUE:   hwm(1),tlm(2),callpNni(3),callpUni(4)
	-- info-VALUE:   extAlarm(5),vccTp(6),vpcTp(7)
	-- info-COMMENT: to identify the reporting source
	-- info-IMPL:    V1.0->
	SYNTAX        Xldv11RepSource
	ACCESS        not-accessible
	STATUS        mandatory
	DESCRIPTION
	      " Indicates the source of the reporting entity. "
	::= { xldv11TrapVars 15 }

     xldv11TvStcOldAdminStatus OBJECT-TYPE
	-- info-LEAF:    xldv11TvStcOldAdminStatus
	-- info-TREE:    xldv11Traps
	-- info-ACC:     nac
	-- info-SYNTAX:  Xldv11AdminState
	-- info-VALUE:   unlocked(1)..locked(2)
	-- info-COMMENT: - 
	-- info-IMPL:    V1.0->
	SYNTAX        Xldv11AdminState
	ACCESS        not-accessible
	STATUS        mandatory
	DESCRIPTION
	     " This value is the old administrative status of the
	       entity changing its state. "
	::= { xldv11TrapVars 16 }

     xldv11TvStcNewAdminStatus OBJECT-TYPE
	-- info-LEAF:    xldv11TvStcNewAdminStatus
	-- info-TREE:    xldv11Traps
	-- info-ACC:     nac
	-- info-SYNTAX:  Xldv11AdminState
	-- info-VALUE:   unlocked(1)..locked(2)
	-- info-COMMENT: -
	-- info-IMPL:    V1.0->
	SYNTAX        Xldv11AdminState
	ACCESS        not-accessible
	STATUS        mandatory
	DESCRIPTION
	     " This value is the new administrative status of the
	       entity changing its state. "
	::= { xldv11TrapVars 17 }

     xldv11TvStcOldOperStatus OBJECT-TYPE
	-- info-LEAF:    xldv11TvStcOldOperStatus
	-- info-TREE:    xldv11Traps
	-- info-ACC:     nac
	-- info-SYNTAX:  Xldv11OperState
	-- info-VALUE:   enabled(1)..disabled(2)
	-- info-COMMENT: -
	-- info-IMPL:    V1.0->
	SYNTAX        Xldv11OperState
	ACCESS        not-accessible
	STATUS        mandatory
	DESCRIPTION
	     " The old operational state of the reporting entity. "
	::= { xldv11TrapVars 18 }

     xldv11TvStcNewOperStatus OBJECT-TYPE
	-- info-LEAF:    xldv11TvStcNewOperStatus
	-- info-TREE:    xldv11Traps
	-- info-ACC:     nac
	-- info-SYNTAX:  Xldv11OperState
	-- info-VALUE:   enabled(1)..disabled(2)
	-- info-COMMENT: -
	-- info-IMPL:    V1.0->
	SYNTAX        Xldv11OperState
	ACCESS        not-accessible
	STATUS        mandatory
	DESCRIPTION
	     " The new operational state of the reporting entity. "
	::= { xldv11TrapVars 19 }

     xldv11TvTsrControlStatus OBJECT-TYPE
	-- info-LEAF:    xldv11TvTsrControlStatus
	-- info-TREE:    xldv11Traps
	-- info-ACC:     nac
	-- info-SYNTAX:  Xldv11ControlStatus
	-- info-VALUE:   requestIdle(1)..requestBusy(2),
	-- info-VALUE:   requestPassed(3)..requestFailed(4)
	-- info-COMMENT: -
	-- info-IMPL:    V1.0->
	SYNTAX        Xldv11ControlStatus
	ACCESS        not-accessible
	STATUS        mandatory
	DESCRIPTION
	     " The control status of the test result. "
	::= { xldv11TrapVars 20 }

     xldv11TvRstResult OBJECT-TYPE
	-- info-LEAF:    xldv11TvRstResult
	-- info-TREE:    xldv11Traps
	-- info-ACC:     nac
	-- info-SYNTAX:  Xldv11RstResult
	-- info-VALUE:   requestFailed(4)
	-- info-COMMENT: result of reset request
	-- info-IMPL:    V1.0->
	SYNTAX        Xldv11RstResult
	ACCESS        not-accessible
	STATUS        mandatory
	DESCRIPTION
	     " This value indicates the result of a reset request. "
	::= { xldv11TrapVars 21 }

     xldv11TvRstHwUnitIndex OBJECT-TYPE
	-- info-LEAF:    xldv11TvRstHwUnitIndex
	-- info-TREE:    xldv11Traps
	-- info-ACC:     nac
	-- info-SYNTAX:  Unsigned16
	-- info-VALUE:   0..65535
	-- info-COMMENT: -
	-- info-IMPL:    V1.0->
	SYNTAX        Unsigned16
	ACCESS        not-accessible
	STATUS        mandatory
	DESCRIPTION
	     " This value indicates the hardware unit of a reset request. "
	::= { xldv11TrapVars 22 }

     xldv11TvHweResetType OBJECT-TYPE
	-- info-LEAF:    xldv11TvHweResetType
	-- info-TREE:    xldv11Traps
	-- info-ACC:     nac
	-- info-SYNTAX:  Xldv11StartupType
	-- info-VALUE:   cold, warm, reload
	-- info-COMMENT: indicates a replaceable unit reset.
	-- info-IMPL:    V1.0->
	SYNTAX        Xldv11StartupType
            ACCESS        not-accessible
            STATUS        mandatory
            DESCRIPTION
                 " The reset type of a hardware event. "
            ::= { xldv11TrapVars 23 }
 
         xldv11TvAdcControlStatus OBJECT-TYPE
            -- info-LEAF:    xldv11TvAdcControlStatus
            -- info-TREE:    xldv11Traps
            -- info-ACC:     nac
            -- info-SYNTAX:  Integer32
            -- info-VALUE:   -2147483648..2147483647
            -- info-COMMENT: Variable of change rate trap
            -- info-IMPL:    V1.0->
            SYNTAX        Integer32
            ACCESS        not-accessible
            STATUS        mandatory
            DESCRIPTION
                 " The result of the changeRate request. "
            ::= { xldv11TrapVars 24 }
 
         xldv11TvSucResult OBJECT-TYPE
            -- info-LEAF:    xldv11TvSucResult
            -- info-TREE:    xldv11Traps
            -- info-ACC:     nac
            -- info-SYNTAX:  Xldv11ControlReq
            -- info-VALUE:   sucOk ,sucNotOk
            -- info-VALUE:   sucDbAccessFailed ,sucPiuUnlocked
            -- info-VALUE:   sucTransmissionError,sucWrongSwVersion
            -- info-VALUE:   sucUnitTypeMismatch,sucFtpTransError
            -- info-VALUE:   sucFtpCrcError,sucSwHwMismatch
            -- info-VALUE:   sucUpgrWrongAvState,sucFepromCopyFault
            -- info-VALUE:   sucUpdateDescFileFailed,sucFtpServerNoteAvailable
            -- info-VALUE:   sucFtpSendError,sucDbBackupFault
            -- info-VALUE:   sucUpgradeComplete,sucUpgradeNotComplete
            -- info-COMMENT: Result of SW upgrade.
            -- info-IMPL:    V1.0->
            SYNTAX        Xldv11ControlReq
            ACCESS        not-accessible
            STATUS        mandatory
            DESCRIPTION
                 " Result of software upgrade. "
            ::= { xldv11TrapVars 25 }
 
         xldv11TvSucUnit OBJECT-TYPE
            -- info-LEAF:    xldv11TvSucUnit
            -- info-TREE:    xldv11Traps
            -- info-ACC:     nac
            -- info-SYNTAX:  DisplayString (SIZE (0..20))
            -- info-VALUE:   string: plug in unit
            -- info-COMMENT: corresponds to attribute of SwmUpgradeControl.
            -- info-IMPL:    V1.0->
            SYNTAX        DisplayString (SIZE (0..20))
            ACCESS        not-accessible
            STATUS        mandatory
            DESCRIPTION
                 " It's value corresponds to the attribute
                   xldSwmUpgradeControl. "
            ::= { xldv11TrapVars 26 }
 
         xldv11TvSucHwUnitIndex OBJECT-TYPE
            -- info-LEAF:    xldv11TvSucHwUnitIndex
            -- info-TREE:    xldv11Traps
            -- info-ACC:     nac
            -- info-SYNTAX:  Unsigned16
            -- info-VALUE:   0..65535
            -- info-COMMENT: corresponds to attribute of SwmUpgradeControl.
            -- info-IMPL:    V1.0->
            SYNTAX        Unsigned16
            ACCESS        not-accessible
            STATUS        mandatory
            DESCRIPTION
                 " This attribute corresponds to the one in the group
                   xldSwmUpgradeControl. "
            ::= { xldv11TrapVars 27 }
 
         xldv11TvSucVersionNo OBJECT-TYPE
            -- info-LEAF:    xldv11TvSucVersionNo
            -- info-TREE:    xldv11Traps
            -- info-ACC:     nac
            -- info-SYNTAX:  DisplayString (SIZE (0..10))
            -- info-VALUE:   string: version number
            -- info-COMMENT: -
            -- info-IMPL:    V1.0->
            SYNTAX        DisplayString (SIZE (0..10))
            ACCESS        not-accessible
            STATUS        mandatory
            DESCRIPTION
                 " This attribute corresponds to the one in the group
                   xldSwmUpgradeControl.
                   Default value: \0 "
            ::= { xldv11TrapVars 28 }
 
         xldv11TvSucPathName OBJECT-TYPE
            -- info-LEAF:    xldv11TvSucPathName
            -- info-TREE:    xldv11Traps
            -- info-ACC:     nac
            -- info-SYNTAX:  DisplayString (SIZE (0..150))
            -- info-VALUE:   string: path name of load
            -- info-COMMENT: -
            -- info-IMPL:    V1.0->
            SYNTAX        DisplayString (SIZE (0..150))
            ACCESS        not-accessible
            STATUS        mandatory
            DESCRIPTION
                 " This attribute corresponds to the one in the group
                   xldSwmUpgradeControl. "
            ::= { xldv11TrapVars 29 }
 
         xldv11TvSucFileName OBJECT-TYPE
            -- info-LEAF:    xldv11TvSucFileName
            -- info-TREE:    xldv11Traps
            -- info-ACC:     nac
            -- info-SYNTAX:  DisplayString (SIZE (0..50))
            -- info-VALUE:   string: file name of load
            -- info-COMMENT: -
            -- info-IMPL:    V1.0->
            SYNTAX        DisplayString (SIZE (0..50))
            ACCESS        not-accessible
            STATUS        mandatory
            DESCRIPTION
                 " This attribute corresponds to the one in the group
                   xldSwmUpgradeControl. "
            ::= { xldv11TrapVars 30 }
 
         xldv11TvDbuSweLogReadResult OBJECT-TYPE
            -- info-LEAF:    xldv11TvDbuSweLogReadResult
            -- info-TREE:    xldv11Traps
            -- info-ACC:     nac
            -- info-SYNTAX:  Xldv11DbuReadStatus
            -- info-VALUE:   buReadComplete(1),dbuReadFailed(2)
            -- info-VALUE:   dbuFileCreationFailed(3)
            -- info-VALUE:   dbuFileTransmissionFailed(4)
            -- info-COMMENT: Indicates, that LOG reading has been terminated.
            -- info-COMMENT: Returnvalues for error cases.
            -- info-IMPL:    V1.0->
            SYNTAX        Xldv11DbuReadStatus
            ACCESS        not-accessible
            STATUS        mandatory
            DESCRIPTION
                 " The value indicates the read result of the software
                   error log. "
            ::= { xldv11TrapVars 31 }
 
         xldv11TvDbuHwmLogReadResult OBJECT-TYPE
            -- info-LEAF:    xldv11TvDbuHwmLogReadResult
            -- info-TREE:    xldv11Traps
            -- info-ACC:     nac
            -- info-SYNTAX:  Xldv11DbuReadStatus
            -- info-VALUE:   dbuReadComplete(1),dbuReadFailed(2)
            -- info-VALUE:   dbuFileCreationFailed(3)
            -- info-VALUE:   dbuFileTransmissionFailed(4)
            -- info-COMMENT: -
            -- info-IMPL:    V1.0->
            SYNTAX        Xldv11DbuReadStatus
            ACCESS        not-accessible
            STATUS        mandatory
            DESCRIPTION
                 " The value indicates the read result of the hardware
                   maintenance log. "
            ::= { xldv11TrapVars 32 }
 
         xldv11TvDbuSwTraceLogReadResult OBJECT-TYPE
            -- info-LEAF:    xldv11TvDbuSwTraceLogReadResult
            -- info-TREE:    xldv11Traps
            -- info-ACC:     nac
            -- info-SYNTAX:  Xldv11DbuReadStatus
            -- info-VALUE:   buReadComplete(1),dbuReadFailed(2)
            -- info-VALUE:   dbuFileCreationFailed(3)
            -- info-VALUE:   dbuFileTransmissionFailed(4)
            -- info-COMMENT: -
            -- info-IMPL:    V1.0->
            SYNTAX        Xldv11DbuReadStatus
            ACCESS        not-accessible
            STATUS        mandatory
            DESCRIPTION
                 " The value indicates the read result of the software
                   trace log. "
            ::= { xldv11TrapVars 33 }

         xldv11TvHwUnitType OBJECT-TYPE
            -- info-LEAF:    xldv11TvHwUnitType
            -- info-TREE:    xldv11Traps
            -- info-ACC:     nac
            -- info-SYNTAX:  Xldv11HwUnitType
            -- info-VALUE:   equipment(1),equipmentHolder(2)
            -- info-VALUE:   plugInUnit(3)
            -- info-COMMENT: Sent within trap ObjCreate/Delete. Specifies
            -- info-COMMENT: the object, which has been created or deleted.
            -- info-IMPL:    V1.2A->
            SYNTAX        Xldv11HwUnitType
            ACCESS        not-accessible
            STATUS        mandatory
            DESCRIPTION
                 " The type of the created or deleted Hwm object. "
            ::= { xldv11TrapVars 34 }
 

         xldv11TvHwContainingUnitIndex OBJECT-TYPE
            -- info-LEAF:    xldv11TvHwContainingUnitIndex
            -- info-TREE:    xldv11Traps
            -- info-ACC:     nac
            -- info-SYNTAX:  Unsigned16
            -- info-VALUE:   0..65535
            -- info-COMMENT: Index of containing unit.
            -- info-IMPL:    V1.2A->
            SYNTAX        Unsigned16
            ACCESS        not-accessible
            STATUS        mandatory
            DESCRIPTION
                 " xldv11HwUnitIndex of the created or deleted Hwm object. "
            ::= { xldv11TrapVars 35 }


         xldv11TvHwContainedUnitAddr OBJECT-TYPE
            -- info-LEAF:    xldv11TvHwContainedUnitAddr
            -- info-TREE:    xldv11Traps
            -- info-ACC:     nac
            -- info-SYNTAX:  INTEGER
            -- info-VALUE:   1..512
            -- info-COMMENT: Address of containded unit.
            -- info-IMPL:    V1.2A->
            SYNTAX        INTEGER(1..512)
            ACCESS        not-accessible
            STATUS        mandatory
            DESCRIPTION
                 " A number of the contained Unit "
            ::= { xldv11TrapVars 36 }


         xldv11TvHwuControlResult OBJECT-TYPE
            -- info-LEAF:    xldv11TvHwuControlResult
            -- info-TREE:    xldv11Traps
            -- info-ACC:     nac
            -- info-SYNTAX:  Xldv11HwuControlResult
            -- info-VALUE:   paramFaulty(11), commandFailed(212),
            -- info-VALUE:   objExists(1003), equTypeNotAvail(1004),
            -- info-VALUE:   eqhTypeNotAvail(1005), piuTypeNotAvail(1006),
            -- info-VALUE:   piuTypeNotAccepted(1007),
            -- info-VALUE:   containingUnitNotAvail(1008),
            -- info-VALUE:   objNotAvail(1009), objNotEmpty(1010),
            -- info-VALUE:   objNotLocked(1011), objNotValid(1012)
            -- info-COMMENT: Result of xldv11HwuControlReq.
            -- info-IMPL:    V1.2A->
            SYNTAX        Xldv11HwuControlResult
            ACCESS        not-accessible
            STATUS        mandatory
            DESCRIPTION
                 " The result of the request xldv11HwuControlReq. "
            ::= { xldv11TrapVars 37 }


         xldv11TvRiRemInvResult OBJECT-TYPE
            -- info-LEAF:    xldv11TvRiRemInvResult
            -- info-TREE:    xldv11Traps
            -- info-ACC:     nac
            -- info-SYNTAX:  Xldv11RiResultType
            -- info-VALUE:   riRemoteInventoryComplete(1)
            -- info-VALUE:   riFileCreationFailed(2)
            -- info-VALUE:   riFileTransmissionFailed(3)
            -- info-COMMENT: Result of Rem-Inv-Data reading.
            -- info-IMPL:    V1.2A->
            SYNTAX        Xldv11RiResultType 
            ACCESS        not-accessible
            STATUS        mandatory
            DESCRIPTION
                 " The result of the request xldv11RiControlReq. "
            ::= { xldv11TrapVars 38 }

         xldv11TvVersionNrCmuLoad OBJECT-TYPE
            -- info-LEAF:    xldv11TvVersionNrCmuLoad
            -- info-TREE:    xldv11Traps
            -- info-ACC:     nac
            -- info-SYNTAX:  DisplayString (SIZE (0..20))
            -- info-VALUE:   string: Version number of current CMU load.
            -- info-COMMENT: Sent with xldv11TrStartupEnd.
            -- info-IMPL:    V1.2A->
            SYNTAX        DisplayString (SIZE (0..20))
            ACCESS        not-accessible
            STATUS        mandatory
            DESCRIPTION
                 " The version number of the current CMU load. "
            ::= { xldv11TrapVars 39 }

         xldv11TvBackupResult OBJECT-TYPE
            -- info-LEAF:    xldv11TvBackupResult
            -- info-TREE:    xldv11Traps
            -- info-ACC:     nac
            -- info-SYNTAX:  Xldv11DbmResultType
            -- info-VALUE:   dbOk(1),dbNok(2),flashAccessfailed(3)
            -- info-VALUE:   dbReadFailed(4),dbWriteFailed(5)
            -- info-COMMENT: -
            -- info-IMPL:    V1.2A->
            SYNTAX        Xldv11DbmResultType
            ACCESS        not-accessible
            STATUS        mandatory
            DESCRIPTION
                 " The result of the request xldv11DbmControlReq. "
            ::= { xldv11TrapVars 40 }

         xldv11TvVpiNni      OBJECT-TYPE
            -- info-LEAF:    xldv11TvVpiNni
            -- info-TREE:    xldv11Traps
            -- info-ACC:     nac
            -- info-SYNTAX:  Integer32
            -- info-VALUE:   -2147483648..2147483647
            -- info-COMMENT: -
            -- info-IMPL:    V1.0->
            SYNTAX        Integer32
            ACCESS        not-accessible
            STATUS        mandatory
            DESCRIPTION
                 " The VpiNni value of the cross connect. "
            ::= { xldv11TrapVars 41 }

         xldv11TvVpiNniIndex OBJECT-TYPE
            -- info-LEAF:    xldv11TvVpiNniIndex
            -- info-TREE:    xldv11Traps
            -- info-ACC:     nac
            -- info-SYNTAX:  Unsigned16
            -- info-VALUE:   0..65535
            -- info-COMMENT: -
            -- info-IMPL:    V1.0->
            SYNTAX        Unsigned16
            ACCESS        not-accessible
            STATUS        mandatory
            DESCRIPTION
                 " The index of the cross connect in the ATM 
                   cross connect table. "
            ::= { xldv11TrapVars 42 }

         xldv11TvVplTerminationPointA OBJECT-TYPE
            -- info-LEAF:    xldv11TvVplTerminationPointA
            -- info-TREE:    xldv11Traps
            -- info-ACC:     nac
            -- info-SYNTAX:  Integer32
            -- info-VALUE:   -2147483648..2147483647
            -- info-COMMENT: Index of VPL-TP at drop???switch side.
            -- info-IMPL:    V1.0->
            SYNTAX        Integer32
            ACCESS        not-accessible
            STATUS        mandatory
            DESCRIPTION
                 " For a point-to-point cross connect this attribute identifies
                   the instance of the VPL termination point that represents
                   the VPL at the LE side. "
            ::= { xldv11TrapVars 43 }

         xldv11TvVplTerminationPointZ OBJECT-TYPE
            -- info-LEAF:    xldv11TvVplTerminationPointZ
            -- info-TREE:    xldv11Traps
            -- info-ACC:     nac
            -- info-SYNTAX:  Integer32
            -- info-VALUE:   -2147483648..2147483647
            -- info-COMMENT: Index of VPL-TP at drop???switch side.
            -- info-IMPL:    V1.0->
            SYNTAX        Integer32
            ACCESS        not-accessible
            STATUS        mandatory
            DESCRIPTION
                 " For a point-to-point cross connect this attribute identifies
                   the instance of the VPL termination point that represents
                   the VPL at the NT side. "
            ::= { xldv11TrapVars 44 }

         xldv11TvSdvVpiNniOld OBJECT-TYPE
            -- info-LEAF:    xldv11TvSdvVpiNniOld
            -- info-TREE:    xldv11Traps
            -- info-ACC:     nac
            -- info-SYNTAX:  Integer32
            -- info-VALUE:   -2147483648..2147483647
            -- info-COMMENT: Sent within xldv11TrAttributeValueChange.
            -- info-IMPL:    V1.1U 
            SYNTAX        Integer32
            ACCESS        not-accessible
            STATUS        mandatory
            DESCRIPTION
                 " Send within trap xldv11TrAttributeValueChange. "
            ::= { xldv11TrapVars 45 }

         xldv11TvSdvVpiNniNew OBJECT-TYPE
            -- info-LEAF:    xldv11TvSdvVpiNniNew
            -- info-TREE:    xldv11Traps
            -- info-ACC:     nac
            -- info-SYNTAX:  Integer32
            -- info-VALUE:   -2147483648..2147483647
            -- info-COMMENT: Sent within xldv11TrAttributeValueChange.
            -- info-IMPL:    V1.1U
            SYNTAX        Integer32
            ACCESS        not-accessible
            STATUS        mandatory
            DESCRIPTION
                 " Send within trap xldv11TrAttributeValueChange. "
            ::= { xldv11TrapVars 46 }

         xldv11TvSnmMibVersion OBJECT-TYPE
            -- info-LEAF:    xldv11TvSnmMibVersion
            -- info-TREE:    xldv11Traps
            -- info-ACC:     nac
            -- info-SYNTAX:  DisplayString (SIZE (0..30))
            -- info-VALUE:   string: MIB version.
            -- info-COMMENT: Sent within xldv11TrAgentRunning/StartupEnd.
            -- info-IMPL:    V1.1U->
            SYNTAX        DisplayString (SIZE (0..30))
            ACCESS        not-accessible
            STATUS        mandatory
            DESCRIPTION
                 " The version number of the current MIB . "
            ::= { xldv11TrapVars 47 }

         xldv11TvSnmAgentVersion OBJECT-TYPE
            -- info-LEAF:    xldv11TvSnmAgentVersion
            -- info-TREE:    xldv11Traps
            -- info-ACC:     nac
            -- info-SYNTAX:  DisplayString (SIZE (0..30))
            -- info-VALUE:   string: SNMP agent version.
            -- info-COMMENT: Sent within xldv11TrAgentRunning/StartupEnd.
            -- info-IMPL:    V1.1U->
            SYNTAX        DisplayString (SIZE (0..30))
            ACCESS        not-accessible
            STATUS        mandatory
            DESCRIPTION
                 " The version number of the current Agent SW . "
            ::= { xldv11TrapVars 48 }

         xldv11TvVciNni  OBJECT-TYPE
            -- info-LEAF:    xldv11TvVciNni
            -- info-TREE:    xldv11Traps
            -- info-ACC:     nac
            -- info-SYNTAX:  Integer32
            -- info-VALUE:   -2147483648..2147483647
            -- info-COMMENT: -
            -- info-IMPL:    V1.2B->
            SYNTAX        Integer32
            ACCESS        not-accessible
            STATUS        mandatory
            DESCRIPTION
                 " new for V1.2B"
            ::= { xldv11TrapVars 49 }

         xldv11TvVciNniIndex  OBJECT-TYPE
            -- info-LEAF:    xldv11TvVciNniIndex
            -- info-TREE:    xldv11Traps
            -- info-ACC:     nac
            -- info-SYNTAX:  Unsigned16
            -- info-VALUE:   0..65535
            -- info-COMMENT: -
            -- info-IMPL:    V1.2B->
            SYNTAX        Unsigned16
            ACCESS        not-accessible
            STATUS        mandatory
            DESCRIPTION
                 " new for V1.2B"
            ::= { xldv11TrapVars 50 }

         xldv11TvVclTerminationPointA  OBJECT-TYPE
            -- info-LEAF:    xldv11TvVclTerminationPointA
            -- info-TREE:    xldv11Traps
            -- info-ACC:     nac
            -- info-SYNTAX:  Integer32
            -- info-VALUE:   -2147483648..2147483647
            -- info-COMMENT: Index of VCL-TP at switch side.
            -- info-IMPL:    V1.2B->
            SYNTAX        Integer32
            ACCESS        not-accessible
            STATUS        mandatory
            DESCRIPTION
                 " new for V1.2B"
            ::= { xldv11TrapVars 51 }

         xldv11TvVclTerminationPointZ  OBJECT-TYPE
            -- info-LEAF:    xldv11TvVclTerminationPointZ
            -- info-TREE:    xldv11Traps
            -- info-ACC:     nac
            -- info-SYNTAX:  Integer32
            -- info-VALUE:   -2147483648..2147483647
            -- info-COMMENT: Index of VCL-TP at drop side.
            -- info-IMPL:    V1.2B->
            SYNTAX        Integer32
            ACCESS        not-accessible
            STATUS        mandatory
            DESCRIPTION
                 " new for V1.2B"
            ::= { xldv11TrapVars 52 }

         xldv11TvVpcTpIndex OBJECT-TYPE
            -- info-LEAF:    xldv11TvVpcTpIndex
            -- info-TREE:    xldv11Traps
            -- info-ACC:     nac
            -- info-SYNTAX:  Unsigned16
            -- info-VALUE:   0..65535
            -- info-COMMENT: Used to address the corresponding.
            -- info-COMMENT: entry in the xlv11VpcTpTable
            -- info-IMPL:    V1.2B->
            SYNTAX        Unsigned16
            ACCESS        not-accessible
            STATUS        mandatory
            DESCRIPTION
                 " new for V1.2B"
            ::= { xldv11TrapVars 53 }

         xldv11TvVpcNniIndex OBJECT-TYPE
            -- info-LEAF:    xldv11TvVpcNniIndex
            -- info-TREE:    xldv11Traps
            -- info-ACC:     nac
            -- info-SYNTAX:  Unsigned16
            -- info-VALUE:   0..65535
            -- info-COMMENT: Used within xldv11TrCcCreation.
            -- info-IMPL:    V1.2B->
            SYNTAX        Unsigned16
            ACCESS        not-accessible
            STATUS        mandatory
            DESCRIPTION
                 " new for V1.2B"
            ::= { xldv11TrapVars 54 }

         xldv11TvVpcUniIndex OBJECT-TYPE
            -- info-LEAF:    xldv11TvVpcUniIndex
            -- info-TREE:    xldv11Traps
            -- info-ACC:     nac
            -- info-SYNTAX:  Unsigned16
            -- info-VALUE:   0..65535
            -- info-COMMENT: Used within xldv11TrCcCreation.
            -- info-IMPL:    V1.2B->
            SYNTAX        Unsigned16
            ACCESS        not-accessible
            STATUS        mandatory
            DESCRIPTION
                 " new for V1.2B "
            ::= { xldv11TrapVars 55 }

         xldv11TvEthVccTpIndex OBJECT-TYPE
            -- info-LEAF:    xldv11TvEthVccTpIndex
            -- info-TREE:    xldv11Traps
            -- info-ACC:     nac
            -- info-SYNTAX:  Unsigned16
            -- info-VALUE:   0..65535
            -- info-COMMENT: Used to address the corresponding.
            -- info-COMMENT: entry in the xlv11VccTpTable
            -- info-IMPL:    V1.2B->
            SYNTAX        Unsigned16
            ACCESS        not-accessible
            STATUS        mandatory
            DESCRIPTION
                 " new for V1.2B "
            ::= { xldv11TrapVars 56 }
 

         xldv11TvVpiValue OBJECT-TYPE
            -- info-LEAF:    xldv11TvVpiValue
            -- info-TREE:    xldv11Traps
            -- info-ACC:     nac
            -- info-SYNTAX:  Integer32
            -- info-VALUE:   -2147483648..2147483647
            -- info-COMMENT: Used within xldv11TrVplTpCreation.
            -- info-IMPL:    V1.2B->
            SYNTAX        Integer32 
            ACCESS        not-accessible
            STATUS        mandatory
            DESCRIPTION
                 " new for V1.2B "
            ::= { xldv11TrapVars 57 }

         xldv11TvVciValue OBJECT-TYPE
            -- info-LEAF:    xldv11TvVciValue
            -- info-TREE:    xldv11Traps
            -- info-ACC:     nac
            -- info-SYNTAX:  INTEGER
            -- info-VALUE:   0..65535
            -- info-COMMENT: Used within xldv11TrVccTpDeletion.
            -- info-IMPL:    V1.2B->
            SYNTAX        Unsigned16
            ACCESS        not-accessible
            STATUS        mandatory
            DESCRIPTION
                 " new for V1.2B"
            ::= { xldv11TrapVars 58 }

         xldv11TvVplTpIndex OBJECT-TYPE
            -- info-LEAF:    xldv11TvVplTpIndex
            -- info-TREE:    xldv11Traps
            -- info-ACC:     nac
            -- info-SYNTAX:  Integer32
            -- info-VALUE:   -2147483648..2147483647
            -- info-COMMENT: Used within xldv11TrVplTpCreation.
            -- info-IMPL:    V1.2B->
            SYNTAX        Integer32 
            ACCESS        not-accessible
            STATUS        mandatory
            DESCRIPTION
                 " new for V1.2B"
            ::= { xldv11TrapVars 59 }
 
         xldv11TvVplIfIndex OBJECT-TYPE
            -- info-LEAF:    xldv11TvVplIfIndex
            -- info-TREE:    xldv11Traps
            -- info-ACC:     nac
            -- info-SYNTAX:  Integer32
            -- info-VALUE:   -2147483648..2147483647
            -- info-COMMENT: Used within xldv11TrVplTpCreation/Deletion.
            -- info-IMPL:    V1.2B->
            SYNTAX        Integer32
            ACCESS        not-accessible
            STATUS        mandatory
            DESCRIPTION
                 " new for V1.2B"
            ::= { xldv11TrapVars 60 }

         xldv11TvAlmFailedComponentString OBJECT-TYPE
            -- info-LEAF:    xldv11TvAlmFailedComponentString
            -- info-TREE:    xldv11Traps
            -- info-ACC:     nac
            -- info-SYNTAX:  OCTET STRING ( SIZE (1..100) )
            -- info-VALUE:   default value 0
            -- info-COMMENT: list of indeces of VpcTps or VccTps
            -- info-IMPL:    V1.2B->
            SYNTAX        OCTET STRING ( SIZE (1..100) ) 
            ACCESS        not-accessible
            STATUS        mandatory
            DESCRIPTION
                  " Up 50 times indeces of VpcTp's or VccTp's. "
            ::= { xldv11TrapVars 61 }

         xldv11TvTelnetSession OBJECT-TYPE
            -- info-LEAF:    xldv11TvTelnetSession
            -- info-TREE:    xldv11Traps
            -- info-ACC:     nac
            -- info-SYNTAX:  Xldv11TvTelnetSessionStatus
            -- info-VALUE:   default stopped
            -- info-COMMENT: Signalizes the status of a telnet session.
            -- info-IMPL:    V1.3A->
            SYNTAX        Xldv11TvTelnetSessionStatus
            ACCESS        not-accessible
            STATUS        mandatory
            DESCRIPTION
                  " Signalizes the status of a telnet session. "
            ::= { xldv11TrapVars 62 }

        xldv11TvEthIfIndex OBJECT-TYPE
           -- info-LEAF:    xldv11TvEthIfIndex 
           -- info-TREE:    xldv11Traps
           -- info-ACC:     nac
           -- info-SYNTAX:  Integer32
           -- info-VALUE:   -2147483648..2147483647
           -- info-COMMENT: index of configured Eth Entry
           -- info-IMPL:    V1.1UA->
           SYNTAX        Integer32
           ACCESS        not-accessible
           STATUS        mandatory
           DESCRIPTION
                 " Index of configured Eth Entry. "
           ::= { xldv11TrapVars 63 }

        xldv11TvCACProblemType OBJECT-TYPE
           -- info-LEAF:    xldv11TvCACProblemType 
           -- info-TREE:    xldv11Traps
           -- info-ACC:     nac
           -- info-SYNTAX:  Xldv11CACProblemType
           -- info-VALUE:   bandwitdhUpstreamWarning(1),bandwidthDownstreamWarning(2)
           -- info-VALUE:   mbsUpstreamWarning(3), mbsDownstreamWarning(4)
           -- info-COMMENT: problem type when CAC problem 
           -- info-IMPL:    V1.3a->
           SYNTAX        Xldv11CACProblemType
           ACCESS        not-accessible
           STATUS        mandatory
           DESCRIPTION
                 " problem type when CAC problem . "
           ::= { xldv11TrapVars 64 }

        xldv11TvCACGuaranteedBandwidthUsage OBJECT-TYPE
           -- info-LEAF:    xldv11TvCACGuaranteedBandwidthUsage 
           -- info-TREE:    xldv11Traps
           -- info-ACC:     nac
           -- info-SYNTAX:  INTEGER
           -- info-VALUE:   0..100
           -- info-COMMENT: used bandwidth in percent
           -- info-IMPL:    V1.3a->
           SYNTAX        INTEGER ( 0..100 )
           ACCESS        not-accessible
           STATUS        mandatory
           DESCRIPTION
                 "used bandwidth in percent. "
           ::= { xldv11TrapVars 65 }

        xldv11TvEthVpcTpIndex OBJECT-TYPE
           -- info-LEAF:    xldv11TvEthVpcTpIndex 
           -- info-TREE:    xldv11Traps
           -- info-ACC:     nac
           -- info-SYNTAX:  Unsigned16
           -- info-VALUE:   0..65535
           -- info-COMMENT: used with TrVplCcDeletion
           -- info-IMPL:    V1.1U->
           SYNTAX        Unsigned16
           ACCESS        not-accessible
           STATUS        mandatory
           DESCRIPTION
                 "used with TrVplCcDeletio."
           ::= { xldv11TrapVars 66 }

        xldv11TvEthVplTpIndex OBJECT-TYPE
           -- info-LEAF:    xldv11TvEthVplTpIndex 
           -- info-TREE:    xldv11Traps
           -- info-ACC:     nac
           -- info-SYNTAX:  Unsigned16
           -- info-VALUE:   0..65535
           -- info-COMMENT: used with TrVplCcDeletion
           -- info-IMPL:    V1.1U->
           SYNTAX        Unsigned16
           ACCESS        not-accessible
           STATUS        mandatory
           DESCRIPTION
                 "used with TrVplCcDeletio."
           ::= { xldv11TrapVars 67 }

        xldv11TvEthEntryIndex OBJECT-TYPE
           -- info-LEAF:    xldv11TvEthEntryIndex
           -- info-TREE:    xldv11Traps
           -- info-ACC:     nac
           -- info-SYNTAX:  Unsigned16
           -- info-VALUE:   0..65535
           -- info-COMMENT: used with TrVplCcDeletion
           -- info-IMPL:    V1.1U->
           SYNTAX        Unsigned16
           ACCESS        not-accessible
           STATUS        mandatory
           DESCRIPTION
                 "used with TrVplCcDeletion."
           ::= { xldv11TrapVars 68 }

         xldv11TvRepEntityExt OBJECT-TYPE
            -- info-LEAF:    xldv11TvRepEntityExt
            -- info-TREE:    xldv11Traps
            -- info-ACC:     nac
            -- info-SYNTAX:  Integer32
            -- info-VALUE:   -2147483648..2147483647
            -- info-COMMENT: range: xldv11HwUnitIndex (HWM) or
            -- info-COMMENT: xldv11IfIndex (TLM) or range of Callp objects.
            -- info-IMPL:    V1.0->
            SYNTAX        Integer32
            ACCESS        not-accessible
            STATUS        mandatory
            DESCRIPTION
                 " The hardware unit index (HWM) or interface index (TLM)
                   or index of CallP reporting ext. entities. "
            ::= { xldv11TrapVars 69 }

         xldv11TvTelnetSessionUser OBJECT-TYPE
            -- info-LEAF:    xldv11TvTelnetSessionUser
            -- info-TREE:    xldv11Traps
            -- info-ACC:     nac
            -- info-SYNTAX:  DisplayString (SIZE (0..20))
            -- info-VALUE:   string: Telnet User Name.
            -- info-COMMENT: Used within xldv11TrTelnetSession.
            -- info-IMPL:    V1.3B->
            SYNTAX        DisplayString (SIZE (0..20))
            ACCESS        not-accessible
            STATUS        mandatory
            DESCRIPTION
                 " The Name of the currently logged in used."
            ::= { xldv11TrapVars 70 }
                
         xldv11TvCvpIndexSource OBJECT-TYPE
            -- info-LEAF:    xldv11TvCvpIndexSource
            -- info-TREE:    xldv11Traps
            -- info-ACC:     nac
            -- info-SYNTAX:  Unsigned16
            -- info-VALUE:   0..65535
            -- info-COMMENT: index of Xldv11ContinuityCheckVplTpEntry for COC source
            -- info-IMPL:    V1.3B->
            SYNTAX        Unsigned16
            ACCESS        not-accessible
            STATUS        mandatory
            DESCRIPTION
                 " Index of a Xldv11ContinuityCheckVplEntry for a source
                 of continuity check cells."
            ::= { xldv11TrapVars 71 }

         xldv11TvCvpIndexSink OBJECT-TYPE
            -- info-LEAF:    xldv11TvCvpIndexSink
            -- info-TREE:    xldv11Traps
            -- info-ACC:     nac
            -- info-SYNTAX:  Unsigned16
            -- info-VALUE:   0..65535
            -- info-COMMENT: index of Xldv11ContinuityCheckVplTpEntry for COC sink
            -- info-IMPL:    V1.3B->
            SYNTAX        Unsigned16
            ACCESS        not-accessible
            STATUS        mandatory
            DESCRIPTION
                 " Index of a Xldv11ContinuityCheckVplEntry for a sink
                 of continuity check cells."
            ::= { xldv11TrapVars 72 }

         xldv11TvCvcIndexSource OBJECT-TYPE
            -- info-LEAF:    xldv11TvCvcIndexSource
            -- info-TREE:    xldv11Traps
            -- info-ACC:     nac
            -- info-SYNTAX:  Unsigned16
            -- info-VALUE:   0..65535
            -- info-COMMENT: index of Xldv11ContinuityCheckVclTpEntry for COC source
            -- info-IMPL:    V1.3B->
            SYNTAX        Unsigned16
            ACCESS        not-accessible
            STATUS        mandatory
            DESCRIPTION
                 " Index of a Xldv11ContinuityCheckVclTpEntry for a source
                 of continuity check cells."
            ::= { xldv11TrapVars 73 }

         xldv11TvCvcIndexSink OBJECT-TYPE
            -- info-LEAF:    xldv11TvCvcIndexSink
            -- info-TREE:    xldv11Traps
            -- info-ACC:     nac
            -- info-SYNTAX:  Unsigned16
            -- info-VALUE:   0..65535
            -- info-COMMENT: index of Xldv11ContinuityCheckVclTpEntry for COC sink
            -- info-IMPL:    V1.3B->
            SYNTAX        Unsigned16
            ACCESS        not-accessible
            STATUS        mandatory
            DESCRIPTION
                 " Index of a Xldv11ContinuityCheckVclTpEntry for a sink
                 of continuity check cells."
            ::= { xldv11TrapVars 74 }

         xldv11TvRestoreResult OBJECT-TYPE
            -- info-LEAF:    xldv11TvRestoreResult
            -- info-TREE:    xldv11Traps
            -- info-ACC:     nac
            -- info-SYNTAX:  INTEGER
            -- info-VALUE:   restoreOk(1060),restoreFailed(1061),
            -- info-VALUE:   ftpAccessFailed(1062), dbWriteFailed(1063),
            -- info-VALUE:   localBackupFileFaulty(1064), remoteBackupFileFaulty(1065)
            -- info-COMMENT: -
            -- info-IMPL:    V1.2A->
            SYNTAX        INTEGER{
	                     restoreOk(1060),
			     restoreFailed(1061),
			     ftpAccessFailed(1062),
			     dbWriteFailed(1063),
			     localBackupFileFaulty(1064),
			     remoteBackupFileFaulty(1065)
			     }
            ACCESS        not-accessible
            STATUS        mandatory
            DESCRIPTION
                 " The result of the DB restoration after reload. "
            ::= { xldv11TrapVars 75 }

         -- --------------------------------------------------------------
         --                    Trap types group
         -- --------------------------------------------------------------
 
         xldv11TrapTypes OBJECT IDENTIFIER ::= { xldv11Traps 2 }
            -- info-NODE:      xldv11TrapTypes
            -- info-TREE:      xldv11Traps
            -- info-ACC:       nac
            -- info-IMPL:      V1.0->

         -- Note that XLDV1.1 inherits all traps from XLDV1.0.
         --

         -- Alarm Trap (Introduced for XLDV1.0) 
         xldv11TrHpExcBER TRAP-TYPE
            -- info-LEAF:      xldv11TrHpExcBER
            -- info-TREE:      xldv11Traps
            -- info-TRAPTYPE:  alarm
            -- info-TRAPID:    1
            -- info-TRAPVAR:   alarm list:
            -- info-TRAPVAR:   xldv11TvTimeAndDate, xldv11TvRepEntity
            -- info-TRAPVAR:   xldv11TvRepSource,xldv11TvAlmSpecProblem
            -- info-TRAPVAR:   xldv11TvAlmNatureOfAlarm, xldv11TvAlmFailedComponent
            -- info-TRAPVAR:   xldv11TvAlmFailedComponentRepSource
            -- info-TRAPVAR:   xldv11TvAlmSeverityOfFailure
            -- info-TRAPVAR:   xldv11TvAlmStatus,xldv11TvAlmPropRepairAction
            -- info-COMMENT:   Excessive bit error rate at high order path. 
            -- info-FAILEDSRC: tlm
            -- info-FAILEDOBJ: S1n(= STM-1 NePPTP),S3n
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Excessive bit error rate at high order path. "
            ::= 1

         -- Alarm Trap (Introduced for XLDV1.0) 
         xldv11TrHpUNEQ TRAP-TYPE
            -- info-LEAF:      xldv11TrHpUNEQ
            -- info-TREE:      xldv11Traps
            -- info-TRAPTYPE:  alarm
            -- info-TRAPID:    2
            -- info-TRAPVAR:   alarm list
            -- info-COMMENT:   Unequipped at higher order path. 
            -- info-FAILEDSRC: tlm
            -- info-FAILEDOBJ: S1n(= STM-1 NePPTP),S3n,E3n
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Unequipped at higher order path. "
            ::= 2

         -- Alarm Trap (Introduced for XLDV1.0) 
         xldv11TrLcd TRAP-TYPE
            -- info-LEAF:      xldv11TrLcd
            -- info-TREE:      xldv11Traps
            -- info-TRAPTYPE:  alarm
            -- info-TRAPID:    3
            -- info-TRAPVAR:   alarm list
            -- info-COMMENT:   Loss of cell delineation.
            -- info-FAILEDSRC: tlm
            -- info-FAILEDOBJ: Tca
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Loss of cell delineation. "
            ::= 3

         -- Alarm Trap (Introduced for XLDV1.0) 
         xldv11TrLof TRAP-TYPE
            -- info-LEAF:      xldv11TrLof
            -- info-TREE:      xldv11Traps
            -- info-TRAPTYPE:  alarm
            -- info-TRAPID:    4
            -- info-TRAPVAR:   alarm list
            -- info-COMMENT:   Los of frame.
            -- info-FAILEDOBJ: S1n(= STM-1 NePPTP),S3n,E3n,D3n,
            -- info-FAILEDOBJ: Pon,Adc(= Adc-PPTP),Adr,Vdc,Vdr,
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Los of frame. "
            ::= 4

         -- Alarm Trap (Introduced for XLDV1.0) 
         xldv11TrLop TRAP-TYPE
            -- info-LEAF:      xldv11TrLop
            -- info-TREE:      xldv11Traps
            -- info-TRAPTYPE:  alarm
            -- info-TRAPID:    5
            -- info-TRAPVAR:   alarm list
            -- info-COMMENT:   Loss of pointer.
            -- info-FAILEDSRC: tlm 
            -- info-FAILEDOBJ: S1n(= STM-1 NePPTP),S3n
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Loss of pointer. "
            ::= 5

         -- Alarm Trap (Introduced for XLDV1.0) 
         xldv11TrLos TRAP-TYPE
            -- info-LEAF:      xldv11TrLos
            -- info-TREE:      xldv11Traps
            -- info-TRAPTYPE:  alarm
            -- info-TRAPID:    6
            -- info-TRAPVAR:   alarm list
            -- info-COMMENT:   Loss of signal. 
            -- info-FAILEDSRC: tlm
            -- info-FAILEDOBJ: S1n(= STM-1 NePPTP),S3n,E3n,D3n
            -- info-FAILEDOBJ: Pon,Adc(= Adc-PPTP),Adr,Vdc,Vdr
            -- info-FAILEDOBJ: Ibm(= Ibm-PPTP),Eth
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Loss of signal. "
            ::= 6

         -- Alarm Trap (Introduced for XLDV1.0) 
         xldv11TrMsAIS TRAP-TYPE
            -- info-LEAF:      xldv11TrMsAIS
            -- info-TREE:      xldv11Traps
            -- info-TRAPTYPE:  alarm
            -- info-TRAPID:    7
            -- info-TRAPVAR:   alarm list
            -- info-COMMENT:   Alarm indication signal at multiplexer section.
            -- info-FAILEDSRC: tlm
            -- info-FAILEDOBJ: S1n(= STM-1 NePPTP),S3n
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Alarm indication signal at multiplexer section. "
            ::= 7

         -- Alarm Trap (Introduced for XLDV1.0) 
         xldv11TrMsExcBER TRAP-TYPE
            -- info-LEAF:      xldv11TrMsExcBER
            -- info-TREE:      xldv11Traps
            -- info-TRAPTYPE:  alarm
            -- info-TRAPID:    8
            -- info-TRAPVAR:   alarm list
            -- info-COMMENT:   Excessive bit error rate at multiplexer section.
            -- info-FAILEDSRC: tlm
            -- info-FAILEDOBJ: S1n(= STM-1 NePPTP),S3n
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Excessive bit error rate at multiplexer section. "
            ::= 8

         -- Alarm Trap (Introduced for XLDV1.0) 
         xldv11TrMsRDI TRAP-TYPE
            -- info-LEAF:      xldv11TrMsRDI
            -- info-TREE:      xldv11Traps
            -- info-TRAPTYPE:  alarm
            -- info-TRAPID:    9
            -- info-TRAPVAR:   alarm list
            -- info-COMMENT:   Remote defect indication at multiplexer section. 
            -- info-FAILEDSRC: tlm
            -- info-FAILEDOBJ: S1f(= STM-1 FePPTP),S3f
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Remote defect indication at multiplexer section. "
            ::= 9

         -- Alarm Trap (Introduced for XLDV1.0) 
         xldv11TrMsSD TRAP-TYPE
            -- info-LEAF:      xldv11TrMsSD
            -- info-TREE:      xldv11Traps
            -- info-TRAPTYPE:  alarm
            -- info-TRAPID:    10
            -- info-TRAPVAR:   alarm list
            -- info-COMMENT:   Signal degrade at multiplexer section. 
            -- info-FAILEDSRC: tlm
            -- info-FAILEDOBJ: S1n(= STM-1 NePPTP),S3n
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Signal degrade at multiplexer section. "
            ::= 10

         -- Alarm Trap (Introduced for XLDV1.0) 
         xldv11TrPAIS TRAP-TYPE
            -- info-LEAF:      xldv11TrPAIS
            -- info-TREE:      xldv11Traps
            -- info-TRAPTYPE:  alarm
            -- info-TRAPID:    11
            -- info-TRAPVAR:   xldv11TvTrapVar1, xldv11TvTrapVar2
            -- info-COMMENT:   Alarm indication signal at path.
            -- info-FAILEDSRC: tlm
            -- info-FAILEDOBJ: S1n(= STM-1 NePPTP),S3n
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Alarm indication signal at path. "
            ::= 11

         -- Alarm Trap (Introduced for XLDV1.0) 
         xldv11TrPRDI TRAP-TYPE
            -- info-LEAF:      xldv11TrPRDI
            -- info-TREE:      xldv11Traps
            -- info-TRAPTYPE:  alarm
            -- info-TRAPID:    12
            -- info-TRAPVAR:   alarm list
            -- info-COMMENT:   Remote defect indication at path.
            -- info-FAILEDSRC: tlm
            -- info-FAILEDOBJ: S1f(= STM-1 FePPTP),S3f
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Remote defect indication at path. "
            ::= 12

         -- Alarm Trap (Introduced for XLDV1.0) 
         xldv11TrRsExcBER TRAP-TYPE
            -- info-LEAF:      xldv11TrRsExcBER
            -- info-TREE:      xldv11Traps
            -- info-TRAPTYPE:  alarm
            -- info-TRAPID:    13
            -- info-TRAPVAR:   xldv11TvTrapVar1, xldv11TvTrapVar2
            -- info-COMMENT:   Excessive bit error rate at repeater section.
            -- info-FAILEDSRC: tlm
            -- info-FAILEDOBJ: S1n(= STM-1 NePPTP),S3n
            -- info-IMPL:    [V1.0,V1.1U,V1.2A,V1.2B,V1.3A,V1.3B/[rw,ro,*]
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Excessive bit error rate at repeater section. "
            ::= 13

         -- Alarm Trap (Introduced for XLDV1.0) 
         xldv11TrSlm TRAP-TYPE
            -- info-LEAF:      xldv11TrSlm
            -- info-TREE:      xldv11Traps
            -- info-TRAPTYPE:  alarm
            -- info-TRAPID:    14
            -- info-TRAPVAR:   alarm list
            -- info-COMMENT:   Signal label mismatch.
            -- info-FAILEDSRC: tlm
            -- info-FAILEDOBJ: S1n(= STM-1 NePPTP),S3n,E3n
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Signal label mismatch. "
            ::= 14

         -- Alarm Trap (Introduced for XLDV1.0) 
         xldv11TrTim TRAP-TYPE
            -- info-LEAF:      xldv11TrTim
            -- info-TREE:      xldv11Traps
            -- info-TRAPTYPE:  alarm
            -- info-TRAPID:    15
            -- info-TRAPVAR:   alarm list
            -- info-COMMENT:   Trace identification mismatch.
            -- info-FAILEDSRC: tlm
            -- info-FAILEDOBJ: S1n(= STM-1 NePPTP),S3n,E3n
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Trace identification mismatch. "
            ::= 15

         -- Alarm Trap (Introduced for XLDV1.0) 
         xldv11TrActFault TRAP-TYPE
            -- info-LEAF:      xldv11TrActFault
            -- info-TREE:      xldv11Traps
            -- info-TRAPTYPE:  alarm
            -- info-TRAPID:    16
            -- info-TRAPVAR:   alarm list
            -- info-COMMENT:   The ADSL C PPTP reports a link activation fault.
            -- info-FAILEDSRC: tlm
            -- info-FAILEDOBJ: Adc(= Adc-PPTP)
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                  " The ADSL C PPTP reports a link activation fault. "
            ::= 16

         -- Alarm Trap (Introduced for XLDV1.0) 
         xldv11TrReplaceableUnitTypeMismatch TRAP-TYPE
            -- info-LEAF:      xldv11TrReplaceableUnitTypeMismatch
            -- info-TREE:      xldv11Traps
            -- info-TRAPTYPE:  alarm
            -- info-TRAPID:    17
            -- info-TRAPVAR:   alarm list
            -- info-COMMENT:   Trap to indicate that a wrong unit is plugged.
            -- info-FAILEDSRC: hwm
            -- info-FAILEDOBJ: LU155,LUDSX3,LUPON,CMU,SUAD,SUVD,LTAD,
            -- info-FAILEDOBJ: LIETH,LI25,NTAD,NTVD
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                  " Trap to indicate that a wrong unit is plugged. "
            ::= 17

         -- Alarm Trap (Introduced for XLDV1.0) 
         xldv11TrReplaceableUnitFailure TRAP-TYPE
            -- info-LEAF:      xldv11TrReplaceableUnitFailure
            -- info-TREE:      xldv11Traps
            -- info-TRAPTYPE:  alarm
            -- info-TRAPID:    18
            -- info-TRAPVAR:   alarm list
            -- info-COMMENT:   Indicates a unit Out Of Service.
            -- info-FAILEDSRC: hwm
            -- info-FAILEDOBJ: LU155,LUDSX3,LUPON,CMU,SUAD,SUVD,LTAD,
            -- info-FAILEDOBJ: LIETH,LI25,NTAD,NTVD
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                  " Indicates a unit Out Of Service. "
            ::= 18

         -- Alarm Trap (Introduced for XLDV1.0) 
         xldv11TrReplaceableUnitProblem TRAP-TYPE
            -- info-LEAF:      xldv11TrReplaceableUnitProblem
            -- info-TREE:      xldv11Traps
            -- info-TRAPTYPE:  alarm
            -- info-TRAPID:    19
            -- info-TRAPVAR:   alarm list
            -- info-COMMENT:   Indicates a unit partly Out Of Service.
            -- info-FAILEDSRC: hwm
            -- info-FAILEDOBJ: LU155,LUDSX3,LUPON,CMU,SUAD,SUVD,LTAD,
            -- info-FAILEDOBJ: LIETH,LI25,NTAD,NTVD,
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                  " Indicates a unit partly Out Of Service. "
            ::= 19

         -- Alarm Trap (Introduced for XLDV1.0) 
         xldv11TrReplaceableUnitNotInstalled TRAP-TYPE
            -- info-LEAF:      xldv11TrReplaceableUnitNotInstalled
            -- info-TREE:      xldv11Traps
            -- info-TRAPTYPE:  alarm
            -- info-TRAPID:    20
            -- info-TRAPVAR:   alarm list
            -- info-COMMENT:   Indicates that the unit is not plugged.
            -- info-FAILEDSRC: hwm
            -- info-FAILEDOBJ: LU155,LUDSX3,LUPON,CMU,SUAD,SUVD,LTAD,
            -- info-FAILEDOBJ: LIETH,LI25,NTAD,NTVD
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                  " Indicates that the unit is not plugged. "
            ::= 20

         -- Alarm Trap (Introduced for XLDV1.0) 
         xldv11TrReplaceableUnitSwMismatch TRAP-TYPE
            -- info-LEAF:      xldv11TrReplaceableUnitSwMismatch
            -- info-TREE:      xldv11Traps
            -- info-TRAPTYPE:  alarm
            -- info-TRAPID:    21
            -- info-TRAPVAR:   alarm list
            -- info-COMMENT:   The SW version in the inventory data mismatches with the
            -- info-COMMENT:   configured version in the equipment holder.
            -- info-FAILEDSRC: hwm
            -- info-FAILEDOBJ: LU155,LUDSX3,LUPON,CMU,SUAD,SUVD,LTAD,
            -- info-FAILEDOBJ: LIETH,LI25,NTAD,NTVD
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                  " The SW version in the inventory data mismatches with the
                    configured version in the equipment holder. "
            ::= 21

         -- Event Trap (Introduced for XLDV1.0) 
         xldv11TrReplaceableUnitReset TRAP-TYPE
            -- info-LEAF:      xldv11TrReplaceableUnitReset
            -- info-TREE:      xldv11Traps
            -- info-TRAPTYPE:  event
            -- info-TRAPID:    22
            -- info-TRAPVAR:   xldv11TvTimeAndDate, xldv11TvRepEntity
            -- info-TRAPVAR:   xldv11TvRepSource, xldv11TvHweResetType 
            -- info-COMMENT:   A replaceable unit is performing a reset.
            -- info-IMPL:      V1.0->
            ENTERPRISE xldv11Traps
            VARIABLES { xldv11TvTimeAndDate,
                        xldv11TvRepEntity,
                        xldv11TvRepSource,
                        xldv11TvHweResetType }
            DESCRIPTION
                 " A replaceable unit is performing a reset. "
            ::= 22

         -- Event Trap (Introduced for XLDV1.0) 
         xldv11TrReplaceableUnitResetEnd TRAP-TYPE
            -- info-LEAF:     xldv11TrReplaceableUnitResetEnd
            -- info-TREE:     xldv11Traps
            -- info-TRAPTYPE: event
            -- info-TRAPID:   23
            -- info-TRAPVAR:  xldv11TvTimeAndDate,xldv11TvRepEntity
            -- info-TRAPVAR:  xldv11TvRepSource
            -- info-COMMENT:  A replaceable unit finished a reset.
            -- info-IMPL:     V1.0->
            ENTERPRISE xldv11Traps
            VARIABLES { xldv11TvTimeAndDate,
                        xldv11TvRepEntity,
                        xldv11TvRepSource }
            DESCRIPTION
                 " A replaceable unit finished a reset. "
            ::= 23

         -- Event Trap (Introduced for XLDV1.0) 
         xldv11TrStartupEnd TRAP-TYPE
            -- info-LEAF:     xldv11TrStartupEnd
            -- info-TREE:     xldv11Traps
            -- info-TRAPTYPE: event
            -- info-TRAPID:   24
            -- info-TRAPVAR:  xldv11TvTimeAndDate,xldv11TvStartupResult
            -- info-TRAPVAR:  xldv11TvStartupType,xldv11TvSnmMibVersion
            -- info-TRAPVAR:  xldv11TvSnmAgentVersion, xldv11TvVersionNrCmuLoad
            -- info-COMMENT:  Trap ID must not be changed, because it 
            -- info-COMMENT:  must be the same for all XLD ONUs.
            -- info-IMPL:     V1.0->
            ENTERPRISE xldv11Traps
            VARIABLES { xldv11TvTimeAndDate,
                        xldv11TvStartupResult,
                        xldv11TvStartupType,
                        xldv11TvSnmMibVersion,
                        xldv11TvSnmAgentVersion,
                        xldv11TvVersionNrCmuLoad }
            DESCRIPTION
                 " End of startup. "
            ::= 24

         -- Event Trap (Introduced for XLDV1.0) 
         xldv11TrLctSession TRAP-TYPE
            -- info-LEAF:     xldv11TrLctSession
            -- info-TREE:     xldv11Traps
            -- info-TRAPTYPE: event
            -- info-TRAPID:   25
            -- info-TRAPVAR:  xldv11TvTimeAndDate,xldv11TvSnmLctSession
            -- info-COMMENT:  Signalizes events concerning a
            -- info-COMMENT:  LCT session
            -- info-IMPL:     V1.0->
            ENTERPRISE xldv11Traps
            VARIABLES { xldv11TvTimeAndDate,
                        xldv11TvSnmLctSession }
            DESCRIPTION
                 " Event concerning a LCT session . "
            ::= 25

         -- Event Trap (Introduced for XLDV1.0) 
         xldv11TrSnmAgentRunning TRAP-TYPE
            -- info-LEAF:     xldv11TrSnmAgentRunning
            -- info-TREE:     xldv11Traps
            -- info-TRAPTYPE: event
            -- info-TRAPID:   26
            -- info-TRAPVAR:  xldv11TvTimeAndDate,xldv11TvSnmMibVersion
            -- info-TRAPVAR:  xldv11TvSnmAgentVersion 
            -- info-COMMENT:  Trap ID must not be changed, because it 
            -- info-COMMENT:  must be the same for all XLD ONUs.
            -- info-IMPL:     V1.0->
            ENTERPRISE xldv11Traps
            VARIABLES { xldv11TvTimeAndDate,
                        xldv11TvSnmMibVersion,
                        xldv11TvSnmAgentVersion }
            DESCRIPTION
                 " SNMP agent is active now. "
            ::= 26

         -- Event Trap (Introduced for XLDV1.0) 
         xldv11TrRstResult TRAP-TYPE
            -- info-LEAF:     xldv11TrRstResult
            -- info-TREE:     xldv11Traps
            -- info-TRAPTYPE: event
            -- info-TRAPID:   27
            -- info-TRAPVAR:  xldv11TvTimeAndDate,xldv11TvRstResult
            -- info-TRAPVAR:  xldv11TvRepSource,xldv11TvRstHwUnitIndex
            -- info-COMMENT:  Result of reset.
            -- info-IMPL:     V1.0->
            ENTERPRISE xldv11Traps
            VARIABLES { xldv11TvTimeAndDate,
                        xldv11TvRstResult,
                        xldv11TvRepSource,
                        xldv11TvRstHwUnitIndex }
            DESCRIPTION
                 " Result of reset. "
            ::= 27

         -- Event Trap (Introduced for XLDV1.3N) 
         xldv11TrPltTestResult TRAP-TYPE
            -- info-LEAF:     xldv11TrPltTestResult
            -- info-TREE:     xldv11Traps
            -- info-TRAPTYPE: event
            -- info-TRAPID:   28
            -- info-TRAPVAR:  xldv11TvTimeAndDate,xldv11TvTsrControlStatus
            -- info-COMMENT:  Result of physical loop test.
            -- info-IMPL:     V1.3N->
            ENTERPRISE xldv11Traps
            VARIABLES { xldv11TvTimeAndDate,
                        xldv11TvTsrControlStatus }
            DESCRIPTION
                 " Result of physical loop test. "
            ::= 28

         -- Event Trap (Introduced for XLDV1.0) 
         xldv11TrStateChangeAdmin TRAP-TYPE
            -- info-LEAF:     xldv11TrStateChangeAdmin
            -- info-TREE:     xldv11Traps
            -- info-TRAPTYPE: event
            -- info-TRAPID:   29
            -- info-TRAPVAR:  xldv11TvTimeAndDate,xldv11TvRepEntity
            -- info-TRAPVAR:  xldv11TvRepSource,xldv11TvStcOldAdminStatus
            -- info-TRAPVAR:  xldv11TvStcNewAdminStatus
            -- info-COMMENT:  The administrative state of the
            -- info-COMMENT:  reporting entity has changed.
            -- info-IMPL:     V1.0->
            ENTERPRISE xldv11Traps
            VARIABLES { xldv11TvTimeAndDate,
                        xldv11TvRepEntity,
                        xldv11TvRepSource,
                        xldv11TvStcOldAdminStatus,
                        xldv11TvStcNewAdminStatus }
            DESCRIPTION
                 " The administrative state of the reporting entity
                   has changed. "
            ::= 29

         -- Event Trap (Introduced for XLDV1.0) 
         xldv11TrStateChangeOper TRAP-TYPE
            -- info-LEAF:     xldv11TrStateChangeOper
            -- info-TREE:     xldv11Traps
            -- info-TRAPTYPE: event
            -- info-TRAPID:   30
            -- info-TRAPVAR:  xldv11TvTimeAndDate,xldv11TvRepEntity
            -- info-TRAPVAR:  xldv11TvRepSource,xldv11TvStcOldOperStatus
            -- info-TRAPVAR:  xldv11TvStcNewOperStatus
            -- info-COMMENT:  The operational state of the
            -- info-COMMENT:  reporting entity has changed.
            -- info-IMPL:     V1.0->
            ENTERPRISE xldv11Traps
            VARIABLES { xldv11TvTimeAndDate,
                        xldv11TvRepEntity,
                        xldv11TvRepSource,
                        xldv11TvStcOldOperStatus,
                        xldv11TvStcNewOperStatus }
            DESCRIPTION
                 " The operational state of the reporting entity
                   has changed. "
            ::= 30

         -- Event Trap (Introduced for XLDV1.0) 
         xldv11TrChangeRate TRAP-TYPE
            -- info-LEAF:     xldv11TrChangeRate
            -- info-TREE:     xldv11Traps
            -- info-TRAPTYPE: event
            -- info-TRAPID:   31
            -- info-TRAPVAR:  xldv11TvTimeAndDate,xldv11TvAdcControlStatus
            -- info-TRAPVAR:  xldv11TvRepEntity,xldv11TvRepSource
            -- info-COMMENT:  This trap indicates the end of
            -- info-COMMENT:  change rate request.
            -- info-IMPL:     V1.0->
            ENTERPRISE xldv11Traps
            VARIABLES { xldv11TvTimeAndDate,
                        xldv11TvAdcControlStatus,
                        xldv11TvRepEntity,
                        xldv11TvRepSource }
            DESCRIPTION
                 " This trap indicates the end of change rate request. "
            ::= 31

         -- Event Trap (Introduced for XLDV1.0) 
         xldv11TrCmuReadyForReset TRAP-TYPE
            -- info-LEAF:     xldv11TrCmuReadyForReset
            -- info-TREE:     xldv11Traps
            -- info-TRAPTYPE: event
            -- info-TRAPID:   32
            -- info-TRAPVAR:  xldv11TvTimeAndDate
            -- info-COMMENT:  Indicates upgrade end;
            -- info-COMMENT:  Unit is ready for reset.
            -- info-IMPL:     V1.0->
            ENTERPRISE xldv11Traps
            VARIABLES { xldv11TvTimeAndDate }
            DESCRIPTION
                " Indicates upgrade end. Unit is ready for reset. "
            ::= 32
 
         -- Event Trap (Introduced for XLDV1.3N)  
         xldv11TrAltTestResult TRAP-TYPE
            -- info-LEAF:     xldv11TrAltTestResult
            -- info-TREE:     xldv11Traps
            -- info-TRAPTYPE: event
            -- info-TRAPID:   33
            -- info-TRAPVAR:  xldv11TvTimeAndDate,xldv11TvTsrControlStatus
            -- info-COMMENT:  Result of physical loop test.
            -- info-IMPL:     V1.3N->
            ENTERPRISE xldv11Traps
            VARIABLES { xldv11TvTimeAndDate,
                        xldv11TvTsrControlStatus }
            DESCRIPTION
                 " Result of ATM loop test. "
            ::= 33

         -- Event Trap (Introduced for XLDV1.0) 
         xldv11TrActivateLoadResult TRAP-TYPE
            -- info-LEAF:     xldv11TrActivateLoadResult
            -- info-TREE:     xldv11Traps
            -- info-TRAPTYPE: event
            -- info-TRAPID:   34
            -- info-TRAPVAR:  xldv11TvTimeAndDate,xldv11TvSucResult
            -- info-TRAPVAR:  xldv11TvSucUnit,xldv11TvSucHwUnitIndex
            -- info-COMMENT:  This trap indicates that a
            -- info-COMMENT:  replaceable unit is performing a reset.
            -- info-IMPL:     V1.0->
            ENTERPRISE xldv11Traps
            VARIABLES { xldv11TvTimeAndDate,
                        xldv11TvSucResult,
                        xldv11TvSucUnit,
                        xldv11TvSucHwUnitIndex }
            DESCRIPTION
                  " This trap indicates that a replaceable unit is performing
                    a reset. "
            ::= 34

         -- Event Trap (Introduced for XLDV1.0) 
         xldv11TrPuUpgradeSucc TRAP-TYPE
            -- info-LEAF:     xldv11TrPuUpgradeSucc
            -- info-TREE:     xldv11Traps
            -- info-TRAPTYPE: event
            -- info-TRAPID:   35
            -- info-TRAPVAR:  xldv11TvTimeAndDate,xldv11TvSucUnit
            -- info-TRAPVAR:  xldv11TvSucHwUnitIndex,xldv11TvSucVersionNo
            -- info-COMMENT:  Upgrade ended successfully.
            -- info-IMPL:     V1.0->
            ENTERPRISE xldv11Traps
            VARIABLES { xldv11TvTimeAndDate,
                        xldv11TvSucUnit,
                        xldv11TvSucHwUnitIndex,
                        xldv11TvSucVersionNo }
            DESCRIPTION
                 " Upgrade ended successfully. "
            ::= 35

         -- Event Trap (Introduced for XLDV1.0) 
         xldv11TrUpgradeCancelled TRAP-TYPE
            -- info-LEAF:     xldv11TrUpgradeCancelled
            -- info-TREE:     xldv11Traps
            -- info-TRAPTYPE: event
            -- info-TRAPID:   36
            -- info-TRAPVAR:  xldv11TvTimeAndDate,xldv11TvSucUnit
            -- info-TRAPVAR:  xldv11TvSucHwUnitIndex,xldv11TvSucVersionNo
            -- info-TRAPVAR:  xldv11TvSucResult
            -- info-COMMENT:  The upgrade request has been cancelled.
            -- info-IMPL:     V1.0->
            ENTERPRISE xldv11Traps
            VARIABLES { xldv11TvTimeAndDate,
                        xldv11TvSucUnit,
                        xldv11TvSucHwUnitIndex,
                        xldv11TvSucVersionNo,
                        xldv11TvSucResult }
            DESCRIPTION
                 " The upgrade request has been cancelled. "
            ::= 36

         -- Event Trap (Introduced for XLDV1.0) 
         xldv11TrFtpError TRAP-TYPE
            -- info-LEAF:     xldv11TrFtpError
            -- info-TREE:     xldv11Traps
            -- info-TRAPTYPE: event
            -- info-TRAPID:   38
            -- info-TRAPVAR:  xldv11TvTimeAndDate,xldv11TvSucUnit
            -- info-TRAPVAR:  xldv11TvSucPathName,xldv11TvSucFileName
            -- info-TRAPVAR:  xldv11TvSucResult
            -- info-COMMENT:  Sw upgrade reports a problem with FTP.
            -- info-IMPL:     V1.0->
            ENTERPRISE xldv11Traps
            VARIABLES { xldv11TvTimeAndDate,
                        xldv11TvSucUnit,
                        xldv11TvSucPathName,
                        xldv11TvSucFileName ,
                        xldv11TvSucResult }
            DESCRIPTION
                  " Sw upgrade reports a problem with FTP. "
            ::= 38

         -- Event Trap (Introduced for XLDV1.0) 
         xldv11TrSweLogRead TRAP-TYPE
            -- info-LEAF:     xldv11TrSweLogRead
            -- info-TREE:     xldv11Traps
            -- info-TRAPTYPE: event
            -- info-TRAPID:   40
            -- info-TRAPVAR:  xldv11TvTimeAndDate,xldv11TvDbuSweLogReadResult
            -- info-COMMENT:  End of SWE log reading.
            -- info-IMPL:     V1.0->
            ENTERPRISE xldv11Traps
            VARIABLES { xldv11TvTimeAndDate,
                        xldv11TvDbuSweLogReadResult }
            DESCRIPTION
                 " End of SWE log reading. "
            ::= 40

         -- Event Trap (Introduced for XLDV1.0) 
         xldv11TrHwmLogRead TRAP-TYPE
            -- info-LEAF:     xldv11TrHwmLogRead
            -- info-TREE:     xldv11Traps
            -- info-TRAPTYPE: event
            -- info-TRAPID:   41
            -- info-TRAPVAR:  xldv11TvTimeAndDate,xldv11TvDbuHwmLogReadResult
            -- info-COMMENT:  End of HWM log reading.
            -- info-IMPL:     V1.0->
            ENTERPRISE xldv11Traps
            VARIABLES { xldv11TvTimeAndDate,
                        xldv11TvDbuHwmLogReadResult }
            DESCRIPTION
                 " End of HWM log reading. "
            ::= 41

         -- Event Trap (Introduced for XLDV1.0) 
         xldv11TrTraceLogRead TRAP-TYPE
            -- info-LEAF:     xldv11TrTraceLogRead
            -- info-TREE:     xldv11Traps
            -- info-TRAPTYPE: event
            -- info-TRAPID:   42
            -- info-TRAPVAR:  xldv11TvTimeAndDate,xldv11TvDbuSwTraceLogReadResult
            -- info-COMMENT:  End of trace log reading.
            -- info-IMPL:     V1.0->
            ENTERPRISE xldv11Traps
            VARIABLES { xldv11TvTimeAndDate,
                        xldv11TvDbuSwTraceLogReadResult }
            DESCRIPTION
                 " End of trace log reading. "
            ::= 42

         -- MR OK000308: Add new Trap Id xldv11TrHiBER 
         -- Because of already defined V1.1U and V1.1 Trap Id's a gap resulted
         -- from the last trap xldv11TrActCcReload to the new defined trap
         -- xldv11TrHiBER.
         -- This trap, which is an alarm trap, indicates the defect "high bit error
         -- rate" for AdcPPTP.

         -- Alarm Trap (Introduced for XLDV1.0) 
         xldv11TrHiBER TRAP-TYPE
            -- info-LEAF:      xldv11TrHiBER
            -- info-TREE:      xldv11Traps
            -- info-TRAPTYPE:  alarm
            -- info-TRAPID:    43
            -- info-TRAPVAR:   alarm list
            -- info-COMMENT:   High Bit Error Rate for AdcPPTP. 
            -- info-FAILEDSRC: tlm
            -- info-FAILEDOBJ: Adc(= Adc-PPTP),Vdc,Vdr
            -- info-IMPL:      V1.0->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " High Bit Error Rate for AdcPPTP. "
            ::= 43

		 
         -- This trap delivers the resulting indeces of a VPC creation.
         -- The trap variables are xldv11TvTimeAndDate, the xldv11TvVpiNni value of
         -- the CC, the index xldv11TvVpiNniIndex belonging to the CC of the
         -- AtmCrossConnect Table and the indeces xldv11TvVplTerminationPointA and
         -- xldv11TvVplTerminationPointZ of the VPLs of the VPL table.

         -- Event Trap (Introduced for XLDV1.0)
            xldv11TrVplCcCreation TRAP-TYPE
               -- info-LEAF: xldv11TrVplCcCreation
               -- info-TREE: xldv11Traps
               -- info-TRAPTYPE: event
               -- info-TRAPID: 45
               -- info-TRAPVAR: xldv11TvTimeAndDate,xldv11TvVpiNni
               -- info-TRAPVAR: xldv11TvVpiNniIndex,xldv11TvVplTerminationPointA
               -- info-TRAPVAR: xldv11TvVplTerminationPointZ, xldv11TvEthVplTpindex
               -- info-COMMENT: VPL cross connect created.
               -- info-IMPL: V1.0->
               ENTERPRISE xldv11Traps
               VARIABLES { xldv11TvTimeAndDate,
                           xldv11TvVpiNni,
                           xldv11TvVpiNniIndex,
                           xldv11TvVplTerminationPointA,
                           xldv11TvVplTerminationPointZ,
                           xldv11TvEthVplTpIndex,
                           xldv11TvEthVpcTpIndex,
                           xldv11TvEthVccTpIndex }
               DESCRIPTION
                     " The resulting indeces of a VPC creation command.  "
               ::= 45

         -- This trap delivers the indeces of a CC, which was deleted.
         -- The trap variables are xldv11TvTimeAndDate, the xldv11TvVpiNni value of
         -- the deleted CC, the index xldv11TvVpiNniIndex belonging to the deleted
         -- CC of the AtmCrossConnect Table and the indeces xldv11TvVplTerminationPointA
         -- and xldv11TvVplTerminationPointZ of the deleted VPLs of the VPL table.

         -- Event Trap (Introduced for XLDV1.0) 
         xldv11TrVplCcDeletion TRAP-TYPE
            -- info-LEAF:     xldv11TrVplCcDeletion
            -- info-TREE:     xldv11Traps
            -- info-TRAPTYPE: event
            -- info-TRAPID:   46
            -- info-TRAPVAR:  xldv11TvTimeAndDate,xldv11TvVpiNni
            -- info-TRAPVAR:  xldv11TvVpiNniIndex,xldv11TvVplTerminationPointA
            -- info-TRAPVAR:  xldv11TvVplTerminationPointZ,xldv11TvVpcNniIndex
            -- info-TRAPVAR:  xldv11TvVpcUniIndex
            -- info-TRAPVAR:  xldv11TvEthVpcTpIndex, xldv11TvEthVccTpIndex
            -- info-TRAPVAR:  xldv11TvEthVplTpIndex, xldv11TvEthEntryIndex 
            -- info-COMMENT:  VPL cross connect deleted.
            -- info-IMPL:     V1.0->
            ENTERPRISE xldv11Traps
            VARIABLES { xldv11TvTimeAndDate,
                        xldv11TvVpiNni,
                        xldv11TvVpiNniIndex,
                        xldv11TvVplTerminationPointA,
                        xldv11TvVplTerminationPointZ,
                        xldv11TvEthVpcTpIndex,   
                        xldv11TvEthVccTpIndex,   
                        xldv11TvEthVplTpIndex,   
                        xldv11TvEthEntryIndex }   
            DESCRIPTION
                  " The resulting indeces of a VPC deletion command. "
            ::= 46

         -- Event Trap (Introduced for XLDV1.1U)        
         xldv11TrObjCreate TRAP-TYPE
            -- info-LEAF:     xldv11TrObjCreate
            -- info-TREE:     xldv11Traps
            -- info-TRAPTYPE: event
            -- info-TRAPID:   100
            -- info-TRAPVAR:  xldv11TvTimeAndDate,xldv11TvRepSource
            -- info-TRAPVAR:  xldv11TvRepEntity,xldv11TvHwUnitType
            -- info-TRAPVAR:  xldv11TvHwContainingUnitIndex,xldv11TvHwContainedUnitAddr
            -- info-COMMENT:  Sent for the created HWM of TLM objects 
            -- info-COMMENT:  during change of a HWM object type.
            -- info-COMMENT:  Par. xldv11TvRepSource = hwm or tlm.
            -- info-COMMENT:  Par. xldv11TvRepEntity = xldv11HwUnitIndex
            -- info-COMMENT:  or xldIfIndex.
            -- info-COMMENT:  if xldv11TvRepSource = hwm then:
            -- info-COMMENT:     valid parameters: xldv11TvHwUnitType,
            -- info-COMMENT:     xldv11TvHwContainingUnitIndex,
            -- info-COMMENT:     xldv11TvHwContainedUnitAddr
            -- info-COMMENT:  else: none 
            -- info-IMPL:     V1.1U->
            ENTERPRISE xldv11Traps
            VARIABLES { xldv11TvTimeAndDate,
                        xldv11TvRepSource,
                        xldv11TvRepEntity,
                        xldv11TvHwUnitType,
                        xldv11TvHwContainingUnitIndex,
                        xldv11TvHwContainedUnitAddr }
            DESCRIPTION
                 " Create object event.
                   The varBinds xldv11TvHwUnitType and xldv11TvHwContainingUnitIndex
                   only occure when xldv11TvRepSource = hwm. "
            ::= 100
 
         -- Event Trap (Introduced for XLDV1.1U)        
        xldv11TrObjDelete TRAP-TYPE
            -- info-LEAF:     xldv11TrObjDelete
            -- info-TREE:     xldv11Traps
            -- info-TRAPTYPE: event
            -- info-TRAPID:   101
            -- info-TRAPVAR:  xldv11TvTimeAndDate, xldv11TvRepSource,
            -- info-TRAPVAR:  xldv11TvRepEntity, xldv11TvHwUnitType,
            -- info-TRAPVAR:  xldv11TvHwContainingUnitIndex, xldv11TvHwContainedUnitAddr 
            -- info-COMMENT:  Sent for the deleted HWM of TLM objects 
            -- info-COMMENT:  during change of a HWM object type.
            -- info-COMMENT:  see xldv11TrObjCreate
            -- info-IMPL:      V1.1U->
            ENTERPRISE xldv11Traps
            VARIABLES { xldv11TvTimeAndDate,
                        xldv11TvRepSource,
                        xldv11TvRepEntity,
                        xldv11TvHwUnitType,
                        xldv11TvHwContainingUnitIndex,
                        xldv11TvHwContainedUnitAddr  }
            DESCRIPTION
                 " Delete object event.
                   The varBinds xldv11TvHwUnitType and xldv11TvHwContainingUnitIndex
                   only occure when xldv11TvRepSource = hwm. "
            ::= 101

         -- Alarm Trap (Introduced for XLDV1.1U)        
         xldv11TrLOMF TRAP-TYPE
            -- info-LEAF:      xldv11TrLOMF
            -- info-TREE:      xldv11Traps
            -- info-TRAPTYPE:  alarm
            -- info-TRAPID:    102
            -- info-TRAPVAR:   alarm list
            -- info-COMMENT:   Loss of multiple frame from LUPON:0.
            -- info-FAILEDSRC: tlm
            -- info-FAILEDOBJ: Pon
            -- info-IMPL:      V1.1U->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Loss of multiple frame from LUPON:O. "
            ::= 102

         -- Alarm Trap (Introduced for XLDV1.1L)        
         xldv11TrXmissionErr TRAP-TYPE
            -- info-LEAF:      xldv11TrXmissionErr
            -- info-TREE:      xldv11Traps
            -- info-TRAPTYPE:  alarm
            -- info-TRAPID:    105
            -- info-TRAPVAR:   alarm list
            -- info-COMMENT:   Transmission Error from LIETH:S.
            -- info-FAILEDSRC: tlm
            -- info-FAILEDOBJ: Eth
            -- info-IMPL:      V1.1U->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Transmission Error from LIETH:S. "
            ::= 105

         -- Alarm Trap (Introduced for XLDV1.1L)        
         xldv11TrVpcTpAIS TRAP-TYPE
            -- info-LEAF:      xldv11TrVpcTpAIS
            -- info-TREE:      xldv11Traps
            -- info-TRAPTYPE:  alarm
            -- info-TRAPID:    106
            -- info-TRAPVAR:   alarm list
            -- info-COMMENT:   VP alarm indication signal.
            -- info-FAILEDSRC: callp
            -- info-FAILEDOBJ:  VpcTP
            -- info-IMPL:      V1.2A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " VP alarm indication signal. "
            ::= 106

         -- Alarm Trap (Introduced for XLDV1.1L)        
         xldv11TrVpcTpRDI TRAP-TYPE
            -- info-LEAF:      xldv11TrVpcTpRDI
            -- info-TREE:      xldv11Traps
            -- info-TRAPTYPE:  alarm
            -- info-TRAPID:    107
            -- info-TRAPVAR:   alarm list
            -- info-COMMENT:   VP remote defect alarm indication.
            -- info-FAILEDSRC: callp
            -- info-FAILEDOBJ: VpcTP
            -- info-IMPL:      V1.2A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " VP remote defect alarm indication. "
            ::= 107

         -- Alarm Trap (Introduced for XLDV1.1L)        
         xldv11TrVccTpAIS TRAP-TYPE
            -- info-LEAF:      xldv11TrVccTpAIS
            -- info-TREE:      xldv11Traps
            -- info-TRAPTYPE:  alarm
            -- info-TRAPID:    108
            -- info-TRAPVAR:   alarm list
            -- info-COMMENT:   VC alarm indication signal.
            -- info-FAILEDSRC: callp
            -- info-FAILEDOBJ: VccTP
            -- info-IMPL:    [V1.0,V1.1U,V1.2A,V1.2B,V1.3A,V1.3B/[rw,ro,*]
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " VC alarm indication signal. "
            ::= 108

         -- Alarm Trap (Introduced for XLDV1.1L)        
         xldv11TrVccTpRDI TRAP-TYPE
            -- info-LEAF:      xldv11TrVccTpRDI
            -- info-TREE:      xldv11Traps
            -- info-TRAPTYPE:  alarm
            -- info-TRAPID:    109
            -- info-TRAPVAR:   alarm list
            -- info-COMMENT:   VC remote defect alarm indication.
            -- info-FAILEDSRC: callp
            -- info-FAILEDOBJ: VccTP
            -- info-IMPL:      V1.2A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " VC remote defect alarm indication. "
            ::= 109

         -- Alarm Trap (Introduced for XLDV1.1U)        
         xldv11TrExternalAlarm TRAP-TYPE
            -- info-LEAF:      xldv11TrExternalAlarm
            -- info-TREE:      xldv11Traps
            -- info-TRAPTYPE:  alarm
            -- info-TRAPID:    110
            -- info-TRAPVAR:   alarm list
            -- info-COMMENT:   External alarm.
            -- info-FAILEDSRC: hwm
            -- info-FAILEDOBJ: CMU
            -- info-IMPL:      V1.1U V1.3A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " External alarm. "
            ::= 110

         -- Event Trap (Introduced for XLDV1.1L)        
         -- This trap replaces the xldv11TrSuAd16ReadyForReset trap.
         xldv11TrUnitReadyForReset TRAP-TYPE
            -- info-LEAF:     xldv11TrUnitReadyForReset
            -- info-TREE:     xldv11Traps
            -- info-TRAPTYPE: event
            -- info-TRAPID:   111
            -- info-TRAPVAR:  xldv11TvTimeAndDate,xldv11TvSucUnit
            -- info-TRAPVAR:  xldv11TvSucHwUnitIndex,xldv11TvSucVersionNo
            -- info-COMMENT:  Indicates upgrade end. Unit is ready for reset.
            -- info-IMPL:     V1.1U->
            ENTERPRISE xldv11Traps
            VARIABLES { xldv11TvTimeAndDate,
                        xldv11TvSucUnit,
                        xldv11TvSucHwUnitIndex,
                        xldv11TvSucVersionNo }
            DESCRIPTION
                 " Indicates upgrade end. Unit is ready for reset. "
            ::= 111

         -- Event Trap (Introduced for XLDV1.1U)        
         xldv11TrHwuControl TRAP-TYPE
            -- info-LEAF:     xldv11TrHwuControl
            -- info-TREE:     xldv11Traps
            -- info-TRAPTYPE: event
            -- info-TRAPID:   112
            -- info-TRAPVAR:  xldv11TvTimeAndDate,xldv11TvRepSource
            -- info-TRAPVAR:  xldv11TvHwuControlResult
            -- info-COMMENT:  End of object create command.
            -- info-IMPL:     V1.1U->
            ENTERPRISE xldv11Traps
            VARIABLES { xldv11TvTimeAndDate,
                        xldv11TvRepSource,
                        xldv11TvHwuControlResult }
            DESCRIPTION
                 " End of xldv11HwuControlReq. "
            ::= 112

         -- Alarm Trap (Introduced for XLDV1.1U)        
         xldv11TrReplaceableUnitRemoved TRAP-TYPE
            -- info-LEAF:      xldv11TrReplaceableUnitRemoved
            -- info-TREE:      xldv11Traps
            -- info-TRAPTYPE:  alarm
            -- info-TRAPID:    113
            -- info-TRAPVAR:   alarm list
            -- info-COMMENT:   Replaceable unit removed.
            -- info-FAILEDSRC: hwm
            -- info-FAILEDOBJ: LU155,LUDSX3,LUPON,CMU,SUAD,SUVD,LTAD,
            -- info-FAILEDOBJ: LIETH,LI25,NTAD,NTVD,
            -- info-IMPL:      V1.1U->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Replaceable unit removed. "
            ::= 113

         -- Alarm Trap (Introduced for XLDV1.1) 
         xldv11TrAIS TRAP-TYPE
            -- info-LEAF:      xldv11TrAIS
            -- info-TREE:      xldv11Traps
            -- info-TRAPTYPE:  alarm
            -- info-TRAPID:    114
            -- info-TRAPVAR:   alarm list
            -- info-COMMENT:   Alarm indication signal at E3/DS3.
            -- info-FAILEDSRC: tlm
            -- info-FAILEDOBJ: E3n,D3n
            -- info-IMPL:      V1.3A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Alarm indication signal at E3/DS3. "
            ::= 114

         -- Alarm Trap (Introduced for XLDV1.1) 
         xldv11TrRDI TRAP-TYPE
            -- info-LEAF:      xldv11TrRDI
            -- info-TREE:      xldv11Traps
            -- info-TRAPTYPE:  alarm
            -- info-TRAPID:    115
            -- info-TRAPVAR:   alarm list
            -- info-COMMENT:   Remote defect indication at E3/DS3.
            -- info-FAILEDSRC: tlm
            -- info-FAILEDOBJ: D3f,E3f
            -- info-IMPL:      V1.3A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Remote defect indication at E3/DS3. "
            ::= 115

         -- Alarm Trap (Introduced for XLDV1.1) 
         xldv11TrPlcpLof TRAP-TYPE
            -- info-LEAF:      xldv11TrPlcpLof
            -- info-TREE:      xldv11Traps
            -- info-TRAPTYPE:  alarm
            -- info-TRAPID:    116
            -- info-TRAPVAR:   alarm list
            -- info-COMMENT:   Loss of Plcp frame at E3/DS3.
            -- info-FAILEDSRC: tlm
            -- info-FAILEDOBJ: D3n
            -- info-IMPL:      V1.3A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Loss of Plcp frame at E3/DS3. "
            ::= 116

         -- Alarm Trap (Introduced for XLDV1.1) 
         xldv11TrPlcpRDI TRAP-TYPE
            -- info-LEAF:      xldv11TrPlcpRDI
            -- info-TREE:      xldv11Traps
            -- info-TRAPTYPE:  alarm
            -- info-TRAPID:    117
            -- info-TRAPVAR:   alarm list
            -- info-COMMENT:   Plcp Remote defect indication at E3/DS3.
            -- info-FAILEDSRC: tlm
            -- info-FAILEDOBJ: D3f
            -- info-FAILEDOBJ: [callp] NePPTP, FePPTP,
            -- info-IMPL:      V1.3A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Plcp Remote defect indication at E3/DS3. "
            ::= 117

         -- Event Trap (Introduced for XLDV1.1) 
         xldv11TrRemInvReady TRAP-TYPE
            -- info-LEAF:     xldv11TrRemInvReady
            -- info-TREE:     xldv11Traps
            -- info-TRAPTYPE: event
            -- info-TRAPID:   118
            -- info-TRAPVAR:  xldv11TvTimeAndDate,xldv11TvRiRemInvResult
            -- info-COMMENT:  Result of Storage of DB. 
            -- info-IMPL:     V1.3B->
            ENTERPRISE xldv11Traps
            VARIABLES { xldv11TvTimeAndDate,
                        xldv11TvRiRemInvResult }
            DESCRIPTION
                 " Remote inventory ready. "
            ::= 118

         -- Event Trap (Introduced for XLDV1.1) 
         xldv11TrDbBackup TRAP-TYPE
            -- info-LEAF:     xldv11TrDbBackup
            -- info-TREE:     xldv11Traps
            -- info-TRAPTYPE: event
            -- info-TRAPID:   119
            -- info-TRAPVAR:  xldv11TvTimeAndDate,xldv11TvBackupResult
            -- info-COMMENT:  Result of Storage of DB.
            -- info-IMPL:     V1.3B->
            ENTERPRISE xldv11Traps
            VARIABLES { xldv11TvTimeAndDate,
                        xldv11TvBackupResult,
                        xldv11TvBackupResult }
            DESCRIPTION
                 " Result of Storage of DB. "
            ::= 119

         -- Event Trap (Introduced for XLDV1.1) 
         xldv11TrSwVersionSet TRAP-TYPE
            -- info-LEAF:     xldv11TrSwVersionSet
            -- info-TREE:     xldv11Traps
            -- info-TRAPTYPE: event
            -- info-TRAPID:   120
            -- info-TRAPVAR:  xldv11TvTimeAndDate,xldv11TvRepSource
            -- info-TRAPVAR:  xldv11TvRepEntity
            -- info-COMMENT:  Equipment holder data updated.
            -- info-IMPL:     V1.1U->
            ENTERPRISE xldv11Traps
            VARIABLES { xldv11TvTimeAndDate,
                        xldv11TvRepSource,
                        xldv11TvRepEntity }
            DESCRIPTION
                 " Equipment holder data updated. "
            ::= 120

         -- Event Trap (Introduced for XLDV1.1U)        
         xldv11TrReadSAPSContentFileReady TRAP-TYPE
            -- info-LEAF:     xldv11TrReadSAPSContentFileReady
            -- info-TREE:     xldv11Traps
            -- info-TRAPTYPE: event
            -- info-TRAPID:   121
            -- info-TRAPVAR:  xldv11TvTimeAndDate,xldv11TvSucResult 
            -- info-COMMENT:  End of SAPS content file reading.
            -- info-IMPL:     V1.1U->
            ENTERPRISE xldv11Traps
            VARIABLES { xldv11TvTimeAndDate,
                        xldv11TvSucResult }
            DESCRIPTION
                 " End of SAPS content file reading. "
            ::= 121

         -- Alarm Trap (Introduced for XLDV1.1U)        
         xldv11TrReplaceableUnitSwMissing TRAP-TYPE
            -- info-LEAF:      xldv11TrReplaceableUnitSwMissing
            -- info-TREE:      xldv11Traps
            -- info-TRAPTYPE:  alarm
            -- info-TRAPID:    122
            -- info-TRAPVAR:   alarm list
            -- info-COMMENT:   No SW load found in content file corresponding to mnemo
            -- info-COMMENT:   code and FW item number in equipHolder entry.
            -- info-FAILEDSRC: hwm
            -- info-FAILEDOBJ: LU155,LUDSX3,LUPON,CMU,SUAD,SUVD,LTAD
            -- info-FAILEDOBJ: LIETH,LI25,NTAD,NTVD
            -- info-IMPL:      V1.1U->
            ENTERPRISE xldv11Traps 
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " No SW load found in content file corresponding to mnemo code and
                   FW item number in equipHolder entry. "
            ::= 122

         -- Alarm Trap (Introduced for XLDV1.1U)        
         xldv11TrInternalFault TRAP-TYPE
            -- info-LEAF:      xldv11TrInternalFault
            -- info-TREE:      xldv11Traps
            -- info-TRAPTYPE:  alarm
            -- info-TRAPID:    123
            -- info-TRAPVAR:   alarm list
            -- info-COMMENT:   Internal SW/HW fault.
            -- info-FAILEDSRC: tlm
            -- info-FAILEDOBJ: S1n(= STM-1 NePPTP),S1f,S3n,E3n,D3n,S3f,
            -- info-FAILEDOBJ: D3f,E3f,Pon,Adc(= Adc-PPTP),Adr,Vdc,Vdr,
            -- info-FAILEDOBJ: Ibm(= Ibm-PPTP),Eth,Tca
            -- info-IMPL:      V1.1U->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Internal SW/HW fault. "
            ::= 123

         -- Event Trap (Introduced for XLDV1.1U)        
         xldv11TrAttributeValueChange TRAP-TYPE
            -- info-LEAF:     xldv11TrAttributeValueChange
            -- info-TREE:     xldv11Traps
            -- info-TRAPTYPE: event
            -- info-TRAPID:   124
            -- info-TRAPVAR:  xldv11TvTimeAndDate,xldv11TvSdvVpiNniOld
            -- info-TRAPVAR:  xldv11TvSdvVpiNniNew
            -- info-COMMENT:  SDVB configuration data modified.
            -- info-IMPL:     V1.1U->
            ENTERPRISE xldv11Traps
            VARIABLES { xldv11TvTimeAndDate,
                        xldv11TvSdvVpiNniOld,
                        xldv11TvSdvVpiNniNew }
            DESCRIPTION
                 " SDVB configuration data modified. "
            ::= 124


         -- Event Trap (Introduced for XLDV1.2a)        
         xldv11TrVplTpCreation TRAP-TYPE
            -- info-LEAF:     xldv11TrVplTpCreation
            -- info-TREE:     xldv11Traps
            -- info-TRAPTYPE: event
            -- info-TRAPID:   125
            -- info-TRAPVAR:  xldv11TvTimeAndDate,xldv11TvVpiValue
            -- info-TRAPVAR:  xldv11TvVplIfIndex,xldv11TvVplTpIndex
            -- info-TRAPVAR:  xldv11TvVpcTpIndex 
            -- info-COMMENT:  Vpl TP created.
            -- info-IMPL:     V1.2B->
            ENTERPRISE xldv11Traps
            VARIABLES { xldv11TvTimeAndDate,
                        xldv11TvVpiValue,
                        xldv11TvVplIfIndex,
                        xldv11TvVplTpIndex,
                        xldv11TvVpcTpIndex }
            DESCRIPTION
                 " Vpl TP created "
            ::= 125

         -- Event Trap (Introduced for XLDV1.2a)        
         xldv11TrVplTpDeletion TRAP-TYPE
            -- info-LEAF:     xldv11TrVplTpDeletion
            -- info-TREE:     xldv11Traps
            -- info-TRAPTYPE: event
            -- info-TRAPID:   126
            -- info-TRAPVAR:  xldv11TvTimeAndDate, xldv11TvVpiValue,
            -- info-TRAPVAR:  xldv11TvVplIfIndex, xldv11TvVplTpIndex,
            -- info-TRAPVAR:  xldv11TvVpcTpIndex
            -- info-COMMENT:  Vpl TP deleted.
            -- info-IMPL:     V1.2B->
            ENTERPRISE xldv11Traps
            VARIABLES { xldv11TvTimeAndDate,
                        xldv11TvVpiValue,
                        xldv11TvVplIfIndex,
                        xldv11TvVplTpIndex,
                        xldv11TvVpcTpIndex }
            DESCRIPTION
                 " Vpl TP deleted "
            ::= 126


         -- Event Trap (Introduced for XLDV1.2b)        
         xldv11TrVclCcCreation TRAP-TYPE
            -- info-LEAF:     xldv11TrVclCcCreation
            -- info-TREE:     xldv11Traps
            -- info-TRAPTYPE: event
            -- info-TRAPID:   127
            -- info-TRAPVAR:  xldv11TvTimeAndDate,xldv11TvVpiNni
            -- info-TRAPVAR:  xldv11TvVciNni,xldv11TvVciNniIndex
            -- info-TRAPVAR:  xldv11TvVplTerminationPointA,xldv11TvVplTerminationPointZ
            -- info-TRAPVAR:  xldv11TvVclTerminationPointA,xldv11TvVclTerminationPointZ
            -- info-TRAPVAR:  xldv11TvVpcNniIndex,xldv11TvVpcUniIndex 
            -- info-TRAPVAR:  xldv11TvEthVpcTpIndex, xldv11TvEthVccTpIndex,
            -- info-TRAPVAR:  xldv11TvEthVplTpIndex
            -- info-COMMENT:  The resulting indeces of a VC CC creation command.
            -- info-IMPL:     V1.2B->
            ENTERPRISE xldv11Traps
            VARIABLES { xldv11TvTimeAndDate,
                        xldv11TvVpiNni,
                        xldv11TvVciNni,
                        xldv11TvVciNniIndex,
                        xldv11TvVplTerminationPointA,
                        xldv11TvVplTerminationPointZ,
                        xldv11TvVclTerminationPointA,
                        xldv11TvVclTerminationPointZ,
                        xldv11TvEthVpcTpIndex,  
                        xldv11TvEthVccTpIndex,  
                        xldv11TvEthVplTpIndex }
            DESCRIPTION
                  " The resulting indeces of a VC CC creation command. "
            ::= 127

         -- Event Trap (Introduced for XLDV1.2b)        
         xldv11TrVclCcDeletion TRAP-TYPE
            -- info-LEAF:     xldv11TrVclCcDeletion
            -- info-TREE:     xldv11Traps
            -- info-TRAPTYPE: event
            -- info-TRAPID:   128
            -- info-TRAPVAR:  xldv11TvTimeAndDate,xldv11TvVpiNni
            -- info-TRAPVAR:  xldv11TvVciNni, xldv11TvVciNniIndex, 
            -- info-TRAPVAR:  xldv11TvVclTerminationPointA,xldv11TvVclTerminationPointZ
            -- info-TRAPVAR:  xldv11TvEthVpcTpIndex, xldv11TvEthVccTpIndex
            -- info-TRAPVAR:  xldv11TvEthVplTpIndex, xldv11TvEthEntryIndex 
            -- info-COMMENT:  The resulting indeces of a VCL CC deletion command.
            -- info-IMPL:     V1.2B->
            ENTERPRISE xldv11Traps
            VARIABLES { xldv11TvTimeAndDate,
                        xldv11TvVpiNni,
                        xldv11TvVciNni,
                        xldv11TvVciNniIndex,
                        xldv11TvVclTerminationPointA,
                        xldv11TvVclTerminationPointZ,
                        xldv11TvEthVpcTpIndex,
                        xldv11TvEthVccTpIndex,
                        xldv11TvEthVplTpIndex,
                        xldv11TvEthEntryIndex }
            DESCRIPTION
                  " The resulting indeces of a VCL CC deletion command. "
            ::= 128


         -- Alarm Trap (Introduced for XLDV1.2)
         xldv11TrImmMNR TRAP-TYPE
            -- info-LEAF:      xldv11TrImmMNR
            -- info-TREE:      xldv11Traps
            -- info-TRAPTYPE:  alarm
            -- info-TRAPID:    130
            -- info-TRAPVAR:   alarm list
            -- info-COMMENT:   Immediate Margin Not Reached Fault
            -- info-FAILEDSRC: tlm
            -- info-FAILEDOBJ: Adc(= Adc-PPTP)
            -- info-IMPL:      V1.3A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Immediate Margin Not Reached Fault "
            ::= 130

         -- Alarm Trap (Introduced for XLDV1.3)
         xldv11TrLpr TRAP-TYPE
            -- info-LEAF:      xldv11TrLpr
            -- info-TREE:      xldv11Traps
            -- info-TRAPTYPE:  alarm
            -- info-TRAPID:    131
            -- info-TRAPVAR:   alarm list
            -- info-COMMENT:   Loss of Power (dying gasp)
            -- info-FAILEDSRC: tlm
            -- info-FAILEDOBJ: Adr
            -- info-IMPL:      V1.3A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Loss of Power (dying gasp) "
            ::= 131
 
         -- Alarm Trap (Introduced for XLDV1.3)
         xldv11TrLol TRAP-TYPE
            -- info-LEAF:      xldv11TrLol
            -- info-TREE:      xldv11Traps
            -- info-TRAPTYPE:  alarm
            -- info-TRAPID:    132
            -- info-TRAPVAR:   alarm list
            -- info-COMMENT:   Loss of Link (ADC Los without preceding ADR Lpr)
            -- info-FAILEDSRC: tlm
            -- info-FAILEDOBJ: Adc(= Adc-PPTP)
            -- info-IMPL:      V1.3A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Loss of Link (ADC Los without preceding ADR Lpr) "
            ::= 132

         -- This trap indicates mass alarms AIS/RDI/LOC at
         -- VpcTp and VccTp objects. Up to 14 traps could be sent.
         -- These alarms are not logged at TMN-OS. 
         -- Via the xldv11AlmControlReq=startSendingAlarm the ONU is requested
         -- to send these alarms.

         -- Alarm Trap (Introduced for XLDV1.2B)
         xldv11TrAtmLayerMultiAlarm TRAP-TYPE
            -- info-LEAF:      xldv11TrAtmLayerMultiAlarm
            -- info-TREE:      xldv11Traps
            -- info-TRAPTYPE:  alarm
            -- info-TRAPID:    135
            -- info-TRAPVAR:   xldv11TvTimeAndDate, xldv11TvAlmSpecProblem,
            -- info-TRAPVAR:   xldv11TvAlmNatureOfAlarm,
            -- info-TRAPVAR:   xldv11TvAlmFailedComponentRepSource,
            -- info-TRAPVAR:   xldv11TvAlmSeverityOfFailure,
            -- info-TRAPVAR:   xldv11TvAlmStatus, xldv11TvAlmPropRepairAction,
            -- info-TRAPVAR:   xldv11TvAlmFailedComponentString 
            -- info-COMMENT:   Atm layer multi alarm trap 
            -- info-FAILEDSRC: cp
            -- info-FAILEDOBJ: VpcTp, VccTp,VclTp,VplTp
            -- info-IMPL:      V1.3A->
            ENTERPRISE xldv11Traps
            VARIABLES { xldv11TvTimeAndDate,
                        xldv11TvAlmSpecProblem,
                        xldv11TvAlmNatureOfAlarm,
                        xldv11TvAlmFailedComponentRepSource,
                        xldv11TvAlmSeverityOfFailure,
                        xldv11TvAlmStatus,
                        xldv11TvAlmPropRepairAction,
                        xldv11TvAlmFailedComponentString }
            DESCRIPTION
                 " Atm Layer Multi Alarm "
            ::= 135

         -- Event Trap (Introduced for XLDV1.3A)
         xldv11TrTelnetSession TRAP-TYPE
            -- info-LEAF:     xldv11TrTelnetSession
            -- info-TREE:     xldv11Traps
            -- info-TRAPTYPE: event
            -- info-TRAPID:   136
            -- info-TRAPVAR:  xldv11TvTimeAndDate,xldv11TvTelnetSession
            -- info-COMMENT:  Signalizes an established / stopped telnet session.
            -- info-IMPL:     V1.3A->
            ENTERPRISE xldv11Traps
            VARIABLES { xldv11TvTimeAndDate,
                        xldv11TvTelnetSession,
                        xldv11TvTelnetSessionUser }
            DESCRIPTION
                  " Signalizes an established / stopped telnet session. "
            ::= 136


         -- Event Trap (Introduced for XLDV1.3A)
         xldv11TrVplCACProblem TRAP-TYPE
            -- info-LEAF:     xldv11TrVplCACProblem
            -- info-TREE:     xldv11Traps
            -- info-TRAPTYPE: event
            -- info-TRAPID:   137
            -- info-TRAPVAR:   xldv11TvTimeAndDate, xldv11TvVpiValue, xldv11TvVplIfIndex,
            -- info-TRAPVAR:   xldv11TvCACProblemType, xldv11TvCACGuaranteedBandwidthUsage 
            -- info-COMMENT:  Indicates a resource warning by creating a VplCC 
            -- info-IMPL:     V1.3A->
            ENTERPRISE xldv11Traps
            VARIABLES { xldv11TvTimeAndDate,
                        xldv11TvVpiValue,
                        xldv11TvVplIfIndex,
                        xldv11TvCACProblemType,
                        xldv11TvCACGuaranteedBandwidthUsage }
            DESCRIPTION
                  " Indicates a warning for a resource problem
                    by creating a VplCC "
            ::= 137

         -- Event Trap (Introduced for XLDV1.3A)
         xldv11TrVplTpCACProblem TRAP-TYPE
            -- info-LEAF:     xldv11TrVplTpCACProblem
            -- info-TREE:     xldv11Traps
            -- info-TRAPTYPE: event
            -- info-TRAPID:   138
            -- info-TRAPVAR:   xldv11TvTimeAndDate, xldv11TvVpiValue, xldv11TvVplIfIndex,
            -- info-TRAPVAR:   xldv11TvCACProblemType, xldv11TvCACGuaranteedBandwidthUsage 
            -- info-COMMENT:  Indicates a resource warning while creating a VplTp 
            -- info-IMPL:     V1.3A->
            ENTERPRISE xldv11Traps
            VARIABLES { xldv11TvTimeAndDate,
                        xldv11TvVpiValue,
                        xldv11TvVplIfIndex,
                        xldv11TvCACProblemType,
                        xldv11TvCACGuaranteedBandwidthUsage }
            DESCRIPTION
                  " Indicates a warning for a resource problem
                    while creating a VplTP "
            ::= 138



         -- Event Trap (Introduced for XLDV1.3A)
         xldv11TrVclCACProblem TRAP-TYPE
            -- info-LEAF:     xldv11TrVclCACProblem
            -- info-TREE:     xldv11Traps
            -- info-TRAPTYPE: event
            -- info-TRAPID:   139
            -- info-TRAPVAR:   xldv11TvTimeAndDate, xldv11TvVpiValue, xldv11TvVplIfIndex  
            -- info-TRAPVAR:   xldv11TvVplTpIndex, xldv11TvVciValue, 
            -- info-TRAPVAR:   xldv11TvCACProblemType, xldv11TvCACGuaranteedBandwidthUsage 
            -- info-COMMENT:  Indicates a resource warning while creating a VclCC
            -- info-IMPL:     V1.3A->
            ENTERPRISE xldv11Traps
            VARIABLES { xldv11TvTimeAndDate, 
                        xldv11TvVpiValue, 
                        xldv11TvVplIfIndex,
                        xldv11TvVplTpIndex,
                        xldv11TvVciValue, 
                        xldv11TvCACProblemType, 
                        xldv11TvCACGuaranteedBandwidthUsage }
            DESCRIPTION
                  " Indicates a warning for a resource problem
                    while creating a VclCC"
            ::= 139

         -- Alarm Trap (Introduced for XLDV1.3a)        
         xldv11TrWrongServiceConfigData TRAP-TYPE
            -- info-LEAF:      xldv11TrWrongServiceConfigData
            -- info-TREE:      xldv11Traps
            -- info-TRAPTYPE:  alarm
            -- info-TRAPID:    141
            -- info-TRAPVAR:   alarm list
            -- info-COMMENT:   Config Adc Rates out of Range for UDSL.
            -- info-FAILEDSRC: tlm
            -- info-FAILEDOBJ: Adc(= Adc-PPTP)
            -- info-IMPL:      V1.3A->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Config Adc Rates out of Range for UDSL."
            ::= 141

         -- Event Trap (Introduced for XLDV1.2A)        
         xldv11TrReplaceableUnitPlugged TRAP-TYPE
            -- info-LEAF:     xldv11TrReplaceableUnitPlugged
            -- info-TREE:     xldv11Traps
            -- info-TRAPTYPE: event
            -- info-TRAPID:   142
            -- info-TRAPVAR:  xldv11TvTimeAndDate,xldv11TvRepEntity
            -- info-TRAPVAR:  xldv11TvRepSource
            -- info-COMMENT:  Notification: A PIU has been plugged.
            -- info-IMPL:     V1.2A->
            ENTERPRISE xldv11Traps
            VARIABLES { xldv11TvTimeAndDate,
                        xldv11TvRepEntity,
                        xldv11TvRepSource }
            DESCRIPTION
                 " Notification: A PIU has been plugged. "
            ::= 142

         -- Event Trap (Introduced for XLDV1.2A)        
         xldv11TrReplaceableUnitUnplugged TRAP-TYPE
            -- info-LEAF:     xldv11TrReplaceableUnitUnplugged
            -- info-TREE:     xldv11Traps
            -- info-TRAPTYPE: event
            -- info-TRAPID:   143
            -- info-TRAPVAR:  xldv11TvTimeAndDate,xldv11TvRepEntity
            -- info-TRAPVAR:  xldv11TvRepSource
            -- info-COMMENT:  Notification: A PIU has been unplugged.
            -- info-IMPL:     V1.2A->
            ENTERPRISE xldv11Traps
            VARIABLES { xldv11TvTimeAndDate,
                        xldv11TvRepEntity,
                        xldv11TvRepSource }
            DESCRIPTION
                 " Notification: A PIU has been unplugged. "
            ::= 143

         -- Event Trap (Introduced for XLDV1.3B)        
         xldv11TrStateChangeOperExt TRAP-TYPE
            -- info-LEAF:     xldv11TrStateChangeOperExt
            -- info-TREE:     xldv11Traps
            -- info-TRAPTYPE: event
            -- info-TRAPID:   144
            -- info-TRAPVAR:  xldv11TvTimeAndDate,xldv11TvRepEntityExt
            -- info-TRAPVAR:  xldv11TvRepSource,xldv11TvStcOldOperStatus
            -- info-TRAPVAR:  xldv11TvStcNewOperStatus
            -- info-COMMENT:  The operational state of the
            -- info-COMMENT:  reporting entity has changed.
            -- info-IMPL:     V1.2B->
            ENTERPRISE xldv11Traps
            VARIABLES { xldv11TvTimeAndDate,
                        xldv11TvRepEntityExt,
                        xldv11TvRepSource,
                        xldv11TvStcOldOperStatus,
                        xldv11TvStcNewOperStatus }
            DESCRIPTION
                 " The operational state of the reporting external entity
                   has changed. "
            ::= 144

         -- Alarm Trap (Introduced for XLDV1.3B)        
         xldv11TrLOC TRAP-TYPE
            -- info-LEAF:      xldv11TrLOC 
            -- info-TREE:      xldv11Traps
            -- info-TRAPTYPE:  alarm
            -- info-TRAPID:    145 
            -- info-TRAPVAR:   alarm lists
            -- info-COMMENT:   Loss of continuity 
            -- info-FAILEDSRC: cp   
            -- info-FAILEDOBJ: VclTp, VplTp
            -- info-IMPL:      V1.3B->
            ENTERPRISE xldv11Traps
            VARIABLES { xldv11TvTimeAndDate,
                        xldv11TvRepEntity,
                        xldv11TvRepSource,
                        xldv11TvAlmSpecProblem,
                        xldv11TvAlmNatureOfAlarm,
                        xldv11TvAlmFailedComponent,
                        xldv11TvAlmFailedComponentRepSource,
                        xldv11TvAlmSeverityOfFailure,
                        xldv11TvAlmStatus,
                        xldv11TvAlmPropRepairAction }
            DESCRIPTION
                 " Loss of continuity. "
            ::= 145

         -- Event Trap (Introduced for XLDV1.3B)        
         xldv11TrContinuityCheckVplTpEntryCreated TRAP-TYPE
            -- info-LEAF:      xldv11TrContinuityCheckVplTpEntryCreated
            -- info-TREE:      xldv11Traps
            -- info-TRAPTYPE:  event
            -- info-TRAPID:    146 
            -- info-TRAPVAR:   xldv11TvTimeAndDate,xldv11TvCvpIndexSource,
            -- info-TRAPVAR:   xldv11TvCvpIndexSink
            -- info-COMMENT:   Xldv11ContinuityCheckVplTpEntry created
            -- info-IMPL:      V1.3B->
            ENTERPRISE xldv11Traps
            VARIABLES { xldv11TvTimeAndDate,
                        xldv11TvCvpIndexSource,
                        xldv11TvCvpIndexSink}
            DESCRIPTION
                 " Xldv11ContinuityCheckVplTpEntry created . "
            ::= 146

         -- Event Trap (Introduced for XLDV1.3B)        
         xldv11TrContinuityCheckVplTpEntryDeleted TRAP-TYPE
            -- info-LEAF:      xldv11TrContinuityCheckVplTpEntryDeleted
            -- info-TREE:      xldv11Traps
            -- info-TRAPTYPE:  event
            -- info-TRAPID:    147 
            -- info-TRAPVAR:   xldv11TvTimeAndDate,xldv11TvCvpIndexSource,
            -- info-TRAPVAR:   xldv11TvCvpIndexSink
            -- info-COMMENT:   Xldv11ContinuityCheckVplTpEntry deleted
            -- info-IMPL:      V1.3B->
            ENTERPRISE xldv11Traps
            VARIABLES { xldv11TvTimeAndDate,
                        xldv11TvCvpIndexSource,
                        xldv11TvCvpIndexSink}
            DESCRIPTION
                 " Xldv11ContinuityCheckVplTpEntry deleted . "
            ::= 147

         -- Event Trap (Introduced for XLDV1.3B)        
         xldv11TrContinuityCheckVclTpEntryCreated TRAP-TYPE
            -- info-LEAF:      xldv11TrContinuityCheckVclTpEntryCreated
            -- info-TREE:      xldv11Traps
            -- info-TRAPTYPE:  event
            -- info-TRAPID:    148 
            -- info-TRAPVAR:   xldv11TvTimeAndDate,xldv11TvCvcIndexSource,
            -- info-TRAPVAR:   xldv11TvCvcIndexSink
            -- info-COMMENT:   Xldv11ContinuityCheckVclTpEntry created
            -- info-IMPL:      V1.3B->
            ENTERPRISE xldv11Traps
            VARIABLES { xldv11TvTimeAndDate,
                        xldv11TvCvcIndexSource,
                        xldv11TvCvcIndexSink}
            DESCRIPTION
                 " Xldv11ContinuityCheckVclTpEntry created . "
            ::= 148

         xldv11TrContinuityCheckVclTpEntryDeleted TRAP-TYPE
            -- info-LEAF:      xldv11TrContinuityCheckVclTpEntryDeleted
            -- info-TREE:      xldv11Traps
            -- info-TRAPTYPE:  event
            -- info-TRAPID:    149 
            -- info-TRAPVAR:   xldv11TvTimeAndDate,xldv11TvCvcIndexSource,
            -- info-TRAPVAR:   xldv11TvCvcIndexSink
            -- info-COMMENT:   Xldv11ContinuityCheckVclTpEntry deleted
            -- info-IMPL:      V1.3B->
            ENTERPRISE xldv11Traps
            VARIABLES { xldv11TvTimeAndDate,
                        xldv11TvCvcIndexSource,
                        xldv11TvCvcIndexSink}
            DESCRIPTION
                 " Xldv11ContinuityCheckVclTpEntry deleted . "
            ::= 149

         xldv11TrDbRestore TRAP-TYPE
            -- info-LEAF:      xldv11TrDbRestore
            -- info-TREE:      xldv11Traps
            -- info-TRAPTYPE:  event
            -- info-TRAPID:    150
            -- info-TRAPVAR:   xldv11TvTimeAndDate
            -- info-TRAPVAR:   xldv11TvDbRestoreResult
            -- info-COMMENT:   result of DB restoration after reload
            -- info-IMPL:      V1.3H->
            ENTERPRISE xldv11Traps
            VARIABLES { xldv11TvTimeAndDate,
                        xldv11TvRestoreResult}
            DESCRIPTION
                 " DB restoration result. "
            ::= 150

         xldv11TrUpgradeEndRequestResult TRAP-TYPE
            -- info-LEAF:      xldv11TrUpgradeEndRequestResult
            -- info-TREE:      xldv11Traps
            -- info-TRAPTYPE:  event
            -- info-TRAPID:    151
            -- info-TRAPVAR:   xldv11TvTimeAndDate
            -- info-TRAPVAR:   xldv11TvSucResult
            -- info-COMMENT:   result of sucUpgrEndRequest command
            -- info-IMPL:      V1.3H->
            ENTERPRISE xldv11Traps
            VARIABLES { xldv11TvTimeAndDate,
                        xldv11TvSucResult}
            DESCRIPTION
                 " Result of sucUpgrEndRequest command. "
            ::= 151
	    
         xldv11TrUnitUpgradeNotRequested TRAP-TYPE
            -- info-LEAF:      xldv11TrUnitUpgradeNotRequested
            -- info-TREE:      xldv11Traps
            -- info-TRAPTYPE:  event
            -- info-TRAPID:    152
            -- info-TRAPVAR:   xldv11TvTimeAndDate,xldv11TvSucUnit,
            -- info-TRAPVAR:   xldv11TvSucHwUnitIndex,xldv11TvSucVersionNo
            -- info-COMMENT:   result of sucUpgrEndRequest command
            -- info-IMPL:      V1.3H->
            ENTERPRISE xldv11Traps
            VARIABLES { xldv11TvTimeAndDate,
                        xldv11TvSucUnit,
                        xldv11TvSucHwUnitIndex,
                        xldv11TvSucVersionNo }
            DESCRIPTION
                 " Result of sucUpgrEndRequest command. "
            ::= 152
	    
END
